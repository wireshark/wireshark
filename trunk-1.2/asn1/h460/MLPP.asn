-- MLPP.asn
--
-- Taken from ITU ASN.1 database
-- http://www.itu.int/ITU-T/asn1/database/itu-t/h/h460.14/2004/MLPP.asn
--
-- $Id$
--

-- Module MLPP (H.460.14:03/2004)
MLPP DEFINITIONS AUTOMATIC TAGS ::=
BEGIN

IMPORTS
  CallIdentifier, AliasAddress
    FROM H323-MESSAGES; -- defined in H.225.0, Annex H

MLPPInfo ::= SEQUENCE -- root for MLPP data ASN.1
              {
  precedence        MlppPrecedence OPTIONAL,
  mlppReason        MlppReason OPTIONAL,
  mlppNotification  MlppNotification OPTIONAL,
  alternateParty    AlternateParty OPTIONAL,
  releaseCall       ReleaseCall OPTIONAL,
  ...
}

MlppPrecedence ::= ENUMERATED {
  flashOveride(0), flash(1), immediate(2), priority(3), routine(4), ...
  }

MlppReason ::=
  ENUMERATED -- Indicates reasons that call is refused or released.
  {preemptionNoReservation(8), preemptionReservation(9), callBlocked(46), ...
   }

MlppNotification ::=
  CHOICE
   -- Provides various notification events in Call Signalling messages
  {
  preemptionPending     NULL,
  preemptionInProgress  NULL,
  preemptionEnd         NULL,
  preemptionComplete    NULL,
  ...
}

AlternateParty ::= SEQUENCE {
  altID     AliasAddress,
  altTimer  INTEGER(0..255) OPTIONAL, --seconds
  ...
}

ReleaseCall ::= SEQUENCE
                 -- Identifies other call to be preempted first
                {
  preemptCallID  CallIdentifier,
  releaseReason  MlppReason,
  releaseDelay   INTEGER(0..255) OPTIONAL, --seconds to wait
  ...
}

END

-- Generated by Asnp, the ASN.1 pretty-printer of France Telecom R&D

-- RNSAP-Constants.asn
--
-- Taken from 3GPP TS 25.423 V7.9.0 (2008-06-13)
-- http://www.3gpp.org/ftp/Specs/archive/25_series/25.423/25423-790.zip/25423-790.DOC
--
-- 9.3.6	Constant Definitions
--
-- $Id$
--

-- **************************************************************
--
-- Constant definitions
--
-- **************************************************************

RNSAP-Constants {
itu-t (0) identified-organization (4) etsi (0) mobileDomain (0) 
umts-Access (20) modules (3) rnsap (1) version1 (1) rnsap-Constants (4) }

DEFINITIONS AUTOMATIC TAGS ::= 

BEGIN

IMPORTS
	ProcedureCode,
	ProtocolIE-ID
FROM RNSAP-CommonDataTypes;

-- **************************************************************
--
-- Elementary Procedures
--
-- **************************************************************

id-commonTransportChannelResourcesInitialisation			ProcedureCode ::= 0
id-commonTransportChannelResourcesRelease					ProcedureCode ::= 1
id-compressedModeCommand									ProcedureCode ::= 2
id-downlinkPowerControl										ProcedureCode ::= 3
id-downlinkPowerTimeslotControl								ProcedureCode ::= 4
id-downlinkSignallingTransfer								ProcedureCode ::= 5
id-errorIndication											ProcedureCode ::= 6
id-dedicatedMeasurementFailure								ProcedureCode ::= 7
id-dedicatedMeasurementInitiation							ProcedureCode ::= 8
id-dedicatedMeasurementReporting							ProcedureCode ::= 9
id-dedicatedMeasurementTermination							ProcedureCode ::= 10
id-paging													ProcedureCode ::= 11
id-physicalChannelReconfiguration							ProcedureCode ::= 12
id-privateMessage											ProcedureCode ::= 13
id-radioLinkAddition										ProcedureCode ::= 14
id-radioLinkCongestion										ProcedureCode ::= 34
id-radioLinkDeletion										ProcedureCode ::= 15
id-radioLinkFailure											ProcedureCode ::= 16
id-radioLinkPreemption										ProcedureCode ::= 17
id-radioLinkRestoration										ProcedureCode ::= 18
id-radioLinkSetup											ProcedureCode ::= 19
id-relocationCommit											ProcedureCode ::= 20
id-synchronisedRadioLinkReconfigurationCancellation			ProcedureCode ::= 21
id-synchronisedRadioLinkReconfigurationCommit				ProcedureCode ::= 22
id-synchronisedRadioLinkReconfigurationPreparation			ProcedureCode ::= 23
id-unSynchronisedRadioLinkReconfiguration					ProcedureCode ::= 24
id-uplinkSignallingTransfer									ProcedureCode ::= 25
id-commonMeasurementFailure									ProcedureCode ::= 26
id-commonMeasurementInitiation								ProcedureCode ::= 27
id-commonMeasurementReporting								ProcedureCode ::= 28
id-commonMeasurementTermination								ProcedureCode ::= 29
id-informationExchangeFailure								ProcedureCode ::= 30
id-informationExchangeInitiation							ProcedureCode ::= 31
id-informationReporting										ProcedureCode ::= 32
id-informationExchangeTermination							ProcedureCode ::= 33
id-reset													ProcedureCode ::= 35
id-radioLinkActivation 										ProcedureCode ::= 36
id-gERANuplinkSignallingTransfer							ProcedureCode ::= 37
id-radioLinkParameterUpdate									ProcedureCode ::= 38
id-uEMeasurementFailure										ProcedureCode ::= 39
id-uEMeasurementInitiation									ProcedureCode ::= 40
id-uEMeasurementReporting									ProcedureCode ::= 41
id-uEMeasurementTermination									ProcedureCode ::= 42
id-iurDeactivateTrace										ProcedureCode ::= 43
id-iurInvokeTrace											ProcedureCode ::= 44
id-mBMSAttach												ProcedureCode ::= 45
id-mBMSDetach												ProcedureCode ::= 46
id-directInformationTransfer								ProcedureCode ::= 48

-- **************************************************************
--
-- Lists
--
-- **************************************************************

maxCellSIB11OrSIB12						INTEGER ::= 32
maxCellsMeas							INTEGER ::= 8
maxRateMatching							INTEGER ::= 256
maxNoOfDSCHs							INTEGER ::= 10
maxNoOfDSCHsLCR							INTEGER ::= 10
maxNoOfRB								INTEGER ::= 32
maxNoOfUSCHs							INTEGER ::= 10
maxNoOfUSCHsLCR							INTEGER ::= 10
maxNrOfTFCs								INTEGER ::= 1024
maxNrOfTFs								INTEGER ::= 32
maxNrOfCCTrCHs							INTEGER ::= 16
maxNrOfCCTrCHsLCR						INTEGER ::= 16
maxNrOfDCHs								INTEGER ::= 128
maxNrOfDL-Codes							INTEGER ::= 8
maxNrOfDPCHs							INTEGER ::= 240
maxNrOfDPCHsPerRL-1						INTEGER ::= 239 -- maxNrofCCTrCH*maxNrOfULTs-1
maxNrOfDPCHsLCR							INTEGER ::= 240
maxNrOfDPCHsLCRPerRL-1					INTEGER ::= 95  -- maxNrofCCTrCH*maxNrOfULTsLCR-1
maxNrOfDPCHs768							INTEGER ::= 480
maxNrOfDPCHs768PerRL-1					INTEGER ::= 479
maxNrOfErrors							INTEGER ::= 256
maxNrOfMACcshSDU-Length					INTEGER ::= 16
maxNrOfMBMSServices						INTEGER ::= 128
maxNrOfActiveMBMSServices				INTEGER ::= 256
maxNrOfPoints							INTEGER ::= 15
maxNrOfRLs								INTEGER ::= 16
maxNrOfRLSets							INTEGER ::= maxNrOfRLs
maxNrOfRLSets-1						INTEGER ::= 15	-- maxNrOfRLSets - 1
maxNrOfRLs-1							INTEGER ::= 15	-- maxNrOfRLs - 1
maxNrOfRLs-2							INTEGER ::= 14	-- maxNrOfRLs - 2
maxNrOfUEs								INTEGER ::= 4096
maxNrOfULTs								INTEGER ::= 15
maxNrOfULTsLCR							INTEGER ::= 6
maxNrOfDLTs								INTEGER ::= 15
maxNrOfDLTsLCR							INTEGER ::= 6
maxRNCinURA-1							INTEGER ::= 15
maxTTI-Count							INTEGER ::= 4
maxCTFC									INTEGER ::= 16777215
maxNrOfNeighbouringRNCs					INTEGER ::= 10
maxNrOfFDDNeighboursPerRNC				INTEGER ::= 256
maxNrOfGSMNeighboursPerRNC				INTEGER ::= 256
maxNrOfTDDNeighboursPerRNC				INTEGER ::= 256
maxNrOfFACHs							INTEGER	::=	8
maxNrOfLCRTDDNeighboursPerRNC			INTEGER ::= 256
maxIBSEG								INTEGER ::= 16
maxNrOfSCCPCHs							INTEGER	::=	8
maxNrOfSCCPCHs768						INTEGER	::=	16
maxTGPS									INTEGER ::= 6
maxNrOfTS								INTEGER ::= 15
maxNrOfLevels							INTEGER ::= 256
maxNrOfTsLCR							INTEGER ::= 6
maxNoSat								INTEGER ::= 16
maxNoGPSTypes							INTEGER ::= 8
maxNrOfMeasNCell						INTEGER ::= 96
maxNrOfMeasNCell-1						INTEGER ::= 95	-- maxNrOfMeasNCell - 1
maxResetContext							INTEGER ::= 250
maxResetContextGroup					INTEGER ::= 32
maxNrOfHARQProc							INTEGER ::= 8
maxNrOfHSSCCHCodes						INTEGER ::= 4
maxNrOfHSSICHs							INTEGER ::= 4
maxNrOfHSSICHs-1						INTEGER ::= 3
maxNrOfMACdFlows						INTEGER ::= 8
maxNrOfMACdFlows-1						INTEGER ::= 7	-- maxNrOfMACdFlows - 1
maxNrOfMACdPDUSize						INTEGER ::= 32
maxNrOfPDUIndexes						INTEGER ::= 8
maxNrOfPDUIndexes-1						INTEGER ::= 7	-- maxNrOfPDUIndexes - 1
maxNrOfPrioQueues						INTEGER ::= 8
maxNrOfPrioQueues-1						INTEGER ::= 7	-- maxNrOfPrioQueues - 1
maxNrOfSNAs								INTEGER ::= 65536
maxNrOfSatAlmanac-maxNoSat				INTEGER ::= 16
maxNrOfGERANSI 							INTEGER ::= 8
maxNrOfInterfaces						INTEGER ::= 16
maxNrofSigSeqERGHICH-1					INTEGER ::= 39
maxNrOfCells							INTEGER ::= 65536
maxNrOfAddFreq							INTEGER ::= 8
maxNrOfCellsPerFreq						INTEGER ::= 65536
maxNrOfEDCHMACdFlows-1					INTEGER ::= 7
maxNrOfEDCH-HARQ-PO-QUANTSTEPs			INTEGER ::= 6
maxNrOfEDPCCH-PO-QUANTSTEPs				INTEGER ::= 8
maxNrOfEDCHHARQProcesses2msEDCH			INTEGER ::= 8
maxNrOfBits-MACe-PDU-non-scheduled		INTEGER ::= 19982
maxNrOfRefETFCIs						INTEGER ::= 8
maxNrOfRefETFCI-PO-QUANTSTEPs			INTEGER ::= 29
maxNrOfEDCHMACdFlows					INTEGER ::= 8
maxNoOfLogicalChannels					INTEGER ::= 16 -- only maximum 15 can be used
maxNrOfRefBetas							INTEGER ::= 8
maxNrOfEAGCHCodes						INTEGER ::= 4
maxNrOfHS-DSCHTBSs						INTEGER ::= 90
maxNrOfHS-DSCHTBSs-HS-SCCHless			INTEGER ::= 4
maxHS-PDSCHCodeNrComp-1					INTEGER ::= 15
maxNrOfEHICHCodes						INTEGER ::= 4
maxGANSSSat								INTEGER ::= 64
maxNoGANSS								INTEGER ::= 8
maxSgnType								INTEGER ::= 8
maxNrOfBroadcastPLMNs					INTEGER ::= 5
maxHSDPAFrequency						INTEGER ::= 8
maxHSDPAFrequency-1						INTEGER ::= 7
maxFrequencyinCell						INTEGER ::= 12
maxFrequencyinCell-1					INTEGER ::= 11
maxGANSSSatAlmanac						INTEGER ::= 36
maxGANSSClockMod						INTEGER ::= 4
maxNrOfEDCHRLs							INTEGER ::= 4





-- **************************************************************
--
-- IEs
--
-- **************************************************************

id-AllowedQueuingTime														ProtocolIE-ID ::= 4
id-Allowed-Rate-Information													ProtocolIE-ID ::= 42
id-AntennaColocationIndicator												ProtocolIE-ID ::= 309
id-BindingID																ProtocolIE-ID ::= 5
id-C-ID																		ProtocolIE-ID ::= 6
id-C-RNTI																	ProtocolIE-ID ::= 7
id-Cell-Capacity-Class-Value												ProtocolIE-ID ::= 303
id-CFN																		ProtocolIE-ID ::= 8
id-CN-CS-DomainIdentifier													ProtocolIE-ID ::= 9
id-CN-PS-DomainIdentifier													ProtocolIE-ID ::= 10
id-Cause																	ProtocolIE-ID ::= 11
id-CoverageIndicator														ProtocolIE-ID ::= 310
id-CriticalityDiagnostics													ProtocolIE-ID ::= 20
id-ContextInfoItem-Reset													ProtocolIE-ID ::= 211
id-ContextGroupInfoItem-Reset												ProtocolIE-ID ::= 515
id-D-RNTI																	ProtocolIE-ID ::= 21
id-D-RNTI-ReleaseIndication													ProtocolIE-ID ::= 22
id-DCHs-to-Add-FDD															ProtocolIE-ID ::= 26
id-DCHs-to-Add-TDD															ProtocolIE-ID ::= 27
id-DCH-DeleteList-RL-ReconfPrepFDD											ProtocolIE-ID ::= 30
id-DCH-DeleteList-RL-ReconfPrepTDD											ProtocolIE-ID ::= 31
id-DCH-DeleteList-RL-ReconfRqstFDD											ProtocolIE-ID ::= 32
id-DCH-DeleteList-RL-ReconfRqstTDD											ProtocolIE-ID ::= 33
id-DCH-FDD-Information														ProtocolIE-ID ::= 34
id-DCH-TDD-Information														ProtocolIE-ID ::= 35
id-FDD-DCHs-to-Modify														ProtocolIE-ID ::= 39
id-TDD-DCHs-to-Modify														ProtocolIE-ID ::= 40
id-DCH-InformationResponse													ProtocolIE-ID ::= 43
id-DCH-Rate-InformationItem-RL-CongestInd									ProtocolIE-ID ::= 38
id-DL-CCTrCH-InformationAddItem-RL-ReconfPrepTDD							ProtocolIE-ID ::= 44
id-DL-CCTrCH-InformationListIE-RL-ReconfReadyTDD							ProtocolIE-ID ::= 45
id-DL-CCTrCH-InformationDeleteItem-RL-ReconfRqstTDD							ProtocolIE-ID ::= 46
id-DL-CCTrCH-InformationItem-RL-SetupRqstTDD								ProtocolIE-ID ::= 47
id-DL-CCTrCH-InformationListIE-PhyChReconfRqstTDD							ProtocolIE-ID ::= 48
id-DL-CCTrCH-InformationListIE-RL-AdditionRspTDD							ProtocolIE-ID ::= 49
id-DL-CCTrCH-InformationListIE-RL-SetupRspTDD								ProtocolIE-ID ::= 50
id-DL-CCTrCH-InformationAddList-RL-ReconfPrepTDD							ProtocolIE-ID ::= 51
id-DL-CCTrCH-InformationDeleteList-RL-ReconfRqstTDD							ProtocolIE-ID ::= 52
id-DL-CCTrCH-InformationList-RL-SetupRqstTDD								ProtocolIE-ID ::= 53
id-FDD-DL-CodeInformation													ProtocolIE-ID ::= 54
id-DL-DPCH-Information-RL-ReconfPrepFDD										ProtocolIE-ID ::= 59
id-DL-DPCH-Information-RL-SetupRqstFDD										ProtocolIE-ID ::= 60
id-DL-DPCH-Information-RL-ReconfRqstFDD										ProtocolIE-ID ::= 61
id-DL-DPCH-InformationItem-PhyChReconfRqstTDD								ProtocolIE-ID ::= 62
id-DL-DPCH-InformationItem-RL-AdditionRspTDD								ProtocolIE-ID ::= 63
id-DL-DPCH-InformationItem-RL-SetupRspTDD									ProtocolIE-ID ::= 64
id-DL-DPCH-TimingAdjustment													ProtocolIE-ID ::= 278
id-DLReferencePower															ProtocolIE-ID ::= 67
id-DLReferencePowerList-DL-PC-Rqst											ProtocolIE-ID ::= 68
id-DL-ReferencePowerInformation-DL-PC-Rqst									ProtocolIE-ID ::= 69
id-DPC-Mode																	ProtocolIE-ID ::= 12
id-DRXCycleLengthCoefficient												ProtocolIE-ID ::= 70
id-DedicatedMeasurementObjectType-DM-Fail-Ind								ProtocolIE-ID ::= 470
id-DedicatedMeasurementObjectType-DM-Fail									ProtocolIE-ID ::= 471
id-DedicatedMeasurementObjectType-DM-Rprt									ProtocolIE-ID ::= 71
id-DedicatedMeasurementObjectType-DM-Rqst									ProtocolIE-ID ::= 72
id-DedicatedMeasurementObjectType-DM-Rsp									ProtocolIE-ID ::= 73
id-DedicatedMeasurementType													ProtocolIE-ID ::= 74
id-FACH-InfoForUESelectedS-CCPCH-CTCH-ResourceRspFDD						ProtocolIE-ID ::= 82
id-FACH-InfoForUESelectedS-CCPCH-CTCH-ResourceRspTDD						ProtocolIE-ID ::= 83
id-Guaranteed-Rate-Information												ProtocolIE-ID ::= 41
id-IMSI																		ProtocolIE-ID ::= 84
id-HCS-Prio																	ProtocolIE-ID ::= 311
id-L3-Information															ProtocolIE-ID ::= 85
id-AdjustmentPeriod															ProtocolIE-ID ::= 90
id-MaxAdjustmentStep														ProtocolIE-ID ::= 91
id-MeasurementFilterCoefficient												ProtocolIE-ID ::= 92
id-MessageStructure															ProtocolIE-ID ::= 57
id-MeasurementID															ProtocolIE-ID ::= 93
id-Neighbouring-GSM-CellInformation											ProtocolIE-ID ::= 13
id-Neighbouring-UMTS-CellInformationItem									ProtocolIE-ID ::= 95
id-NRT-Load-Information-Value												ProtocolIE-ID ::= 305
id-NRT-Load-Information-Value-IncrDecrThres									ProtocolIE-ID ::= 306
id-PagingArea-PagingRqst													ProtocolIE-ID ::= 102
id-FACH-FlowControlInformation												ProtocolIE-ID ::= 103
id-PartialReportingIndicator												ProtocolIE-ID ::= 472
id-Permanent-NAS-UE-Identity												ProtocolIE-ID ::= 17
id-PowerAdjustmentType														ProtocolIE-ID ::= 107
id-RANAP-RelocationInformation												ProtocolIE-ID ::= 109
id-RL-Information-PhyChReconfRqstFDD										ProtocolIE-ID ::= 110
id-RL-Information-PhyChReconfRqstTDD										ProtocolIE-ID ::= 111
id-RL-Information-RL-AdditionRqstFDD										ProtocolIE-ID ::= 112
id-RL-Information-RL-AdditionRqstTDD										ProtocolIE-ID ::= 113
id-RL-Information-RL-DeletionRqst											ProtocolIE-ID ::= 114
id-RL-Information-RL-FailureInd												ProtocolIE-ID ::= 115
id-RL-Information-RL-ReconfPrepFDD											ProtocolIE-ID ::= 116
id-RL-Information-RL-RestoreInd												ProtocolIE-ID ::= 117
id-RL-Information-RL-SetupRqstFDD											ProtocolIE-ID ::= 118
id-RL-Information-RL-SetupRqstTDD											ProtocolIE-ID ::= 119
id-RL-InformationItem-RL-CongestInd											ProtocolIE-ID ::= 55
id-RL-InformationItem-DM-Rprt												ProtocolIE-ID ::= 120
id-RL-InformationItem-DM-Rqst												ProtocolIE-ID ::= 121
id-RL-InformationItem-DM-Rsp												ProtocolIE-ID ::= 122
id-RL-InformationItem-RL-PreemptRequiredInd									ProtocolIE-ID ::= 2
id-RL-InformationItem-RL-SetupRqstFDD										ProtocolIE-ID ::= 123
id-RL-InformationList-RL-CongestInd											ProtocolIE-ID ::= 56
id-RL-InformationList-RL-AdditionRqstFDD									ProtocolIE-ID ::= 124
id-RL-InformationList-RL-DeletionRqst										ProtocolIE-ID ::= 125
id-RL-InformationList-RL-PreemptRequiredInd									ProtocolIE-ID ::= 1
id-RL-InformationList-RL-ReconfPrepFDD										ProtocolIE-ID ::= 126
id-RL-InformationResponse-RL-AdditionRspTDD									ProtocolIE-ID ::= 127
id-RL-InformationResponse-RL-ReconfReadyTDD									ProtocolIE-ID ::= 128
id-RL-InformationResponse-RL-SetupRspTDD									ProtocolIE-ID ::= 129
id-RL-InformationResponseItem-RL-AdditionRspFDD								ProtocolIE-ID ::= 130
id-RL-InformationResponseItem-RL-ReconfReadyFDD								ProtocolIE-ID ::= 131
id-RL-InformationResponseItem-RL-ReconfRspFDD								ProtocolIE-ID ::= 132
id-RL-InformationResponseItem-RL-SetupRspFDD								ProtocolIE-ID ::= 133
id-RL-InformationResponseList-RL-AdditionRspFDD								ProtocolIE-ID ::= 134
id-RL-InformationResponseList-RL-ReconfReadyFDD								ProtocolIE-ID ::= 135
id-RL-InformationResponseList-RL-ReconfRspFDD								ProtocolIE-ID ::= 136
id-RL-InformationResponse-RL-ReconfRspTDD									ProtocolIE-ID ::= 28
id-RL-InformationResponseList-RL-SetupRspFDD								ProtocolIE-ID ::= 137
id-RL-ReconfigurationFailure-RL-ReconfFail									ProtocolIE-ID ::= 141
id-RL-Set-InformationItem-DM-Rprt											ProtocolIE-ID ::= 143
id-RL-Set-InformationItem-DM-Rqst											ProtocolIE-ID ::= 144
id-RL-Set-InformationItem-DM-Rsp											ProtocolIE-ID ::= 145
id-RL-Set-Information-RL-FailureInd											ProtocolIE-ID ::= 146
id-RL-Set-Information-RL-RestoreInd											ProtocolIE-ID ::= 147
id-RL-Set-Successful-InformationItem-DM-Fail								ProtocolIE-ID ::= 473
id-RL-Set-Unsuccessful-InformationItem-DM-Fail								ProtocolIE-ID ::= 474
id-RL-Set-Unsuccessful-InformationItem-DM-Fail-Ind							ProtocolIE-ID ::= 475
id-RL-Successful-InformationItem-DM-Fail									ProtocolIE-ID ::= 476
id-RL-Unsuccessful-InformationItem-DM-Fail									ProtocolIE-ID ::= 477
id-RL-Unsuccessful-InformationItem-DM-Fail-Ind								ProtocolIE-ID ::= 478
id-ReportCharacteristics													ProtocolIE-ID ::= 152
id-Reporting-Object-RL-FailureInd											ProtocolIE-ID ::= 153
id-Reporing-Object-RL-RestoreInd											ProtocolIE-ID ::= 154
id-RT-Load-Value															ProtocolIE-ID ::= 307
id-RT-Load-Value-IncrDecrThres												ProtocolIE-ID ::= 308
id-S-RNTI																	ProtocolIE-ID ::= 155
id-ResetIndicator															ProtocolIE-ID ::= 244
id-RNC-ID																	ProtocolIE-ID ::= 245
id-SAI																		ProtocolIE-ID ::= 156
id-SRNC-ID																	ProtocolIE-ID ::= 157
id-SuccessfulRL-InformationResponse-RL-AdditionFailureFDD					ProtocolIE-ID ::= 159
id-SuccessfulRL-InformationResponse-RL-SetupFailureFDD						ProtocolIE-ID ::= 160
id-TransportBearerID														ProtocolIE-ID ::= 163
id-TransportBearerRequestIndicator											ProtocolIE-ID ::= 164
id-TransportLayerAddress													ProtocolIE-ID ::= 165
id-TypeOfError																ProtocolIE-ID ::= 140
id-UC-ID																	ProtocolIE-ID ::= 166
id-UL-CCTrCH-AddInformation-RL-ReconfPrepTDD								ProtocolIE-ID ::= 167
id-UL-CCTrCH-InformationAddList-RL-ReconfPrepTDD							ProtocolIE-ID ::= 169
id-UL-CCTrCH-InformationItem-RL-SetupRqstTDD								ProtocolIE-ID ::= 171
id-UL-CCTrCH-InformationList-RL-SetupRqstTDD								ProtocolIE-ID ::= 172
id-UL-CCTrCH-InformationListIE-PhyChReconfRqstTDD							ProtocolIE-ID ::= 173
id-UL-CCTrCH-InformationListIE-RL-AdditionRspTDD							ProtocolIE-ID ::= 174
id-UL-CCTrCH-InformationListIE-RL-ReconfReadyTDD							ProtocolIE-ID ::= 175
id-UL-CCTrCH-InformationListIE-RL-SetupRspTDD								ProtocolIE-ID ::= 176
id-UL-DPCH-Information-RL-ReconfPrepFDD										ProtocolIE-ID ::= 177
id-UL-DPCH-Information-RL-ReconfRqstFDD										ProtocolIE-ID ::= 178
id-UL-DPCH-Information-RL-SetupRqstFDD										ProtocolIE-ID ::= 179
id-UL-DPCH-InformationItem-PhyChReconfRqstTDD								ProtocolIE-ID ::= 180
id-UL-DPCH-InformationItem-RL-AdditionRspTDD								ProtocolIE-ID ::= 181
id-UL-DPCH-InformationItem-RL-SetupRspTDD									ProtocolIE-ID ::= 182
id-UL-DPCH-InformationAddListIE-RL-ReconfReadyTDD							ProtocolIE-ID ::= 183
id-UL-SIRTarget																ProtocolIE-ID ::= 184
id-URA-Information															ProtocolIE-ID ::= 185
id-UnsuccessfulRL-InformationResponse-RL-AdditionFailureFDD					ProtocolIE-ID ::= 188
id-UnsuccessfulRL-InformationResponse-RL-SetupFailureFDD					ProtocolIE-ID ::= 189
id-UnsuccessfulRL-InformationResponse-RL-SetupFailureTDD					ProtocolIE-ID ::= 190
id-Active-Pattern-Sequence-Information										ProtocolIE-ID ::= 193
id-AdjustmentRatio															ProtocolIE-ID ::= 194
id-CauseLevel-RL-AdditionFailureFDD											ProtocolIE-ID ::= 197
id-CauseLevel-RL-AdditionFailureTDD											ProtocolIE-ID ::= 198
id-CauseLevel-RL-ReconfFailure												ProtocolIE-ID ::= 199
id-CauseLevel-RL-SetupFailureFDD											ProtocolIE-ID ::= 200
id-CauseLevel-RL-SetupFailureTDD											ProtocolIE-ID ::= 201
id-DL-CCTrCH-InformationDeleteItem-RL-ReconfPrepTDD							ProtocolIE-ID ::= 205
id-DL-CCTrCH-InformationModifyItem-RL-ReconfPrepTDD							ProtocolIE-ID ::= 206
id-DL-CCTrCH-InformationModifyItem-RL-ReconfRqstTDD							ProtocolIE-ID ::= 207
id-DL-CCTrCH-InformationDeleteList-RL-ReconfPrepTDD							ProtocolIE-ID ::= 208
id-DL-CCTrCH-InformationModifyList-RL-ReconfPrepTDD							ProtocolIE-ID ::= 209
id-DL-CCTrCH-InformationModifyList-RL-ReconfRqstTDD							ProtocolIE-ID ::= 210
id-DL-DPCH-InformationAddListIE-RL-ReconfReadyTDD							ProtocolIE-ID ::= 212
id-DL-DPCH-InformationDeleteListIE-RL-ReconfReadyTDD						ProtocolIE-ID ::= 213
id-DL-DPCH-InformationModifyListIE-RL-ReconfReadyTDD						ProtocolIE-ID ::= 214
id-DSCHs-to-Add-TDD															ProtocolIE-ID ::= 215
id-Unused-ProtocolIE-ID-216													ProtocolIE-ID ::= 216
id-DSCH-DeleteList-RL-ReconfPrepTDD											ProtocolIE-ID ::= 217
id-Unused-ProtocolIE-ID-218													ProtocolIE-ID ::= 218
id-Unused-ProtocolIE-ID-219													ProtocolIE-ID ::= 219
id-DSCH-InformationListIE-RL-AdditionRspTDD									ProtocolIE-ID ::= 220
id-DSCH-InformationListIEs-RL-SetupRspTDD									ProtocolIE-ID ::= 221
id-DSCH-TDD-Information														ProtocolIE-ID ::= 222
id-Unused-ProtocolIE-ID-223													ProtocolIE-ID ::= 223
id-Unused-ProtocolIE-ID-226													ProtocolIE-ID ::= 226
id-DSCH-ModifyList-RL-ReconfPrepTDD											ProtocolIE-ID ::= 227
id-Unused-ProtocolIE-ID-228													ProtocolIE-ID ::= 228
id-Unused-ProtocolIE-ID-324													ProtocolIE-ID ::= 324
id-Unused-ProtocolIE-ID-229													ProtocolIE-ID ::= 229
id-DSCHToBeAddedOrModifiedList-RL-ReconfReadyTDD							ProtocolIE-ID ::= 230
id-Unused-ProtocolIE-ID-29													ProtocolIE-ID ::= 29
id-Unused-ProtocolIE-ID-225													ProtocolIE-ID ::= 225
id-GA-Cell																	ProtocolIE-ID ::= 232
id-GA-CellAdditionalShapes													ProtocolIE-ID ::= 3
id-Unused-ProtocolIE-ID-246													ProtocolIE-ID ::= 246
id-Transmission-Gap-Pattern-Sequence-Information							ProtocolIE-ID ::= 255
id-UL-CCTrCH-DeleteInformation-RL-ReconfPrepTDD								ProtocolIE-ID ::= 256
id-UL-CCTrCH-ModifyInformation-RL-ReconfPrepTDD								ProtocolIE-ID ::= 257
id-UL-CCTrCH-InformationModifyItem-RL-ReconfRqstTDD							ProtocolIE-ID ::= 258
id-UL-CCTrCH-InformationDeleteList-RL-ReconfPrepTDD							ProtocolIE-ID ::= 259
id-UL-CCTrCH-InformationModifyList-RL-ReconfPrepTDD							ProtocolIE-ID ::= 260
id-UL-CCTrCH-InformationModifyList-RL-ReconfRqstTDD							ProtocolIE-ID ::= 261
id-UL-CCTrCH-InformationDeleteItem-RL-ReconfRqstTDD							ProtocolIE-ID ::= 262
id-UL-CCTrCH-InformationDeleteList-RL-ReconfRqstTDD							ProtocolIE-ID ::= 263
id-UL-DPCH-InformationDeleteListIE-RL-ReconfReadyTDD						ProtocolIE-ID ::= 264
id-UL-DPCH-InformationModifyListIE-RL-ReconfReadyTDD						ProtocolIE-ID ::= 265
id-UnsuccessfulRL-InformationResponse-RL-AdditionFailureTDD					ProtocolIE-ID ::= 266
id-USCHs-to-Add																ProtocolIE-ID ::= 267
id-USCH-DeleteList-RL-ReconfPrepTDD											ProtocolIE-ID ::= 268
id-USCH-InformationListIE-RL-AdditionRspTDD									ProtocolIE-ID ::= 269
id-USCH-InformationListIEs-RL-SetupRspTDD									ProtocolIE-ID ::= 270
id-USCH-Information															ProtocolIE-ID ::= 271
id-USCH-ModifyList-RL-ReconfPrepTDD											ProtocolIE-ID ::= 272
id-USCHToBeAddedOrModifiedList-RL-ReconfReadyTDD							ProtocolIE-ID ::= 273
id-DL-Physical-Channel-Information-RL-SetupRqstTDD							ProtocolIE-ID ::= 274
id-UL-Physical-Channel-Information-RL-SetupRqstTDD							ProtocolIE-ID ::= 275
id-ClosedLoopMode1-SupportIndicator											ProtocolIE-ID ::= 276
id-Unused-ProtocolIE-ID-277													ProtocolIE-ID ::= 277
id-STTD-SupportIndicator													ProtocolIE-ID ::= 279
id-CFNReportingIndicator             										ProtocolIE-ID ::= 14
id-CNOriginatedPage-PagingRqst												ProtocolIE-ID ::= 23
id-InnerLoopDLPCStatus														ProtocolIE-ID ::= 24
id-PropagationDelay															ProtocolIE-ID ::= 25
id-RxTimingDeviationForTA													ProtocolIE-ID ::= 36
id-timeSlot-ISCP															ProtocolIE-ID ::= 37
id-CCTrCH-InformationItem-RL-FailureInd										ProtocolIE-ID ::= 15
id-CCTrCH-InformationItem-RL-RestoreInd										ProtocolIE-ID ::= 16
id-CommonMeasurementAccuracy												ProtocolIE-ID ::= 280
id-CommonMeasurementObjectType-CM-Rprt										ProtocolIE-ID ::= 281
id-CommonMeasurementObjectType-CM-Rqst										ProtocolIE-ID ::= 282
id-CommonMeasurementObjectType-CM-Rsp										ProtocolIE-ID ::= 283
id-CommonMeasurementType													ProtocolIE-ID ::= 284
id-CongestionCause 															ProtocolIE-ID ::= 18
id-SFN																		ProtocolIE-ID ::= 285
id-SFNReportingIndicator													ProtocolIE-ID ::= 286
id-InformationExchangeID													ProtocolIE-ID ::= 287
id-InformationExchangeObjectType-InfEx-Rprt									ProtocolIE-ID ::= 288
id-InformationExchangeObjectType-InfEx-Rqst									ProtocolIE-ID ::= 289
id-InformationExchangeObjectType-InfEx-Rsp									ProtocolIE-ID ::= 290
id-InformationReportCharacteristics											ProtocolIE-ID ::= 291
id-InformationType															ProtocolIE-ID ::= 292
id-neighbouring-LCR-TDD-CellInformation										ProtocolIE-ID ::= 58
id-DL-Timeslot-ISCP-LCR-Information-RL-SetupRqstTDD							ProtocolIE-ID ::= 65
id-RL-LCR-InformationResponse-RL-SetupRspTDD								ProtocolIE-ID ::= 66
id-UL-CCTrCH-LCR-InformationListIE-RL-SetupRspTDD							ProtocolIE-ID ::= 75
id-UL-DPCH-LCR-InformationItem-RL-SetupRspTDD								ProtocolIE-ID ::= 76
id-DL-CCTrCH-LCR-InformationListIE-RL-SetupRspTDD							ProtocolIE-ID ::= 77
id-DL-DPCH-LCR-InformationItem-RL-SetupRspTDD								ProtocolIE-ID ::= 78
id-DSCH-LCR-InformationListIEs-RL-SetupRspTDD								ProtocolIE-ID ::= 79
id-USCH-LCR-InformationListIEs-RL-SetupRspTDD								ProtocolIE-ID ::= 80
id-DL-Timeslot-ISCP-LCR-Information-RL-AdditionRqstTDD						ProtocolIE-ID ::= 81
id-RL-LCR-InformationResponse-RL-AdditionRspTDD								ProtocolIE-ID ::= 86
id-UL-CCTrCH-LCR-InformationListIE-RL-AdditionRspTDD						ProtocolIE-ID ::= 87
id-UL-DPCH-LCR-InformationItem-RL-AdditionRspTDD							ProtocolIE-ID ::= 88
id-DL-CCTrCH-LCR-InformationListIE-RL-AdditionRspTDD						ProtocolIE-ID ::= 89
id-DL-DPCH-LCR-InformationItem-RL-AdditionRspTDD							ProtocolIE-ID ::= 94
id-DSCH-LCR-InformationListIEs-RL-AdditionRspTDD							ProtocolIE-ID ::= 96
id-USCH-LCR-InformationListIEs-RL-AdditionRspTDD							ProtocolIE-ID ::= 97
id-UL-DPCH-LCR-InformationAddListIE-RL-ReconfReadyTDD						ProtocolIE-ID ::= 98
id-UL-Timeslot-LCR-InformationModifyList-RL-ReconfReadyTDD					ProtocolIE-ID ::= 100
id-DL-DPCH-LCR-InformationAddListIE-RL-ReconfReadyTDD						ProtocolIE-ID ::= 101
id-DL-Timeslot-LCR-InformationModifyList-RL-ReconfReadyTDD					ProtocolIE-ID ::= 104
id-UL-Timeslot-LCR-InformationList-PhyChReconfRqstTDD						ProtocolIE-ID ::= 105
id-DL-Timeslot-LCR-InformationList-PhyChReconfRqstTDD						ProtocolIE-ID ::= 106
id-timeSlot-ISCP-LCR-List-DL-PC-Rqst-TDD									ProtocolIE-ID ::= 138
id-TSTD-Support-Indicator-RL-SetupRqstTDD									ProtocolIE-ID ::= 139
id-RestrictionStateIndicator												ProtocolIE-ID ::= 142
id-Load-Value																ProtocolIE-ID ::= 233
id-Load-Value-IncrDecrThres													ProtocolIE-ID ::= 234
id-OnModification															ProtocolIE-ID ::= 235
id-Received-Total-Wideband-Power-Value										ProtocolIE-ID ::= 236
id-Received-Total-Wideband-Power-Value-IncrDecrThres						ProtocolIE-ID ::= 237
id-SFNSFNMeasurementThresholdInformation									ProtocolIE-ID ::= 238
id-Transmitted-Carrier-Power-Value											ProtocolIE-ID ::= 239
id-Transmitted-Carrier-Power-Value-IncrDecrThres							ProtocolIE-ID ::= 240
id-TUTRANGPSMeasurementThresholdInformation									ProtocolIE-ID ::= 241
id-UL-Timeslot-ISCP-Value													ProtocolIE-ID ::= 242
id-UL-Timeslot-ISCP-Value-IncrDecrThres										ProtocolIE-ID ::= 243
id-Rx-Timing-Deviation-Value-LCR											ProtocolIE-ID ::= 293
id-DPC-Mode-Change-SupportIndicator											ProtocolIE-ID ::= 19
id-Unused-ProtocolIE-ID-247													ProtocolIE-ID ::= 247
id-Unused-ProtocolIE-ID-295													ProtocolIE-ID ::= 295
id-PrimaryCCPCH-RSCP-RL-ReconfPrepTDD										ProtocolIE-ID ::= 202
id-DL-TimeSlot-ISCP-Info-RL-ReconfPrepTDD									ProtocolIE-ID ::= 203
id-DL-Timeslot-ISCP-LCR-Information-RL-ReconfPrepTDD						ProtocolIE-ID ::= 204
id-DSCH-RNTI																ProtocolIE-ID ::= 249
id-DL-PowerBalancing-Information											ProtocolIE-ID ::= 296
id-DL-PowerBalancing-ActivationIndicator									ProtocolIE-ID ::= 297
id-DL-PowerBalancing-UpdatedIndicator										ProtocolIE-ID ::= 298
id-DL-ReferencePowerInformation												ProtocolIE-ID ::= 299
id-Enhanced-PrimaryCPICH-EcNo												ProtocolIE-ID ::= 224
id-IPDL-TDD-ParametersLCR													ProtocolIE-ID ::= 252
id-CellCapabilityContainer-FDD												ProtocolIE-ID ::= 300
id-CellCapabilityContainer-TDD												ProtocolIE-ID ::= 301
id-CellCapabilityContainer-TDD-LCR											ProtocolIE-ID ::= 302
id-RL-Specific-DCH-Info														ProtocolIE-ID ::= 317
id-RL-ReconfigurationRequestFDD-RL-InformationList 							ProtocolIE-ID ::= 318
id-RL-ReconfigurationRequestFDD-RL-Information-IEs							ProtocolIE-ID ::= 319
id-RL-ReconfigurationRequestTDD-RL-Information								ProtocolIE-ID ::= 321
id-CommonTransportChannelResourcesInitialisationNotRequired					ProtocolIE-ID ::= 250
id-DelayedActivation 														ProtocolIE-ID ::= 312
id-DelayedActivationList-RL-ActivationCmdFDD								ProtocolIE-ID ::= 313
id-DelayedActivationInformation-RL-ActivationCmdFDD							ProtocolIE-ID ::= 314
id-DelayedActivationList-RL-ActivationCmdTDD								ProtocolIE-ID ::= 315
id-DelayedActivationInformation-RL-ActivationCmdTDD							ProtocolIE-ID ::= 316
id-neighbouringTDDCellMeasurementInformationLCR								ProtocolIE-ID ::= 251
id-UL-SIR-Target-CCTrCH-InformationItem-RL-SetupRspTDD						ProtocolIE-ID ::= 150
id-UL-SIR-Target-CCTrCH-LCR-InformationItem-RL-SetupRspTDD					ProtocolIE-ID ::= 151
id-PrimCCPCH-RSCP-DL-PC-RqstTDD												ProtocolIE-ID ::= 451
id-HSDSCH-FDD-Information													ProtocolIE-ID ::= 452
id-HSDSCH-FDD-Information-Response											ProtocolIE-ID ::= 453
id-HSDSCH-FDD-Update-Information											ProtocolIE-ID ::= 466
id-HSDSCH-Information-to-Modify												ProtocolIE-ID ::= 456
id-HSDSCHMacdFlowSpecificInformationList-RL-PreemptRequiredInd				ProtocolIE-ID ::= 516
id-HSDSCHMacdFlowSpecificInformationItem-RL-PreemptRequiredInd				ProtocolIE-ID ::= 517
id-HSDSCH-RNTI																ProtocolIE-ID ::= 457
id-HSDSCH-TDD-Information													ProtocolIE-ID ::= 458
id-HSDSCH-TDD-Information-Response											ProtocolIE-ID ::= 459
id-HSDSCH-TDD-Update-Information											ProtocolIE-ID ::= 467
id-HSPDSCH-RL-ID															ProtocolIE-ID ::= 463
id-HSDSCH-MACdFlows-to-Add 													ProtocolIE-ID ::= 531
id-HSDSCH-MACdFlows-to-Delete												ProtocolIE-ID ::= 532
id-Angle-Of-Arrival-Value-LCR												ProtocolIE-ID ::= 148
id-TrafficClass																ProtocolIE-ID ::= 158
id-Unused-ProtocolIE-ID-248													ProtocolIE-ID ::= 248
id-Unused-ProtocolIE-ID-253													ProtocolIE-ID ::= 253
id-PDSCH-RL-ID																ProtocolIE-ID ::= 323
id-TimeSlot-RL-SetupRspTDD													ProtocolIE-ID ::= 325
id-GERAN-Cell-Capability													ProtocolIE-ID ::= 468
id-GERAN-Classmark															ProtocolIE-ID ::= 469
id-DSCH-InitialWindowSize													ProtocolIE-ID ::= 480
id-UL-Synchronisation-Parameters-LCR										ProtocolIE-ID ::= 464
id-SNA-Information															ProtocolIE-ID ::= 479
id-MAChs-ResetIndicator														ProtocolIE-ID ::= 465
id-TDD-DL-DPCH-TimeSlotFormatModifyItem-LCR-RL-ReconfReadyTDD				ProtocolIE-ID ::= 481
id-TDD-UL-DPCH-TimeSlotFormatModifyItem-LCR-RL-ReconfReadyTDD				ProtocolIE-ID ::= 482
id-TDD-TPC-UplinkStepSize-LCR-RL-SetupRqstTDD								ProtocolIE-ID ::= 483
id-UL-CCTrCH-InformationList-RL-AdditionRqstTDD								ProtocolIE-ID ::= 484
id-UL-CCTrCH-InformationItem-RL-AdditionRqstTDD								ProtocolIE-ID ::= 485
id-DL-CCTrCH-InformationList-RL-AdditionRqstTDD								ProtocolIE-ID ::= 486
id-DL-CCTrCH-InformationItem-RL-AdditionRqstTDD								ProtocolIE-ID ::= 487
id-TDD-TPC-UplinkStepSize-InformationAdd-LCR-RL-ReconfPrepTDD				ProtocolIE-ID ::= 488
id-TDD-TPC-UplinkStepSize-InformationModify-LCR-RL-ReconfPrepTDD			ProtocolIE-ID ::= 489
id-TDD-TPC-DownlinkStepSize-InformationAdd-RL-ReconfPrepTDD					ProtocolIE-ID ::= 490
id-TDD-TPC-DownlinkStepSize-InformationModify-RL-ReconfPrepTDD				ProtocolIE-ID ::= 491
id-UL-TimingAdvanceCtrl-LCR													ProtocolIE-ID ::= 492
id-HSPDSCH-Timeslot-InformationList-PhyChReconfRqstTDD						ProtocolIE-ID ::= 493
id-HSPDSCH-Timeslot-InformationListLCR-PhyChReconfRqstTDD					ProtocolIE-ID ::= 494
id-HS-SICH-Reception-Quality 												ProtocolIE-ID ::= 495
id-HS-SICH-Reception-Quality-Measurement-Value 								ProtocolIE-ID ::= 496
id-HSSICH-Info-DM-Rprt														ProtocolIE-ID ::= 497
id-HSSICH-Info-DM-Rqst														ProtocolIE-ID ::= 498
id-HSSICH-Info-DM															ProtocolIE-ID ::= 499
id-CCTrCH-Maximum-DL-Power-RL-SetupRspTDD									ProtocolIE-ID ::= 500
id-CCTrCH-Minimum-DL-Power-RL-SetupRspTDD	ProtocolIE-ID ::= 501
id-CCTrCH-Maximum-DL-Power-RL-AdditionRspTDD								ProtocolIE-ID ::= 502
id-CCTrCH-Minimum-DL-Power-RL-AdditionRspTDD	ProtocolIE-ID ::= 503
id-CCTrCH-Maximum-DL-Power-RL-ReconfReadyTDD								ProtocolIE-ID ::= 504
id-CCTrCH-Minimum-DL-Power-RL-ReconfReadyTDD								ProtocolIE-ID ::= 505
id-Maximum-DL-Power-TimeslotLCR-InformationModifyItem-RL-ReconfReadyTDD		ProtocolIE-ID ::= 506
id-Minimum-DL-Power-TimeslotLCR-InformationModifyItem-RL-ReconfReadyTDD		ProtocolIE-ID ::= 507
id-DL-CCTrCH-InformationList-RL-ReconfRspTDD								ProtocolIE-ID ::= 508
id-DL-DPCH-InformationModifyItem-LCR-RL-ReconfRspTDD						ProtocolIE-ID ::= 509
id-Maximum-DL-Power-TimeslotLCR-InformationItem								ProtocolIE-ID ::= 510
id-Minimum-DL-Power-TimeslotLCR-InformationItem								ProtocolIE-ID ::= 511
id-TDD-Support-8PSK															ProtocolIE-ID ::= 512
id-TDD-maxNrDLPhysicalchannels												ProtocolIE-ID ::= 513
id-ExtendedGSMCellIndividualOffset											ProtocolIE-ID ::= 514
id-RL-ParameterUpdateIndicationFDD-RL-InformationList 						ProtocolIE-ID ::= 518
id-Primary-CPICH-Usage-For-Channel-Estimation								ProtocolIE-ID ::= 519
id-Secondary-CPICH-Information												ProtocolIE-ID ::= 520
id-Secondary-CPICH-Information-Change										ProtocolIE-ID ::= 521
id-Unused-ProtocolIE-ID-522													ProtocolIE-ID ::= 522
id-Unused-ProtocolIE-ID-523													ProtocolIE-ID ::= 523
id-RL-ParameterUpdateIndicationFDD-RL-Information-Item						ProtocolIE-ID ::= 524
id-Phase-Reference-Update-Indicator											ProtocolIE-ID ::= 525
id-Unidirectional-DCH-Indicator												ProtocolIE-ID ::= 526
id-RL-Information-RL-ReconfPrepTDD											ProtocolIE-ID ::= 527
id-Multiple-RL-InformationResponse-RL-ReconfReadyTDD						ProtocolIE-ID ::= 528
id-RL-ReconfigurationResponseTDD-RL-Information								ProtocolIE-ID ::= 529
id-Satellite-Almanac-Information-ExtItem									ProtocolIE-ID ::= 530
id-HSDSCH-Information-to-Modify-Unsynchronised								ProtocolIE-ID ::= 533
id-TnlQos																	ProtocolIE-ID ::= 534
id-RTLoadValue																ProtocolIE-ID ::= 535
id-NRTLoadInformationValue													ProtocolIE-ID ::= 536
id-CellPortionID															ProtocolIE-ID ::= 537
id-UpPTSInterferenceValue													ProtocolIE-ID ::= 538
id-PrimaryCCPCH-RSCP-Delta													ProtocolIE-ID ::= 539
id-UEMeasurementType														ProtocolIE-ID ::= 540
id-UEMeasurementTimeslotInfoHCR												ProtocolIE-ID ::= 541
id-UEMeasurementTimeslotInfoLCR												ProtocolIE-ID ::= 542
id-UEMeasurementReportCharacteristics										ProtocolIE-ID ::= 543
id-UEMeasurementParameterModAllow											ProtocolIE-ID ::= 544
id-UEMeasurementValueInformation											ProtocolIE-ID ::= 545
id-InterfacesToTraceItem													ProtocolIE-ID ::= 546
id-ListOfInterfacesToTrace													ProtocolIE-ID ::= 547
id-TraceDepth																ProtocolIE-ID ::= 548
id-TraceRecordingSessionReference											ProtocolIE-ID ::= 549
id-TraceReference															ProtocolIE-ID ::= 550
id-UEIdentity																ProtocolIE-ID ::= 551
id-NACC-Related-Data														ProtocolIE-ID ::= 552
id-GSM-Cell-InfEx-Rqst														ProtocolIE-ID ::= 553
id-MeasurementRecoveryBehavior												ProtocolIE-ID ::= 554
id-MeasurementRecoveryReportingIndicator									ProtocolIE-ID ::= 555
id-MeasurementRecoverySupportIndicator										ProtocolIE-ID ::= 556
id-DL-DPCH-Power-Information-RL-ReconfPrepFDD								ProtocolIE-ID ::= 557
id-F-DPCH-Information-RL-ReconfPrepFDD										ProtocolIE-ID ::= 558
id-F-DPCH-Information-RL-SetupRqstFDD										ProtocolIE-ID ::= 559
id-MBMS-Bearer-Service-List													ProtocolIE-ID ::= 560
id-MBMS-Bearer-Service-List-InfEx-Rsp										ProtocolIE-ID ::= 561
id-Active-MBMS-Bearer-ServiceFDD											ProtocolIE-ID ::= 562
id-Active-MBMS-Bearer-ServiceTDD											ProtocolIE-ID ::= 563
id-Old-URA-ID																ProtocolIE-ID ::= 564
id-UE-State																	ProtocolIE-ID ::= 568
id-URA-ID																	ProtocolIE-ID ::= 569
id-HARQ-Preamble-Mode														ProtocolIE-ID ::= 571
id-SynchronisationIndicator													ProtocolIE-ID ::= 572
id-UL-DPDCHIndicatorEDCH													ProtocolIE-ID ::= 573
id-EDPCH-Information														ProtocolIE-ID ::= 574
id-RL-Specific-EDCH-Information												ProtocolIE-ID ::= 575
id-EDCH-RL-Indication														ProtocolIE-ID ::= 576
id-EDCH-FDD-Information														ProtocolIE-ID ::= 577
id-EDCH-RLSet-Id															ProtocolIE-ID ::= 578
id-Serving-EDCHRL-Id														ProtocolIE-ID ::= 579
id-EDCH-FDD-DL-ControlChannelInformation									ProtocolIE-ID ::= 580
id-EDCH-FDD-InformationResponse												ProtocolIE-ID ::= 581
id-EDCH-MACdFlows-To-Add													ProtocolIE-ID ::= 582
id-EDCH-FDD-Information-To-Modify											ProtocolIE-ID ::= 583
id-EDCH-MACdFlows-To-Delete													ProtocolIE-ID ::= 584
id-EDPCH-Information-RLReconfRequest-FDD									ProtocolIE-ID ::= 585
id-EDCH-MacdFlowSpecificInformationList-RL-PreemptRequiredInd				ProtocolIE-ID ::= 586
id-EDCH-MacdFlowSpecificInformationItem-RL-PreemptRequiredInd				ProtocolIE-ID ::= 587
id-EDCH-MacdFlowSpecificInformationList-RL-CongestInd  						ProtocolIE-ID ::= 588
id-EDCH-MacdFlowSpecificInformationItem-RL-CongestInd						ProtocolIE-ID ::= 589
id-MBMS-Bearer-Service-Full-Address											ProtocolIE-ID ::= 590
id-Initial-DL-DPCH-TimingAdjustment											ProtocolIE-ID ::= 591
id-Initial-DL-DPCH-TimingAdjustment-Allowed									ProtocolIE-ID ::= 592
id-User-Plane-Congestion-Fields-Inclusion									ProtocolIE-ID ::= 593
id-HARQ-Preamble-Mode-Activation-Indicator									ProtocolIE-ID ::= 594
id-multiple-DedicatedMeasurementValueList-TDD-DM-Rsp						ProtocolIE-ID ::= 595
id-multiple-DedicatedMeasurementValueList-LCR-TDD-DM-Rsp					ProtocolIE-ID ::= 596
id-ProvidedInformation														ProtocolIE-ID ::= 597
id-Active-MBMS-Bearer-ServiceFDD-PFL										ProtocolIE-ID ::= 598
id-Active-MBMS-Bearer-ServiceTDD-PFL										ProtocolIE-ID ::= 599
id-FrequencyBandIndicator													ProtocolIE-ID ::= 600
id-Serving-cell-change-CFN													ProtocolIE-ID ::= 601
id-HS-DSCH-serving-cell-change-information									ProtocolIE-ID ::= 602
id-HS-DSCH-serving-cell-change-informationResponse							ProtocolIE-ID ::= 603
id-E-DCH-Serving-cell-change-informationResponse							ProtocolIE-ID ::= 604
id-secondary-LCR-CCPCH-Info-TDD												ProtocolIE-ID ::= 605
id-E-DCH-FDD-Update-Information												ProtocolIE-ID ::= 606
id-Inter-Frequency-Cell-List												ProtocolIE-ID ::= 607
id-Inter-Frequency-Cell-Information											ProtocolIE-ID ::= 608
id-multiple-HSSICHMeasurementValueList-TDD-DM-Rsp							ProtocolIE-ID ::= 609
id-TDD-Support-PLCCH														ProtocolIE-ID ::= 610
id-PLCCH-Information-UL-TimeslotLCR-Info									ProtocolIE-ID ::= 611
id-PLCCH-Information-PhyChReconfRqstTDD 									ProtocolIE-ID ::= 612
id-TDD768-maxNrDLPhysicalchannelsTS											ProtocolIE-ID ::= 613
id-RL-InformationResponse-RL-AdditionRspTDD768								ProtocolIE-ID ::= 614
id-UL-CCTrCH-InformationListIE-RL-AdditionRspTDD768							ProtocolIE-ID ::= 615
id-DL-CCTrCH-InformationListIE-RL-AdditionRspTDD768							ProtocolIE-ID ::= 616
id-UL-DPCH-InformationItem-RL-AdditionRspTDD768								ProtocolIE-ID ::= 617
id-DL-DPCH-InformationItem-RL-AdditionRspTDD768								ProtocolIE-ID ::= 618
id-UL-DPCH-InformationAddListIE-RL-ReconfReadyTDD768						ProtocolIE-ID ::= 619
id-UL-Timeslot-InformationModifyList-RL-ReconfReadyTDD768					ProtocolIE-ID ::= 620
id-DL-DPCH-InformationAddListIE-RL-ReconfReadyTDD768						ProtocolIE-ID ::= 621
id-DL-Timeslot-InformationModifyList-RL-ReconfReadyTDD768					ProtocolIE-ID ::= 622
id-secondary-CCPCH-Info-RL-ReconfReadyTDD768								ProtocolIE-ID ::= 623
id-hSSCCH-TDD-Specific-InfoList-Response768 								ProtocolIE-ID ::= 624
id-hSPDSCH-TDD-Specific-InfoList-Response768 								ProtocolIE-ID ::= 625
id-HSPDSCH-Timeslot-InformationList-PhyChReconfRqstTDD768					ProtocolIE-ID ::= 626
id-UL-Timeslot-InformationList-PhyChReconfRqstTDD768						ProtocolIE-ID ::= 627
id-DL-Timeslot-InformationList-PhyChReconfRqstTDD768						ProtocolIE-ID ::= 628
id-CellCapabilityContainer-TDD768											ProtocolIE-ID ::= 629
id-multiple-DedicatedMeasurementValueList-TDD768-DM-Rsp						ProtocolIE-ID ::= 630
id-neighbouringTDDCellMeasurementInformation768								ProtocolIE-ID ::= 631
id-UEMeasurementTimeslotInfo768												ProtocolIE-ID ::= 632
id-Rx-Timing-Deviation-Value-768											ProtocolIE-ID ::= 633
id-UEMeasurementValueTransmittedPowerList768								ProtocolIE-ID ::= 634
id-UEMeasurementValueTimeslotISCPList768									ProtocolIE-ID ::= 635
id-RL-InformationResponse-RL-SetupRspTDD768									ProtocolIE-ID ::= 636
id-UL-CCTrCH-InformationListIE-RL-SetupRspTDD768							ProtocolIE-ID ::= 637
id-DL-CCTrCH-InformationListIE-RL-SetupRspTDD768							ProtocolIE-ID ::= 638
id-UL-DPCH-InformationItem-RL-SetupRspTDD768								ProtocolIE-ID ::= 639
id-DL-DPCH-InformationItem-RL-SetupRspTDD768								ProtocolIE-ID ::= 640
id-TDD768-minimumSpreadingFactor-UL											ProtocolIE-ID ::= 641
id-TDD768-minimumSpreadingFactor-DL											ProtocolIE-ID ::= 642
id-TDD768-maxNrDLPhysicalchannels											ProtocolIE-ID ::= 643
id-DL-DPCH-InformationDeleteList768-RL-ReconfReadyTDD						ProtocolIE-ID ::= 644
id-DPCH-ID768-DM-Rsp														ProtocolIE-ID ::= 645
id-DPCH-ID768-DM-Rqst														ProtocolIE-ID ::= 646
id-DPCH-ID768-DM-Rprt														ProtocolIE-ID ::= 647
id-EDPCH-Information-RLAdditionReq-FDD										ProtocolIE-ID ::= 648
id-HSDSCH-Configured-Indicator												ProtocolIE-ID ::= 649
id-RxTimingDeviationForTAext												ProtocolIE-ID ::= 650
id-RxTimingDeviationForTA768												ProtocolIE-ID ::= 651
id-Rx-Timing-Deviation-Value-ext											ProtocolIE-ID ::= 652
id-E-DCH-PowerOffset-for-SchedulingInfo										ProtocolIE-ID ::= 653
id-TrCH-SrcStatisticsDescr													ProtocolIE-ID ::= 654
id-E-DCH-Information														ProtocolIE-ID ::= 655
id-E-DCH-Serving-RL-ID														ProtocolIE-ID ::= 656
id-E-DCH-Information-Reconfig												ProtocolIE-ID ::= 657
id-E-DCH-Information-Response												ProtocolIE-ID ::= 658
id-E-DCH-768-Information													ProtocolIE-ID ::= 659
id-E-DCH-768-Information-Reconfig											ProtocolIE-ID ::= 660
id-E-DCH-768-Information-Response											ProtocolIE-ID ::= 661
id-ExtendedPropagationDelay													ProtocolIE-ID ::= 662
id-Extended-Round-Trip-Time-Value											ProtocolIE-ID ::= 663
id-AlternativeFormatReportingIndicator										ProtocolIE-ID ::= 664
id-DCH-Indicator-For-E-DCH-HSDPA-Operation									ProtocolIE-ID ::= 665
id-E-RGCH-E-HICH-ChannelisationCodeValidityIndicator						ProtocolIE-ID ::= 666
id-E-DCH-Minimum-Set-E-TFCIValidityIndicator								ProtocolIE-ID ::= 667
id-Fast-Reconfiguration-Mode												ProtocolIE-ID ::= 668
id-Fast-Reconfiguration-Permission											ProtocolIE-ID ::= 669
id-Continuous-Packet-Connectivity-DTX-DRX-Information						ProtocolIE-ID ::= 670
id-Continuous-Packet-Connectivity-HS-SCCH-Less-Information					ProtocolIE-ID ::= 671
id-Continuous-Packet-Connectivity-HS-SCCH-Less-Information-Response			ProtocolIE-ID ::= 672
id-CPC-Information															ProtocolIE-ID ::= 673
id-MIMO-InformationResponse													ProtocolIE-ID ::= 675
id-E-DCH-LCR-Information													ProtocolIE-ID ::= 677
id-E-DCH-LCR-Information-Reconfig											ProtocolIE-ID ::= 678
id-E-DCH-LCR-Information-Response											ProtocolIE-ID ::= 679
id-HS-PDSCH-Code-Change-Grant												ProtocolIE-ID ::= 680
id-HS-PDSCH-Code-Change-Indicator											ProtocolIE-ID ::= 681
id-Extended-SRNC-ID															ProtocolIE-ID ::= 682
id-Extended-RNC-ID															ProtocolIE-ID ::= 683
id-SixtyfourQAM-DL-SupportIndicator											ProtocolIE-ID ::= 684
id-Enhanced-FACH-Support-Indicator											ProtocolIE-ID ::= 685
id-Enhanced-FACH-Information-ResponseFDD									ProtocolIE-ID ::= 686
id-HSDSCH-MACdPDUSizeFormat													ProtocolIE-ID ::= 690
id-MaximumMACdPDU-SizeExtended												ProtocolIE-ID ::= 691
id-F-DPCH-SlotFormat														ProtocolIE-ID ::= 692
id-F-DPCH-SlotFormatSupportRequest											ProtocolIE-ID ::= 693
id-eDCH-MACdFlow-Retransmission-Timer-LCR									ProtocolIE-ID ::= 694
id-Max-UE-DTX-Cycle															ProtocolIE-ID ::= 695
id-GANSS-Common-Data														ProtocolIE-ID ::= 699
id-GANSS-Information														ProtocolIE-ID ::= 700
id-GANSS-Generic-Data														ProtocolIE-ID ::= 701
id-TUTRANGANSSMeasurementThresholdInformation								ProtocolIE-ID ::= 702
id-TUTRANGANSSMeasurementValueInformation									ProtocolIE-ID ::= 703
id-Ext-Reference-E-TFCI-PO													ProtocolIE-ID ::= 705
id-Ext-Max-Bits-MACe-PDU-non-scheduled										ProtocolIE-ID ::= 706
id-HARQ-MemoryPartitioningInfoExtForMIMO									ProtocolIE-ID ::= 707
id-MIMO-ActivationIndicator													ProtocolIE-ID ::= 708
id-MIMO-Mode-Indicator														ProtocolIE-ID ::= 709
id-MIMO-N-M-Ratio															ProtocolIE-ID ::= 710
id-TransportBearerNotSetupIndicator											ProtocolIE-ID ::= 711
id-TransportBearerNotRequestedIndicator										ProtocolIE-ID ::= 712
id-PowerControlGAP																ProtocolIE-ID ::= 713
id-UARFCNforNt																ProtocolIE-ID ::= 714
id-LCRTDD-uplink-Physical-Channel-Capability								ProtocolIE-ID ::= 715
id-number-Of-Supported-Carriers												ProtocolIE-ID ::= 716
id-HSSICH-SIRTarget																ProtocolIE-ID ::= 717
id-HSSICH-TPC-StepSize														ProtocolIE-ID ::= 718
id-tSN-Length																ProtocolIE-ID ::= 719
id-HS-SICH-ID-Extension														ProtocolIE-ID ::= 720
id-HSSICH-Info-DM-Rqst-Extension											ProtocolIE-ID ::= 721
id-multipleFreq-HSPDSCH-InformationList-ResponseTDDLCR						ProtocolIE-ID ::= 722
id-multicarrier-number														ProtocolIE-ID ::= 723
id-UPPCHPositionLCR															ProtocolIE-ID ::= 724
id-UpPCH-InformationList-LCRTDD												ProtocolIE-ID ::= 725
id-UpPCH-InformationItem-LCRTDD												ProtocolIE-ID ::= 726
id-Multiple-PLMN-List														ProtocolIE-ID ::= 727
id-UE-Capabilities-Info														ProtocolIE-ID ::= 728
id-FrameOffset																ProtocolIE-ID ::= 729
id-ChipOffset																ProtocolIE-ID ::= 730
id-Enhanced-PCH-Capability													ProtocolIE-ID ::= 731
id-SixteenQAM-UL-Operation-Indicator										ProtocolIE-ID ::= 732
id-E-TFCI-Boost-Information													ProtocolIE-ID ::= 733
id-SixtyfourQAM-UsageAllowedIndicator										ProtocolIE-ID ::= 734
id-SixtyfourQAM-DL-UsageIndicator											ProtocolIE-ID ::= 735
id-Default-Serving-Grant-in-DTX-Cycle2										ProtocolIE-ID ::= 736
id-E-DPDCH-PowerInterpolation												ProtocolIE-ID ::= 737
id-Extended-E-DCH-LCRTDD-PhysicalLayerCategory								ProtocolIE-ID ::= 738
id-Continuous-Packet-Connectivity-HS-SCCH-Less-Deactivate-Indicator			ProtocolIE-ID ::= 740
id-E-DCH-DL-Control-Channel-Change-Information								ProtocolIE-ID ::= 741
id-E-DCH-DL-Control-Channel-Grant-Information								ProtocolIE-ID ::= 742
id-MaximumNumber-Of-Retransmission-For-SchedulingInfo-LCRTDD				ProtocolIE-ID ::= 743
id-E-DCH-RetransmissionTimer-For-SchedulingInfo-LCRTDD						ProtocolIE-ID ::= 744
id-E-PUCH-PowerControlGAP													ProtocolIE-ID ::= 745
id-HSDSCH-TBSizeTableIndicator												ProtocolIE-ID ::= 746
id-DGANSS-Corrections-Req													ProtocolIE-ID ::= 748

END

-- $Id$
-- Module IN-common-datatypes (Q.1248.1:07/2001)
IN-common-datatypes {itu-t recommendation q 1248 modules(1)
  in-common-datatypes(1) version1(0)} DEFINITIONS IMPLICIT TAGS ::=
BEGIN

IMPORTS
  common-classes
    FROM IN-object-identifiers {itu-t recommendation q 1248 modules(1)
      in-object-identifiers(0) version1(0)}
  EXTENSION, COMMON-BOUNDS, SupportedExtensions
    FROM IN-common-classes common-classes;

CriticalityType ::= ENUMERATED {ignore(0), abort(1)}

Extensions{COMMON-BOUNDS:b1} ::=
  SEQUENCE SIZE (1..b1.&numOfExtensions) OF ExtensionField

ExtensionField ::= SEQUENCE {
  type         EXTENSION.&id({SupportedExtensions}),
  -- shall identify the value of an EXTENSION type
  criticality  CriticalityType DEFAULT ignore,
  value        [1]  EXTENSION.&ExtensionType({SupportedExtensions}{@type})
}

--This parameter indicates an extension of an argument data type. Its content is network operator specific
Integer4 ::= INTEGER(0..2147483647)

InvokeID ::= INTEGER(-128..127)

UnavailableNetworkResource ::= ENUMERATED {
  unavailableResources(0), componentFailure(1),
  basicCallProcessingException(2), resourceStatusFailure(3), endUserFailure(4),
  screening(5)}

-- Indicates the network resource that failed
-- Note that in IN CS4 the screening value can only be used by the SCF.
END

-- Generated by Asnp, the ASN.1 pretty-printer of France Telecom R&D

-- Network-Protocol-Profile-component.asn
--
-- Taken from ITU ASN.1 database
-- http://www.itu.int/ITU-T/asn1/database/itu-t/q/q932/1998-Amd1/Network-Protocol-Profile-component.asn
--
-- $Id$
--

-- Module Network-Protocol-Profile-component (Q.932:05/1998)
Network-Protocol-Profile-component {iso(1) standard(0)
  pss1-generic-procedures(11582) network-protocol-profile-component(8)}
DEFINITIONS ::=
BEGIN

EXPORTS NetworkProtocolProfile;

NetworkProtocolProfile ::= [18] IMPLICIT INTEGER {acse(19), dse(32)}(0..254)

END -- of Network-Protocol-Profile-component

-- Generated by Asnp, the ASN.1 pretty-printer of France Telecom R&D

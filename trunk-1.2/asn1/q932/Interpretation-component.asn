-- Interpretation-component.asn
--
-- Taken from ITU ASN.1 database
-- http://www.itu.int/ITU-T/asn1/database/itu-t/q/q932/1998-Amd1/Interpretation-component.asn
--
-- $Id$
--

-- Module Interpretation-component (Q.932:05/1998)
Interpretation-component {iso(1) standard(0) pss1-generic-procedures(11582)
  interpretation-component(3)} DEFINITIONS ::=
BEGIN

EXPORTS InterpretationComponent;

InterpretationComponent ::= [11] IMPLICIT ENUMERATED {
  discardAnyUnrecognisedInvokePdu(0), clearCallIfAnyInvokePduNotRecognised(1),
  rejectAnyUnrecognisedInvokePdu(2)
  -- this coding is implied by the absence of an 
  -- Interpretation Component.
  }

END -- component

-- Generated by Asnp, the ASN.1 pretty-printer of France Telecom R&D

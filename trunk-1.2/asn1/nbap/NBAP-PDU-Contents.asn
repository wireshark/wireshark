-- NBAP-PDU-Contents.asn
--
-- Taken from 3GPP TS 25.433 V8.3.0 (2008-12)
-- http://www.3gpp.org/ftp/Specs/archive/25_series/25.433
--
-- 9.3.3	PDU Definitions
--
-- $Id$
--

-- **************************************************************
--
-- PDU definitions for NBAP.
--
-- **************************************************************

NBAP-PDU-Contents {
itu-t (0) identified-organization (4) etsi (0) mobileDomain (0) 
umts-Access (20) modules (3) nbap (2) version1 (1) nbap-PDU-Contents (1) }

DEFINITIONS AUTOMATIC TAGS ::= 

BEGIN

-- **************************************************************
--
-- IE parameter types from other modules.
--
-- **************************************************************

IMPORTS
	Active-Pattern-Sequence-Information,
	AddorDeleteIndicator,
	AICH-Power,
	AICH-TransmissionTiming,
	AllocationRetentionPriority,
	AlternativeFormatReportingIndicator,
	AvailabilityStatus,
	BCCH-ModificationTime,
	BindingID,
	BlockingPriorityIndicator,
	BroadcastReference,
	SCTD-Indicator,
	Cause,
	CCTrCH-ID,
	Cell-ERNTI-Status-Information,
	CellParameterID,
	CellPortionID,
	CellSyncBurstCode,
	CellSyncBurstCodeShift,
	CellSyncBurstRepetitionPeriod,
	CellSyncBurstSIR,
	CellSyncBurstTiming,
	CellSyncBurstTimingThreshold,
	CFN,
	ChipOffset,
	C-ID,
	Closedlooptimingadjustmentmode,
	CommonChannelsCapacityConsumptionLaw,
	Compressed-Mode-Deactivation-Flag,
	Common-MACFlows-to-DeleteFDD,
	CommonMeasurementAccuracy,
	CommonMeasurementType,
	CommonMeasurementValue,
	CommonMeasurementValueInformation,
	CommonPhysicalChannelID,
	CommonPhysicalChannelID768,
	Common-EDCH-Capability,
	Common-EDCH-System-InformationFDD,
	Common-EDCH-System-Information-ResponseFDD,
	Common-PhysicalChannel-Status-Information,
	Common-PhysicalChannel-Status-Information768,
	Common-TransportChannel-Status-Information,
	CommonTransportChannelID,
	CommonTransportChannel-InformationResponse,
	CommunicationControlPortID,
	ConfigurationGenerationID,
	ConstantValue,
	ContinuousPacketConnectivityDTX-DRX-Capability,
	ContinuousPacketConnectivityDTX-DRX-Information,
	ContinuousPacketConnectivityHS-SCCH-less-Capability,
	ContinuousPacketConnectivityHS-SCCH-less-Information,
	ContinuousPacketConnectivityHS-SCCH-less-Information-Response,
	CPC-Information,
	CriticalityDiagnostics,
	CRNC-CommunicationContextID,
	CSBMeasurementID,
	CSBTransmissionID,
	DCH-FDD-Information,
	DCH-Indicator-For-E-DCH-HSDPA-Operation,
	DCH-InformationResponse,
	DCH-ID,
	FDD-DCHs-to-Modify,
	TDD-DCHs-to-Modify,
	DCH-TDD-Information,
	DedicatedChannelsCapacityConsumptionLaw,
	DedicatedMeasurementType,
	DedicatedMeasurementValue,
	DedicatedMeasurementValueInformation,
	DelayedActivation,
	DelayedActivationUpdate,
	DiversityControlField,
	DiversityMode,
	DL-DPCH-SlotFormat,
	DL-DPCH-TimingAdjustment,
	DL-or-Global-CapacityCredit,
	DL-Power,
	DL-PowerBalancing-Information,
	DL-PowerBalancing-ActivationIndicator,
	DLPowerAveragingWindowSize,
	DL-PowerBalancing-UpdatedIndicator,
	DL-ScramblingCode,
	DL-TimeslotISCP,
	DL-Timeslot-Information,
	DL-TimeslotLCR-Information,
	DL-TimeslotISCPInfo,
	DL-TimeslotISCPInfoLCR,
	DL-TPC-Pattern01Count,
	DPC-Mode,
	DPCH-ID,
	DPCH-ID768,
	DSCH-ID,
	DSCH-InformationResponse,
	DSCH-TDD-Information,
	DwPCH-Power,
	E-AGCH-FDD-Code-Information,
	E-AI-Capability,
	E-DCH-Capability,
	E-DCHCapacityConsumptionLaw,
	E-DCH-TTI2ms-Capability,
	E-DCH-SF-Capability,
	E-DCH-HARQ-Combining-Capability,
	E-DCH-FDD-DL-Control-Channel-Information,
	E-DCH-FDD-Information,
	E-DCH-FDD-Information-Response,
	E-DCH-FDD-Information-to-Modify,
	E-DCH-FDD-Update-Information,
	E-DCH-MACdFlow-ID,
	E-DCH-MACdFlows-Information,
	E-DCH-MACdFlows-to-Delete,
	E-DCH-MACdPDU-SizeCapability,
	E-DCH-RL-Indication,
	E-DCH-Serving-Cell-Change-Info-Response,
	E-DPCCH-PO,
	E-RGCH-E-HICH-FDD-Code-Information,
	E-RGCH-2-IndexStepThreshold,
	E-RGCH-3-IndexStepThreshold,
	End-Of-Audit-Sequence-Indicator,
	Enhanced-FACH-Capability,
	Enhanced-PCH-Capability,
	Enhanced-UE-DRX-Capability,
	Enhanced-UE-DRX-InformationFDD,
	E-TFCS-Information,
	E-TTI,
	ExtendedPropagationDelay,
	Fast-Reconfiguration-Mode,
	Fast-Reconfiguration-Permission,
	FDD-DL-ChannelisationCodeNumber,
	FDD-DL-CodeInformation,
	FDD-S-CCPCH-FrameOffset,
	FDD-S-CCPCH-Offset,
	FDD-TPC-DownlinkStepSize,
	F-DPCH-Capability,
	F-DPCH-SlotFormat,
	F-DPCH-SlotFormatCapability,
	FirstRLS-Indicator,
	FNReportingIndicator,
	FPACH-Power,
	FrameAdjustmentValue,
	FrameHandlingPriority,
	FrameOffset,
	HARQ-Info-for-E-DCH,
	HSDPA-Capability,
	HSDSCH-Common-System-InformationFDD,
	HSDSCH-Common-System-Information-ResponseFDD,
	HSDSCH-Configured-Indicator,
	HSDSCH-Paging-System-InformationFDD,
	HSDSCH-Paging-System-Information-ResponseFDD,
	HS-DSCH-Serving-Cell-Change-Info,
	HS-DSCH-Serving-Cell-Change-Info-Response,
	HSDSCH-MACdPDU-SizeCapability,
	HS-PDSCH-FDD-Code-Information,
	HS-SCCH-ID,
	HS-SCCH-FDD-Code-Information,
	HS-SICH-ID,
	IB-OC-ID,
	IB-SG-DATA,
	IB-SG-POS,
	IB-SG-REP,
	IB-Type,
	InformationExchangeID,
	InformationReportCharacteristics,
	InformationType,
	Initial-DL-DPCH-TimingAdjustment-Allowed,
	InnerLoopDLPCStatus,
	IPDL-FDD-Parameters,
	IPDL-TDD-Parameters,
	IPDL-Indicator,
	IPDL-TDD-Parameters-LCR,
	IPMulticastIndication,
	LimitedPowerIncrease,
	Local-Cell-ID,
	MaximumDL-PowerCapability,
	Maximum-Target-ReceivedTotalWideBandPower,
	MaximumTransmissionPower,
	MaxNrOfUL-DPDCHs,
	Max-Set-E-DPDCHs,
	MaxPRACH-MidambleShifts,
	Max-UE-DTX-Cycle,
	MBMS-Capability,
	MeasurementFilterCoefficient,
	MeasurementID,
	MeasurementRecoveryBehavior,
	MeasurementRecoveryReportingIndicator,
	MeasurementRecoverySupportIndicator,
	MICH-CFN,
	MICH-Mode,
	MidambleAllocationMode,
	MidambleShiftAndBurstType,
	MidambleShiftAndBurstType768,
	MidambleShiftLCR,
	MinimumDL-PowerCapability,
	MinSpreadingFactor,
	MIMO-Capability,
	MIMO-PilotConfiguration,
	MinUL-ChannelisationCodeLength,
	Modification-Period,
	MultiplexingPosition,
	NCyclesPerSFNperiod,
	NRepetitionsPerCyclePeriod,
	N-INSYNC-IND,
	N-OUTSYNC-IND,
	NeighbouringCellMeasurementInformation,
	NeighbouringFDDCellMeasurementInformation,
	NeighbouringTDDCellMeasurementInformation,
	NI-Information,
	NodeB-CommunicationContextID,
	NotificationIndicatorLength,
	NumberOfReportedCellPortions,
	NSubCyclesPerCyclePeriod,
	PagingIndicatorLength,
	Paging-MACFlows-to-DeleteFDD,
	PayloadCRC-PresenceIndicator,
	PCCPCH-Power,
	PDSCHSet-ID,
	PDSCH-ID,
	PDSCH-ID768,
	PICH-Mode,
	PICH-Power,
	PLCCHinformation,
	PowerAdjustmentType,
	PowerOffset,
	PowerRaiseLimit,
	PRACH-Midamble,
	PreambleSignatures,
	PreambleThreshold,
	PredictedSFNSFNDeviationLimit,
	PredictedTUTRANGPSDeviationLimit,
	PrimaryCPICH-Power,
	Primary-CPICH-Usage-for-Channel-Estimation,
	PrimaryScramblingCode,
	PropagationDelay,
	SCH-TimeSlot,
	PunctureLimit,
	PUSCHSet-ID,
	PUSCH-ID,
	QE-Selector,
	RACH-SlotFormat,
	RACH-SubChannelNumbers,
	Reference-ReceivedTotalWideBandPower,
	Reference-ReceivedTotalWideBandPowerReporting,
	Reference-ReceivedTotalWideBandPowerSupportIndicator,
	Maximum-Target-ReceivedTotalWideBandPower-LCR,
	ReferenceClockAvailability,
	ReferenceSFNoffset,
	RepetitionLength,
	RepetitionPeriod,
	ReportCharacteristics,
	RequestedDataValue,
	RequestedDataValueInformation,
	ResourceOperationalState,
	RL-Set-ID,
	RL-ID,
	RL-Specific-DCH-Info,
	RL-Specific-E-DCH-Info,
	Received-total-wide-band-power-Value,
	AdjustmentPeriod,
	ScaledAdjustmentRatio,
	MaxAdjustmentStep,
	RNC-ID,
	ScramblingCodeNumber,
	Secondary-CPICH-Information-Change,
	SecondaryCCPCH-SlotFormat,
	Segment-Type,
	Serving-E-DCH-RL-ID,
	SixteenQAM-UL-Capability,
	SixtyfourQAM-DL-Capability,
	SixtyfourQAM-DL-MIMO-Combined-Capability,
	SFN,
	SFNSFNChangeLimit,
	SFNSFNDriftRate,
	SFNSFNDriftRateQuality,
	SFNSFNQuality,
	ShutdownTimer,
	SIB-Originator,
	SpecialBurstScheduling,
	SignallingBearerRequestIndicator,
	Start-Of-Audit-Sequence-Indicator,
	STTD-Indicator,
	SSDT-SupportIndicator,
	E-DPCCH-Power-Boosting-Capability,
	SyncCase,
	SYNCDlCodeId,
	SyncFrameNumber,
	SynchronisationReportCharacteristics,
	SynchronisationReportType,
	Target-NonServing-EDCH-To-Total-EDCH-Power-Ratio,
	T-Cell,
	T-RLFAILURE,
	TDD-ChannelisationCode,
	TDD-ChannelisationCodeLCR,
	TDD-ChannelisationCode768,
	TDD-DL-Code-LCR-Information,
	TDD-DPCHOffset,
	TDD-TPC-DownlinkStepSize,
	TDD-PhysicalChannelOffset,
	TDD-UL-Code-LCR-Information,
	TFCI-Coding,
	TFCI-Presence,
	TFCI-SignallingMode,
	TFCS,
	TimeSlot,
	TimeSlotLCR,
	TimeSlotDirection,
	TimeSlotStatus,
	TimingAdjustmentValue,
	TimingAdvanceApplied,
	TnlQos,
	ToAWE,
	ToAWS,
	TransmissionDiversityApplied,
	TransmitDiversityIndicator,
	TransmissionGapPatternSequenceCodeInformation,
	Transmission-Gap-Pattern-Sequence-Information,
	TransportBearerRequestIndicator,
	TransportFormatSet,
	TransportLayerAddress,
	TSTD-Indicator,
	TUTRANGPS,
	TUTRANGPSChangeLimit,
	TUTRANGPSDriftRate,
	TUTRANGPSDriftRateQuality,
	TUTRANGPSQuality,
	UARFCN,
	UC-Id,
	USCH-Information,
	USCH-InformationResponse,
	UL-CapacityCredit,
	UL-DPCCH-SlotFormat,
	UL-DPDCH-Indicator-For-E-DCH-Operation,
	UL-SIR,
	UL-FP-Mode,
	UL-PhysCH-SF-Variation,
	UL-ScramblingCode,
	UL-Timeslot-Information,
	UL-TimeslotLCR-Information,
	UL-TimeSlot-ISCP-Info,
	UL-TimeSlot-ISCP-LCR-Info,
	UL-TimeslotISCP-Value,
	UL-TimeslotISCP-Value-IncrDecrThres,
	USCH-ID,
	HSDSCH-FDD-Information,
	HSDSCH-FDD-Information-Response,
	HSDSCH-Information-to-Modify,
	HSDSCH-Information-to-Modify-Unsynchronised,
	HSDSCH-MACdFlow-ID,
	HSDSCH-MACdFlows-Information,
	HSDSCH-MACdFlows-to-Delete,
	HSDSCH-RNTI,
	HSDSCH-TDD-Information,
	HSDSCH-TDD-Information-Response,
	PrimaryCCPCH-RSCP,
	HSDSCH-FDD-Update-Information,
	HSDSCH-TDD-Update-Information,
	UL-Synchronisation-Parameters-LCR,
	TDD-DL-DPCH-TimeSlotFormat-LCR,
	TDD-UL-DPCH-TimeSlotFormat-LCR,
	TDD-TPC-UplinkStepSize-LCR,
	CellSyncBurstTimingLCR,
	TimingAdjustmentValueLCR,
	PrimaryCCPCH-RSCP-Delta,
	SynchronisationIndicator,
	TDD-UL-Code-768-Information,
	UL-Timeslot768-Information,
	TDD-DL-Code-768-Information,
	DL-Timeslot768-Information,
	E-DCH-TDD-CapacityConsumptionLaw,
	E-DCH-Information,
	E-DCH-Information-Response,
	E-DCH-Information-Reconfig,
	LTGI-Presence,
	SNPL-Reporting-Type,
	E-AGCH-Id,
	E-HICH-TimeOffset,
	Maximum-Generated-ReceivedTotalWideBandPowerInOtherCells,
	E-DCH-768-Information,
	E-DCH-768-Information-Reconfig,
	RTWP-ReportingIndicator,
	RTWP-CellPortion-ReportingIndicator,
	MAChs-ResetIndicator,
	E-DCH-LCR-Information,
	E-DCH-LCR-Information-Reconfig,
	E-HICH-ID-TDD,
	E-HICH-TimeOffsetLCR,
	E-HICH-Type,
	ModulationPO-MBSFN,
	Secondary-CCPCH-SlotFormat-Extended,
	ModulationMBSFN,
	MBSFN-Only-Mode-Indicator,
	MBSFN-Only-Mode-Capability,
	UPPCHPositionLCR,
	ControlGAP,
	Extended-HS-SICH-ID,
	Extended-HS-SCCH-ID,
	TimeslotLCR-Extension,
	Extended-E-HICH-ID-TDD,
	AdditionalTimeSlotListLCR,
	AdditionalMeasurementValueList,
	HS-SCCH-ID-LCR,
	Paging-MACFlows-to-DeleteLCR,
	HSDSCH-Paging-System-InformationLCR,
	HSDSCH-Paging-System-Information-ResponseLCR,
	HSDSCH-Common-System-InformationLCR,
	HSDSCH-Common-System-Information-ResponseLCR,
	Enhanced-UE-DRX-InformationLCR,
	E-DCH-MACdFlow-ID-LCR,
	Common-EDCH-System-InformationLCR,
	Common-EDCH-System-Information-ResponseLCR,
	Common-MACFlows-to-DeleteLCR,
	DL-HS-PDSCH-Timeslot-Information-LCR-PSCH-ReconfRqst,
	E-DCH-MACdFlows-to-DeleteLCR,
	HSDSCH-PreconfigurationSetup,
	HSDSCH-PreconfigurationInfo,
	NoOfTargetCellHS-SCCH-Order,
	EnhancedHSServingCC-Abort,
	GANSS-Time-ID,
	HS-DSCH-FDD-Secondary-Serving-Update-Information,
	HS-DSCH-Secondary-Serving-Remove,
	HS-DSCH-FDD-Secondary-Serving-Information-To-Modify-Unsynchronised,
	HS-DSCH-Secondary-Serving-Information-To-Modify,
	HS-DSCH-Secondary-Serving-Cell-Change-Information-Response,
	HS-DSCH-FDD-Secondary-Serving-Information-Response,
	HS-DSCH-FDD-Secondary-Serving-Information,
	Multi-Cell-Capability-Info,
	MinimumReducedE-DPDCH-GainFactor,
	IMB-Parameters,
	E-RNTI

FROM NBAP-IEs

	PrivateIE-Container{},
	ProtocolExtensionContainer{},
	ProtocolIE-Container{},
	ProtocolIE-Single-Container{},
	ProtocolIE-ContainerList{},
	NBAP-PRIVATE-IES,
	NBAP-PROTOCOL-IES,
	NBAP-PROTOCOL-EXTENSION
FROM NBAP-Containers

	id-Active-Pattern-Sequence-Information,
	id-Additional-S-CCPCH-Parameters-CTCH-ReconfRqstTDD,
	id-Additional-S-CCPCH-Parameters-CTCH-SetupRqstTDD,
	id-Additional-S-CCPCH-LCR-Parameters-CTCH-ReconfRqstTDD,
	id-Additional-S-CCPCH-LCR-Parameters-CTCH-SetupRqstTDD,
	id-AdjustmentRatio,
	id-AICH-Information,
	id-AICH-ParametersListIE-CTCH-ReconfRqstFDD,
	id-AlternativeFormatReportingIndicator,
	id-BCH-Information,
	id-BCCH-ModificationTime,
	id-bindingID,
	id-BlockingPriorityIndicator,
	id-BroadcastReference,
	id-Cause,
	id-CauseLevel-PSCH-ReconfFailure,
	id-CauseLevel-RL-AdditionFailureFDD,
	id-CauseLevel-RL-AdditionFailureTDD,
	id-CauseLevel-RL-ReconfFailure,
	id-CauseLevel-RL-SetupFailureFDD,
	id-CauseLevel-RL-SetupFailureTDD,
	id-CauseLevel-SyncAdjustmntFailureTDD,
	id-CCP-InformationItem-AuditRsp,
	id-CCP-InformationList-AuditRsp,
	id-CCP-InformationItem-ResourceStatusInd,
	id-CCTrCH-InformationItem-RL-FailureInd,
	id-CCTrCH-InformationItem-RL-RestoreInd,
	id-CCTrCH-Initial-DL-Power-RL-AdditionRqstTDD,
	id-CCTrCH-Initial-DL-Power-RL-ReconfPrepTDD,
	id-CCTrCH-Initial-DL-Power-RL-SetupRqstTDD,
	id-CellAdjustmentInfo-SyncAdjustmntRqstTDD,
	id-CellAdjustmentInfoItem-SyncAdjustmentRqstTDD,
	id-Cell-ERNTI-Status-Information,
	id-Cell-InformationItem-AuditRsp,
	id-Cell-InformationItem-ResourceStatusInd,
	id-Cell-InformationList-AuditRsp,
	id-CellParameterID,
	id-CellPortion-InformationItem-Cell-SetupRqstFDD,
	id-CellPortion-InformationList-Cell-SetupRqstFDD,
	id-CellPortion-InformationItem-Cell-ReconfRqstFDD,
	id-CellPortion-InformationList-Cell-ReconfRqstFDD,
	id-CellSyncBurstTransInit-CellSyncInitiationRqstTDD,
	id-CellSyncBurstMeasureInit-CellSyncInitiationRqstTDD,
	id-cellSyncBurstRepetitionPeriod,
	id-CellSyncBurstTransReconfiguration-CellSyncReconfRqstTDD,
	id-CellSyncBurstTransReconfInfo-CellSyncReconfRqstTDD,
	id-CellSyncBurstMeasReconfiguration-CellSyncReconfRqstTDD,
	id-CellSyncBurstMeasInfoList-CellSyncReconfRqstTDD,
	id-CellSyncBurstInfoList-CellSyncReconfRqstTDD,
	id-CellSyncInfo-CellSyncReprtTDD,
	id-CFN,
	id-CFNReportingIndicator,
	id-C-ID,
	id-Closed-Loop-Timing-Adjustment-Mode,
	id-Common-EDCH-Capability,
	id-Common-EDCH-MACdFlows-to-DeleteFDD,
	id-Common-EDCH-System-InformationFDD,
	id-Common-EDCH-System-Information-ResponseFDD,
	id-Common-MACFlows-to-DeleteFDD,
	id-CommonMeasurementAccuracy,
	id-CommonMeasurementObjectType-CM-Rprt,
	id-CommonMeasurementObjectType-CM-Rqst,
	id-CommonMeasurementObjectType-CM-Rsp,
	id-CommonMeasurementType,
	id-CommonPhysicalChannelID,
	id-CommonPhysicalChannelType-CTCH-ReconfRqstFDD,
	id-CommonPhysicalChannelType-CTCH-SetupRqstFDD,
	id-CommonPhysicalChannelType-CTCH-SetupRqstTDD,
	id-Common-UL-MACFlows-to-DeleteFDD,
	id-CommunicationContextInfoItem-Reset,
	id-CommunicationControlPortID,
	id-CommunicationControlPortInfoItem-Reset,
	id-Compressed-Mode-Deactivation-Flag,
	id-ConfigurationGenerationID,
	id-ContinuousPacketConnectivityDTX-DRX-Capability,
	id-ContinuousPacketConnectivityDTX-DRX-Information,
	id-ContinuousPacketConnectivityHS-SCCH-less-Capability,
	id-ContinuousPacketConnectivityHS-SCCH-less-Information,
	id-ContinuousPacketConnectivityHS-SCCH-less-Information-Response,
	id-CPC-Information,
	id-CRNC-CommunicationContextID,
	id-CriticalityDiagnostics,
	id-CSBTransmissionID,
	id-CSBMeasurementID,
	id-DCHs-to-Add-FDD,
	id-DCHs-to-Add-TDD,
	id-DCH-AddList-RL-ReconfPrepTDD,
	id-DCH-DeleteList-RL-ReconfPrepFDD,
	id-DCH-DeleteList-RL-ReconfPrepTDD,
	id-DCH-DeleteList-RL-ReconfRqstFDD,
	id-DCH-DeleteList-RL-ReconfRqstTDD,
	id-DCH-FDD-Information,
	id-DCH-TDD-Information,
	id-DCH-Indicator-For-E-DCH-HSDPA-Operation,
	id-DCH-InformationResponse,
	id-DCH-RearrangeList-Bearer-RearrangeInd,
	id-DSCH-RearrangeList-Bearer-RearrangeInd,
	id-FDD-DCHs-to-Modify,
	id-FDD-S-CCPCH-FrameOffset-CTCH-SetupRqstFDD,
	id-TDD-DCHs-to-Modify,
	id-DedicatedMeasurementObjectType-DM-Rprt,
	id-DedicatedMeasurementObjectType-DM-Rqst,
	id-DedicatedMeasurementObjectType-DM-Rsp,
	id-DedicatedMeasurementType,
	id-DelayedActivation,
	id-DelayedActivationList-RL-ActivationCmdFDD,
	id-DelayedActivationList-RL-ActivationCmdTDD,
	id-DelayedActivationInformation-RL-ActivationCmdFDD,
	id-DelayedActivationInformation-RL-ActivationCmdTDD,
	id-DL-CCTrCH-InformationAddList-RL-ReconfPrepTDD,
	id-DL-CCTrCH-InformationDeleteItem-RL-ReconfRqstTDD,
	id-DL-CCTrCH-InformationDeleteList-RL-ReconfPrepTDD,
	id-DL-CCTrCH-InformationDeleteList-RL-ReconfRqstTDD,
	id-DL-CCTrCH-InformationItem-RL-SetupRqstTDD,
	id-DL-CCTrCH-InformationList-RL-AdditionRqstTDD,
	id-DL-CCTrCH-InformationList-RL-SetupRqstTDD,
	id-DL-CCTrCH-InformationModifyItem-RL-ReconfRqstTDD,
	id-DL-CCTrCH-InformationModifyList-RL-ReconfPrepTDD,
	id-DL-CCTrCH-InformationModifyList-RL-ReconfRqstTDD,
	id-DL-DPCH-InformationAddListIE-RL-ReconfPrepTDD,
	id-DL-DPCH-InformationItem-RL-AdditionRqstTDD,
	id-DL-DPCH-InformationList-RL-SetupRqstTDD,
	id-DL-DPCH-InformationModify-AddListIE-RL-ReconfPrepTDD,
	id-DL-DPCH-InformationModify-DeleteListIE-RL-ReconfPrepTDD,
	id-DL-DPCH-InformationModify-ModifyListIE-RL-ReconfPrepTDD,
	id-DL-DPCH-Information-RL-ReconfPrepFDD,
	id-DL-DPCH-Information-RL-ReconfRqstFDD,
	id-DL-DPCH-Information-RL-SetupRqstFDD,
	id-DL-DPCH-TimingAdjustment,
	id-DL-DPCH-Power-Information-RL-ReconfPrepFDD,
	id-DL-PowerBalancing-Information,
	id-DL-PowerBalancing-ActivationIndicator,
	id-DL-ReferencePowerInformationItem-DL-PC-Rqst,
	id-DL-PowerBalancing-UpdatedIndicator,
	id-DLReferencePower,
	id-DLReferencePowerList-DL-PC-Rqst,
	id-DL-TPC-Pattern01Count,
	id-DPC-Mode,
	id-DPCHConstant,
	id-DSCHs-to-Add-TDD,
	id-DSCH-Information-DeleteList-RL-ReconfPrepTDD,
	id-DSCH-Information-ModifyList-RL-ReconfPrepTDD,
	id-DSCH-InformationResponse,
	id-DSCH-TDD-Information,
	id-E-AGCH-And-E-RGCH-E-HICH-FDD-Scrambling-Code,
	id-E-AI-Capability,
	id-E-AGCH-FDD-Code-Information,
	id-E-DCH-Capability,
	id-E-DCH-TTI2ms-Capability,
	id-E-DCH-SF-Capability,
	id-E-DCH-HARQ-Combining-Capability,
	id-E-DCH-FDD-DL-Control-Channel-Information,
	id-E-DCH-FDD-Information,
	id-E-DCH-FDD-Information-Response,
	id-E-DCH-FDD-Information-to-Modify,
	id-E-DCH-FDD-Update-Information,
	id-E-DCH-MACdFlows-to-Add,
	id-E-DCH-MACdFlows-to-Delete,
	id-E-DCH-RearrangeList-Bearer-RearrangeInd,
	id-E-DCH-Resources-Information-AuditRsp,
	id-E-DCH-Resources-Information-ResourceStatusInd,
	id-E-DCH-RL-Indication,
	id-E-DCH-RL-Set-ID,
	id-E-DCH-Serving-Cell-Change-Info-Response,
	id-E-DCH-CapacityConsumptionLaw,
	id-E-DPCH-Information-RL-ReconfPrepFDD,
	id-E-DPCH-Information-RL-ReconfRqstFDD,
	id-E-DPCH-Information-RL-SetupRqstFDD,
	id-E-DPCH-Information-RL-AdditionReqFDD,
	id-E-RGCH-E-HICH-FDD-Code-Information,
	id-ERACH-CM-Rqst,
	id-ERACH-CM-Rsp,
	id-ERACH-CM-Rprt,
	id-End-Of-Audit-Sequence-Indicator,
	id-Enhanced-FACH-Capability,
	id-Enhanced-PCH-Capability,
	id-Enhanced-UE-DRX-Capability,
	id-Enhanced-UE-DRX-InformationFDD,
	id-ExtendedPropagationDelay,
	id-FACH-Information,
	id-FACH-ParametersList-CTCH-ReconfRqstTDD,
	id-FACH-ParametersList-CTCH-SetupRsp,
	id-FACH-ParametersListIE-CTCH-ReconfRqstFDD,
	id-FACH-ParametersListIE-CTCH-SetupRqstFDD,
	id-FACH-ParametersListIE-CTCH-SetupRqstTDD,
	id-Fast-Reconfiguration-Mode,
	id-Fast-Reconfiguration-Permission,
	id-F-DPCH-Capability,
	id-F-DPCH-Information-RL-ReconfPrepFDD,
	id-F-DPCH-Information-RL-SetupRqstFDD,
	id-F-DPCH-SlotFormat,
	id-F-DPCH-SlotFormatCapability,
	id-HSDPA-And-EDCH-CellPortion-Information-PSCH-ReconfRqst,
	id-HSDSCH-Configured-Indicator,
	id-HS-DSCH-Serving-Cell-Change-Info,
	id-HS-DSCH-Serving-Cell-Change-Info-Response,
	id-IndicationType-ResourceStatusInd,
	id-InformationExchangeID,
	id-InformationExchangeObjectType-InfEx-Rqst,
	id-InformationExchangeObjectType-InfEx-Rsp,
	id-InformationExchangeObjectType-InfEx-Rprt,
	id-InformationReportCharacteristics,	
	id-InformationType,
	id-InitDL-Power,
	id-Initial-DL-DPCH-TimingAdjustment,
	id-Initial-DL-DPCH-TimingAdjustment-Allowed,
	id-InnerLoopDLPCStatus,
	id-IntStdPhCellSyncInfoItem-CellSyncReprtTDD,
	id-IPDLParameter-Information-Cell-ReconfRqstFDD,
	id-IPDLParameter-Information-Cell-SetupRqstFDD,
	id-IPDLParameter-Information-Cell-ReconfRqstTDD,
	id-IPDLParameter-Information-Cell-SetupRqstTDD,
	id-IPMulticastIndication,
	id-LateEntranceCellSyncInfoItem-CellSyncReprtTDD,
	id-Limited-power-increase-information-Cell-SetupRqstFDD,
	id-Local-Cell-ID,
	id-Local-Cell-Group-InformationItem-AuditRsp,
	id-Local-Cell-Group-InformationItem-ResourceStatusInd,
	id-Local-Cell-Group-InformationItem2-ResourceStatusInd,
	id-Local-Cell-Group-InformationList-AuditRsp,
	id-Local-Cell-InformationItem-AuditRsp,
	id-Local-Cell-InformationItem-ResourceStatusInd,
	id-Local-Cell-InformationItem2-ResourceStatusInd,
	id-Local-Cell-InformationList-AuditRsp,
	id-AdjustmentPeriod,
	id-MaxAdjustmentStep,
	id-MaximumTransmissionPower,
	id-Max-UE-DTX-Cycle,
	id-MeasurementFilterCoefficient,
	id-MeasurementID,
	id-MeasurementRecoveryBehavior,
	id-MeasurementRecoveryReportingIndicator,
	id-MeasurementRecoverySupportIndicator,
	id-MIB-SB-SIB-InformationList-SystemInfoUpdateRqst,
	id-MBMS-Capability,
	id-MICH-CFN,
	id-MICH-Information-AuditRsp,
	id-MICH-Information-ResourceStatusInd,
	id-MICH-Parameters-CTCH-ReconfRqstFDD,
	id-MICH-Parameters-CTCH-ReconfRqstTDD,
	id-MICH-Parameters-CTCH-SetupRqstFDD,
	id-MICH-Parameters-CTCH-SetupRqstTDD,
	id-MIMO-Capability,
	id-MIMO-PilotConfiguration,
	id-Modification-Period,
	id-multipleRL-dl-DPCH-InformationList,
	id-multipleRL-dl-DPCH-InformationModifyList,
	id-multipleRL-dl-CCTrCH-InformationModifyList-RL-ReconfRqstTDD,
	id-multiple-RL-Information-RL-ReconfPrepTDD,
	id-multiple-RL-Information-RL-ReconfRqstTDD,
	id-multipleRL-ul-DPCH-InformationList,
	id-multipleRL-ul-DPCH-InformationModifyList,
	id-NCyclesPerSFNperiod,
	id-NeighbouringCellMeasurementInformation,
	id-NI-Information-NotifUpdateCmd,
	id-NodeB-CommunicationContextID,
	id-NRepetitionsPerCyclePeriod,
	id-NumberOfReportedCellPortions,
	id-Paging-MACFlows-to-DeleteFDD,
	id-P-CCPCH-Information,
	id-P-CPICH-Information,
	id-P-SCH-Information,
	id-PCCPCH-Information-Cell-ReconfRqstTDD,
	id-PCCPCH-Information-Cell-SetupRqstTDD,
	id-PCH-Parameters-CTCH-ReconfRqstTDD,
	id-PCH-Parameters-CTCH-SetupRsp,
	id-PCH-ParametersItem-CTCH-ReconfRqstFDD,
	id-PCH-ParametersItem-CTCH-SetupRqstFDD,
	id-PCH-ParametersItem-CTCH-SetupRqstTDD,
	id-PCH-Information,
	id-PICH-ParametersItem-CTCH-ReconfRqstFDD,
	id-PDSCH-Information-AddListIE-PSCH-ReconfRqst,
	id-PDSCH-Information-ModifyListIE-PSCH-ReconfRqst,
	id-PDSCH-RL-ID,
	id-PDSCH-Timeslot-Format-PSCH-ReconfRqst-LCR,
	id-PDSCHSets-AddList-PSCH-ReconfRqst,
	id-PDSCHSets-DeleteList-PSCH-ReconfRqst,
	id-PDSCHSets-ModifyList-PSCH-ReconfRqst,
	id-PICH-Information,
	id-PICH-Parameters-CTCH-ReconfRqstTDD,
	id-PICH-ParametersItem-CTCH-SetupRqstTDD,
	id-PLCCH-Information-AuditRsp,
	id-PLCCH-Information-ResourceStatusInd,
	id-PLCCH-Information-RL-ReconfPrepTDDLCR,
	id-PLCCH-InformationList-AuditRsp,
	id-PLCCH-InformationList-ResourceStatusInd,
	id-PLCCH-Parameters-CTCH-ReconfRqstTDD,
	id-PowerAdjustmentType,
	id-Power-Local-Cell-Group-choice-CM-Rqst,
	id-Power-Local-Cell-Group-choice-CM-Rsp,
	id-Power-Local-Cell-Group-choice-CM-Rprt,
	id-Power-Local-Cell-Group-InformationItem-AuditRsp,
	id-Power-Local-Cell-Group-InformationItem-ResourceStatusInd,
	id-Power-Local-Cell-Group-InformationItem2-ResourceStatusInd,
	id-Power-Local-Cell-Group-InformationList-AuditRsp,
	id-Power-Local-Cell-Group-InformationList-ResourceStatusInd,
	id-Power-Local-Cell-Group-InformationList2-ResourceStatusInd,
	id-Power-Local-Cell-Group-ID,
	id-PRACH-Information,
	id-PRACHConstant,
	id-PRACH-ParametersItem-CTCH-SetupRqstTDD,
	id-PRACH-ParametersListIE-CTCH-ReconfRqstFDD,
	id-PrimaryCCPCH-Information-Cell-ReconfRqstFDD,
	id-PrimaryCCPCH-Information-Cell-SetupRqstFDD,
	id-PrimaryCPICH-Information-Cell-ReconfRqstFDD,
	id-PrimaryCPICH-Information-Cell-SetupRqstFDD,
	id-Primary-CPICH-Usage-for-Channel-Estimation,
	id-PrimarySCH-Information-Cell-ReconfRqstFDD,
	id-PrimarySCH-Information-Cell-SetupRqstFDD,
	id-PrimaryScramblingCode,
	id-SCH-Information-Cell-ReconfRqstTDD,
	id-SCH-Information-Cell-SetupRqstTDD,
	id-PUSCH-Information-AddListIE-PSCH-ReconfRqst,
	id-PUSCH-Information-ModifyListIE-PSCH-ReconfRqst,
	id-PUSCH-Timeslot-Format-PSCH-ReconfRqst-LCR,
	id-PUSCHConstant,
	id-PUSCHSets-AddList-PSCH-ReconfRqst,
	id-PUSCHSets-DeleteList-PSCH-ReconfRqst,
	id-PUSCHSets-ModifyList-PSCH-ReconfRqst,
	id-RACH-Information,
	id-RACH-Parameters-CTCH-SetupRsp,
	id-RACH-ParametersItem-CTCH-SetupRqstFDD,
	id-RACH-ParameterItem-CTCH-SetupRqstTDD,
	id-ReferenceClockAvailability,
	id-ReferenceSFNoffset,
	id-ReportCharacteristics,
	id-Reporting-Object-RL-FailureInd,
	id-Reporting-Object-RL-RestoreInd,
	id-ResetIndicator,
	id-RL-ID,
	id-RL-InformationItem-DM-Rprt,
	id-RL-InformationItem-DM-Rqst,
	id-RL-InformationItem-DM-Rsp,
	id-RL-InformationItem-RL-AdditionRqstFDD,
	id-RL-informationItem-RL-DeletionRqst,
	id-RL-InformationItem-RL-FailureInd,
	id-RL-InformationItem-RL-PreemptRequiredInd,
	id-RL-InformationItem-RL-ReconfPrepFDD,
	id-RL-InformationItem-RL-ReconfRqstFDD,
	id-RL-InformationItem-RL-RestoreInd,
	id-RL-InformationItem-RL-SetupRqstFDD,
	id-RL-InformationList-RL-AdditionRqstFDD,
	id-RL-informationList-RL-DeletionRqst,
	id-RL-InformationList-RL-PreemptRequiredInd,
	id-RL-InformationList-RL-ReconfPrepFDD,
	id-RL-InformationList-RL-ReconfRqstFDD,
	id-RL-InformationList-RL-SetupRqstFDD,
	id-RL-InformationResponseItem-RL-AdditionRspFDD,
	id-RL-InformationResponseItem-RL-ReconfReady,
	id-RL-InformationResponseItem-RL-ReconfRsp,
	id-RL-InformationResponseItem-RL-SetupRspFDD,
	id-RL-InformationResponseList-RL-AdditionRspFDD,
	id-RL-InformationResponseList-RL-ReconfReady,
	id-RL-InformationResponseList-RL-ReconfRsp,
	id-RL-InformationResponseList-RL-SetupRspFDD,
	id-RL-InformationResponse-RL-AdditionRspTDD,
	id-RL-InformationResponse-RL-SetupRspTDD,
	id-RL-Information-RL-AdditionRqstTDD,
	id-RL-Information-RL-ReconfRqstTDD,
	id-RL-Information-RL-ReconfPrepTDD,
	id-RL-Information-RL-SetupRqstTDD,
	id-RL-ReconfigurationFailureItem-RL-ReconfFailure,
	id-RL-Set-InformationItem-DM-Rprt,
	id-RL-Set-InformationItem-DM-Rsp,
	id-RL-Set-InformationItem-RL-FailureInd,
	id-RL-Set-InformationItem-RL-RestoreInd,
	id-RL-Specific-DCH-Info,
	id-RL-Specific-E-DCH-Info,
	id-S-CCPCH-Information,
	id-S-CCPCH-InformationListExt-AuditRsp,
	id-S-CCPCH-InformationListExt-ResourceStatusInd,
	id-S-CCPCH-LCR-InformationListExt-AuditRsp,
	id-S-CCPCH-LCR-InformationListExt-ResourceStatusInd,
	id-S-CPICH-Information,
	id-SCH-Information,
	id-S-SCH-Information,
	id-Secondary-CCPCHListIE-CTCH-ReconfRqstTDD,
	id-Secondary-CCPCH-parameterListIE-CTCH-SetupRqstTDD,
	id-Secondary-CCPCH-Parameters-CTCH-ReconfRqstTDD,
	id-Secondary-CPICH-Information,
	id-SecondaryCPICH-InformationItem-Cell-ReconfRqstFDD,
	id-SecondaryCPICH-InformationItem-Cell-SetupRqstFDD,
	id-SecondaryCPICH-InformationList-Cell-ReconfRqstFDD,
	id-SecondaryCPICH-InformationList-Cell-SetupRqstFDD,
	id-Secondary-CPICH-Information-Change,
	id-SecondarySCH-Information-Cell-ReconfRqstFDD,
	id-SecondarySCH-Information-Cell-SetupRqstFDD,
	id-SegmentInformationListIE-SystemInfoUpdate,
	id-Serving-Cell-Change-CFN,
	id-Serving-E-DCH-RL-ID,
	id-SixteenQAM-UL-Capability,
	id-SixtyfourQAM-DL-Capability,
	id-SixtyfourQAM-DL-MIMO-Combined-Capability,
	id-SFN,
	id-SFNReportingIndicator,
	id-ShutdownTimer,
	id-SignallingBearerRequestIndicator,
	id-Start-Of-Audit-Sequence-Indicator,
	id-Successful-RL-InformationRespItem-RL-AdditionFailureFDD,
	id-Successful-RL-InformationRespItem-RL-SetupFailureFDD,
	id-E-DPCCH-Power-Boosting-Capability,
	id-Synchronisation-Configuration-Cell-ReconfRqst,
	id-Synchronisation-Configuration-Cell-SetupRqst,
	id-SyncCase,
	id-SyncCaseIndicatorItem-Cell-SetupRqstTDD-PSCH,
	id-SyncFrameNumber,
	id-SynchronisationReportType,
	id-SynchronisationReportCharacteristics,
	id-SyncReportType-CellSyncReprtTDD,
	id-T-Cell,
	id-TargetCommunicationControlPortID,
	id-Transmission-Gap-Pattern-Sequence-Information,
	id-TimeSlotConfigurationList-Cell-ReconfRqstTDD,
	id-TimeSlotConfigurationList-Cell-SetupRqstTDD,
	id-timeslotInfo-CellSyncInitiationRqstTDD,
	id-TimeslotISCPInfo,
	id-TimingAdvanceApplied,
	id-TnlQos,
	id-TransmissionDiversityApplied,
	id-transportlayeraddress,
	id-Tstd-indicator,
	id-UARFCNforNt,
	id-UARFCNforNd,
	id-UARFCNforNu,
	id-UL-CCTrCH-InformationAddList-RL-ReconfPrepTDD,
	id-UL-CCTrCH-InformationDeleteItem-RL-ReconfRqstTDD,
	id-UL-CCTrCH-InformationDeleteList-RL-ReconfPrepTDD,
	id-UL-CCTrCH-InformationDeleteList-RL-ReconfRqstTDD,
	id-UL-CCTrCH-InformationItem-RL-SetupRqstTDD,
	id-UL-CCTrCH-InformationList-RL-AdditionRqstTDD,
	id-UL-CCTrCH-InformationList-RL-SetupRqstTDD,
	id-UL-CCTrCH-InformationModifyItem-RL-ReconfRqstTDD,
	id-UL-CCTrCH-InformationModifyList-RL-ReconfPrepTDD,
	id-UL-CCTrCH-InformationModifyList-RL-ReconfRqstTDD,
	id-UL-DPCH-InformationAddListIE-RL-ReconfPrepTDD,
	id-UL-DPCH-InformationItem-RL-AdditionRqstTDD,
	id-UL-DPCH-InformationList-RL-SetupRqstTDD,
	id-UL-DPCH-InformationModify-AddListIE-RL-ReconfPrepTDD,
	id-UL-DPCH-InformationModify-DeleteListIE-RL-ReconfPrepTDD,
	id-UL-DPCH-InformationModify-ModifyListIE-RL-ReconfPrepTDD,
	id-UL-DPCH-Information-RL-ReconfPrepFDD,
	id-UL-DPCH-Information-RL-ReconfRqstFDD,
	id-UL-DPCH-Information-RL-SetupRqstFDD,
	id-UL-DPDCH-Indicator-For-E-DCH-Operation,
	id-Unsuccessful-cell-InformationRespItem-SyncAdjustmntFailureTDD,
	id-Unsuccessful-PDSCHSetItem-PSCH-ReconfFailureTDD,
	id-Unsuccessful-PUSCHSetItem-PSCH-ReconfFailureTDD,
	id-Unsuccessful-RL-InformationRespItem-RL-AdditionFailureFDD,
	id-Unsuccessful-RL-InformationRespItem-RL-SetupFailureFDD,
	id-Unsuccessful-RL-InformationResp-RL-AdditionFailureTDD,
	id-Unsuccessful-RL-InformationResp-RL-SetupFailureTDD,
	id-USCH-Information-Add,
	id-USCH-Information-DeleteList-RL-ReconfPrepTDD,
	id-USCH-Information-ModifyList-RL-ReconfPrepTDD,
	id-USCH-InformationResponse,
	id-USCH-Information,
	id-USCH-RearrangeList-Bearer-RearrangeInd,
	id-DL-DPCH-LCR-Information-RL-SetupRqstTDD,
	id-DwPCH-LCR-Information	,
	id-DwPCH-LCR-InformationList-AuditRsp,
	id-DwPCH-LCR-Information-Cell-SetupRqstTDD,
	id-DwPCH-LCR-Information-Cell-ReconfRqstTDD,
	id-DwPCH-LCR-Information-ResourceStatusInd,
	id-maxFACH-Power-LCR-CTCH-SetupRqstTDD,
	id-maxFACH-Power-LCR-CTCH-ReconfRqstTDD,
	id-FPACH-LCR-Information,
	id-FPACH-LCR-Information-AuditRsp,
	id-FPACH-LCR-InformationList-AuditRsp,
	id-FPACH-LCR-InformationList-ResourceStatusInd,
	id-FPACH-LCR-Parameters-CTCH-SetupRqstTDD, 
	id-FPACH-LCR-Parameters-CTCH-ReconfRqstTDD,
	id-PCCPCH-LCR-Information-Cell-SetupRqstTDD,
	id-PCH-Power-LCR-CTCH-SetupRqstTDD,
	id-PCH-Power-LCR-CTCH-ReconfRqstTDD,
	id-PICH-LCR-Parameters-CTCH-SetupRqstTDD,
	id-PRACH-LCR-ParametersList-CTCH-SetupRqstTDD, 
	id-RL-InformationResponse-LCR-RL-SetupRspTDD	,
	id-Secondary-CCPCH-LCR-parameterList-CTCH-SetupRqstTDD,
	id-TimeSlot,
	id-TimeSlotConfigurationList-LCR-Cell-ReconfRqstTDD,
	id-TimeSlotConfigurationList-LCR-Cell-SetupRqstTDD,
	id-TimeslotISCP-LCR-InfoList-RL-SetupRqstTDD,
	id-TimeSlotLCR-CM-Rqst,
	id-UL-DPCH-LCR-Information-RL-SetupRqstTDD,
	id-DL-DPCH-InformationItem-LCR-RL-AdditionRqstTDD,
	id-UL-DPCH-InformationItem-LCR-RL-AdditionRqstTDD,
	id-TimeslotISCP-InformationList-LCR-RL-AdditionRqstTDD,
	id-DL-DPCH-LCR-InformationAddList-RL-ReconfPrepTDD,
	id-DL-DPCH-LCR-InformationModify-AddList-RL-ReconfPrepTDD,
	id-DL-Timeslot-LCR-InformationModify-ModifyList-RL-ReconfPrepTDD,
	id-TimeslotISCPInfoList-LCR-DL-PC-RqstTDD,
	id-UL-DPCH-LCR-InformationAddListIE-RL-ReconfPrepTDD,
	id-UL-DPCH-LCR-InformationModify-AddList,
	id-UL-TimeslotLCR-Information-RL-ReconfPrepTDD,
	id-UL-SIRTarget,
	id-PDSCH-AddInformation-LCR-PSCH-ReconfRqst,
	id-PDSCH-AddInformation-LCR-AddListIE-PSCH-ReconfRqst,
	id-PDSCH-ModifyInformation-LCR-PSCH-ReconfRqst,
	id-PDSCH-ModifyInformation-LCR-ModifyListIE-PSCH-ReconfRqst,
	id-PUSCH-AddInformation-LCR-PSCH-ReconfRqst,
	id-PUSCH-AddInformation-LCR-AddListIE-PSCH-ReconfRqst,
	id-PUSCH-ModifyInformation-LCR-PSCH-ReconfRqst,
	id-PUSCH-ModifyInformation-LCR-ModifyListIE-PSCH-ReconfRqst,
	id-PUSCH-Info-DM-Rqst,
	id-PUSCH-Info-DM-Rsp,
	id-PUSCH-Info-DM-Rprt,
	id-RL-InformationResponse-LCR-RL-AdditionRspTDD,
	id-IPDLParameter-Information-LCR-Cell-SetupRqstTDD,
	id-IPDLParameter-Information-LCR-Cell-ReconfRqstTDD,
	id-HS-PDSCH-HS-SCCH-E-AGCH-E-RGCH-E-HICH-MaxPower-PSCH-ReconfRqst,
	id-HS-PDSCH-HS-SCCH-ScramblingCode-PSCH-ReconfRqst,
	id-HS-PDSCH-FDD-Code-Information-PSCH-ReconfRqst,
	id-HS-SCCH-FDD-Code-Information-PSCH-ReconfRqst,
	id-HS-PDSCH-TDD-Information-PSCH-ReconfRqst,
	id-Add-To-HS-SCCH-Resource-Pool-PSCH-ReconfRqst,
	id-Modify-HS-SCCH-Resource-Pool-PSCH-ReconfRqst,
	id-Delete-From-HS-SCCH-Resource-Pool-PSCH-ReconfRqst,
	id-SYNCDlCodeId-TransInitLCR-CellSyncInitiationRqstTDD,
	id-SYNCDlCodeId-MeasureInitLCR-CellSyncInitiationRqstTDD,
	id-SYNCDlCodeIdTransReconfInfoLCR-CellSyncReconfRqstTDD,
	id-SYNCDlCodeIdMeasReconfigurationLCR-CellSyncReconfRqstTDD,
	id-SYNCDlCodeIdMeasInfoList-CellSyncReconfRqstTDD,
	id-SyncDLCodeIdsMeasInfoList-CellSyncReprtTDD,
	id-NSubCyclesPerCyclePeriod-CellSyncReconfRqstTDD,
	id-DwPCH-Power,
	id-AccumulatedClockupdate-CellSyncReprtTDD,
	id-HSDPA-Capability,
	id-HSDSCH-FDD-Information,
	id-HSDSCH-Common-System-InformationFDD,
	id-HSDSCH-Common-System-Information-ResponseFDD,
	id-HSDSCH-FDD-Information-Response,
	id-HSDSCH-Information-to-Modify,
	id-HSDSCH-Information-to-Modify-Unsynchronised,
	id-HSDSCH-MACdFlows-to-Add,
	id-HSDSCH-MACdFlows-to-Delete,
	id-HSDSCH-Paging-System-InformationFDD,
	id-HSDSCH-Paging-System-Information-ResponseFDD,
	id-HSDSCH-RearrangeList-Bearer-RearrangeInd,
	id-HSDSCH-Resources-Information-AuditRsp,
	id-HSDSCH-Resources-Information-ResourceStatusInd,
	id-HSDSCH-RNTI,
	id-HSDSCH-TDD-Information,
	id-HSDSCH-TDD-Information-Response,
	id-HSPDSCH-RL-ID,
	id-HSSICH-Info-DM-Rprt,
	id-HSSICH-Info-DM-Rqst,
	id-HSSICH-Info-DM-Rsp,
	id-PrimCCPCH-RSCP-DL-PC-RqstTDD,
	id-HSDSCH-FDD-Update-Information,
	id-HSDSCH-TDD-Update-Information,
	id-UL-Synchronisation-Parameters-LCR,
	id-DL-DPCH-TimeSlotFormat-LCR-ModifyItem-RL-ReconfPrepTDD,
	id-UL-DPCH-TimeSlotFormat-LCR-ModifyItem-RL-ReconfPrepTDD,
	id-CCTrCH-Maximum-DL-Power-RL-SetupRqstTDD,
	id-CCTrCH-Minimum-DL-Power-RL-SetupRqstTDD,
	id-CCTrCH-Maximum-DL-Power-RL-AdditionRqstTDD,
	id-CCTrCH-Minimum-DL-Power-RL-AdditionRqstTDD,
	id-CCTrCH-Maximum-DL-Power-InformationAdd-RL-ReconfPrepTDD,
	id-CCTrCH-Minimum-DL-Power-InformationAdd-RL-ReconfPrepTDD, 
	id-CCTrCH-Maximum-DL-Power-InformationModify-RL-ReconfPrepTDD,
	id-CCTrCH-Minimum-DL-Power-InformationModify-RL-ReconfPrepTDD,
	id-Maximum-DL-Power-Modify-LCR-InformationModify-RL-ReconfPrepTDD,
	id-Minimum-DL-Power-Modify-LCR-InformationModify-RL-ReconfPrepTDD,
	id-DL-DPCH-LCR-InformationModify-ModifyList-RL-ReconfRqstTDD,
	id-CCTrCH-Maximum-DL-Power-InformationModify-RL-ReconfRqstTDD,
	id-CCTrCH-Minimum-DL-Power-InformationModify-RL-ReconfRqstTDD,
	id-TDD-TPC-UplinkStepSize-LCR-RL-SetupRqstTDD,
	id-TDD-TPC-UplinkStepSize-LCR-RL-AdditionRqstTDD,
	id-TDD-TPC-DownlinkStepSize-RL-AdditionRqstTDD,
	id-TDD-TPC-UplinkStepSize-InformationAdd-LCR-RL-ReconfPrepTDD,
	id-TDD-TPC-UplinkStepSize-InformationModify-LCR-RL-ReconfPrepTDD,
	id-TDD-TPC-DownlinkStepSize-InformationModify-RL-ReconfPrepTDD,
	id-TDD-TPC-DownlinkStepSize-InformationAdd-RL-ReconfPrepTDD,
	id-TimeslotISCP-LCR-InfoList-RL-ReconfPrepTDD,
	id-TimingAdjustmentValueLCR,
	id-PrimaryCCPCH-RSCP-Delta,
	id-Maximum-Target-ReceivedTotalWideBandPower,
	id-multiple-DedicatedMeasurementValueList-TDD-DM-Rsp,
	id-multiple-DedicatedMeasurementValueList-LCR-TDD-DM-Rsp,
	id-SynchronisationIndicator,
	id-Reference-ReceivedTotalWideBandPower,
	id-Reference-ReceivedTotalWideBandPowerReporting,
	id-Reference-ReceivedTotalWideBandPowerSupportIndicator,
	id-Maximum-Target-ReceivedTotalWideBandPower-LCR,
	id-multiple-PUSCH-InfoList-DM-Rsp,
	id-multiple-PUSCH-InfoList-DM-Rprt,
	id-Target-NonServing-EDCH-To-Total-EDCH-Power-Ratio,
	id-multiple-HSSICHMeasurementValueList-TDD-DM-Rsp,
	id-PCCPCH-768-Information-Cell-SetupRqstTDD,
	id-SCH-768-Information-Cell-SetupRqstTDD,
	id-SCH-768-Information-Cell-ReconfRqstTDD,
	id-PCCPCH-768-Information-Cell-ReconfRqstTDD,
	id-P-CCPCH-768-Information-AuditRsp,
	id-PICH-768-Information-AuditRsp,
	id-PRACH-768-InformationList-AuditRsp,
	id-SCH-768-Information-AuditRsp,
	id-MICH-768-Information-AuditRsp,
	id-CommonPhysicalChannelID768-CommonTrChDeletionReq,
	id-MICH-768-Parameters-CTCH-ReconfRqstTDD,
	id-PICH-768-Parameters-CTCH-SetupRqstTDD,
	id-PICH-768-Parameters-CTCH-ReconfRqstTDD,
	id-PRACH-768-Parameters-CTCH-SetupRqstTDD,
	id-S-CCPCH-768-InformationList-AuditRsp,
	id-S-CCPCH-768-Information-AuditRsp,
	id-S-CCPCH-768-Parameters-CTCH-SetupRqstTDD,
	id-S-CCPCH-768-Parameters-CTCH-ReconfRqstTDD,
	id-S-CCPCH-768-Information-ResourceStatusInd,
	id-P-CCPCH-768-Information-ResourceStatusInd,
	id-PICH-768-Information-ResourceStatusInd,
	id-PRACH-768-InformationList-ResourceStatusInd,
	id-SCH-768-Information-ResourceStatusInd,
	id-MICH-768-Information-ResourceStatusInd,
	id-S-CCPCH-768-InformationList-ResourceStatusInd,
	id-PRACH-768-Information,
	id-UL-DPCH-768-Information-RL-SetupRqstTDD,
	id-DL-DPCH-768-Information-RL-SetupRqstTDD,
	id-DL-DPCH-InformationItem-768-RL-AdditionRqstTDD,
	id-UL-DPCH-InformationItem-768-RL-AdditionRqstTDD,
	id-UL-DPCH-768-InformationAddItemIE-RL-ReconfPrepTDD,
	id-UL-DPCH-768-InformationAddListIE-RL-ReconfPrepTDD,
	id-UL-DPCH-768-InformationModify-AddItem,
	id-UL-DPCH-768-InformationModify-AddList,
	id-UL-Timeslot768-Information-RL-ReconfPrepTDD,
	id-DL-DPCH-768-InformationAddItem-RL-ReconfPrepTDD,
	id-DL-DPCH-768-InformationAddList-RL-ReconfPrepTDD,
	id-DL-DPCH-768-InformationModify-AddItem-RL-ReconfPrepTDD,
	id-DL-DPCH-768-InformationModify-AddList-RL-ReconfPrepTDD,
	id-DL-Timeslot-768-InformationModify-ModifyList-RL-ReconfPrepTDD,
	id-DPCH-ID768-DM-Rqst,
	id-multiple-DedicatedMeasurementValueList-768-TDD-DM-Rsp,
	id-DPCH-ID768-DM-Rsp,
	id-DPCH-ID768-DM-Rprt,
	id-PDSCH-AddInformation-768-PSCH-ReconfRqst,
	id-PDSCH-ModifyInformation-768-PSCH-ReconfRqst,
	id-PUSCH-AddInformation-768-PSCH-ReconfRqst,
	id-PUSCH-ModifyInformation-768-PSCH-ReconfRqst,
	id-dL-HS-PDSCH-Timeslot-Information-768-PSCH-ReconfRqst,
	id-hS-SCCH-Information-768-PSCH-ReconfRqst,
	id-hS-SCCH-InformationModify-768-PSCH-ReconfRqst,
	id-tFCI-Presence,
	id-E-RUCCH-InformationList-AuditRsp,
	id-E-RUCCH-InformationList-ResourceStatusInd,
	id-E-RUCCH-Information,
	id-E-DCH-Information,
	id-E-DCH-Information-Response,
	id-E-DCH-Information-Reconfig,
	id-E-PUCH-Information-PSCH-ReconfRqst,
	id-Add-To-E-AGCH-Resource-Pool-PSCH-ReconfRqst,
	id-Modify-E-AGCH-Resource-Pool-PSCH-ReconfRqst,
	id-Delete-From-E-AGCH-Resource-Pool-PSCH-ReconfRqst,
	id-E-HICH-Information-PSCH-ReconfRqst,
	id-E-DCH-TDD-CapacityConsumptionLaw,
	id-E-HICH-TimeOffset,
	id-Maximum-Generated-ReceivedTotalWideBandPowerInOtherCells,
	id-E-DCH-Serving-RL-ID,
	id-E-RUCCH-768-InformationList-AuditRsp,
	id-E-RUCCH-768-InformationList-ResourceStatusInd,
	id-E-RUCCH-768-Information,
	id-E-DCH-768-Information,
	id-E-DCH-768-Information-Reconfig,
	id-E-PUCH-Information-768-PSCH-ReconfRqst,
	id-Add-To-E-AGCH-Resource-Pool-768-PSCH-ReconfRqst,
	id-Modify-E-AGCH-Resource-Pool-768-PSCH-ReconfRqst,
	id-E-HICH-Information-768-PSCH-ReconfRqst,
	id-RTWP-ReportingIndicator,
	id-RTWP-CellPortion-ReportingIndicator,
	id-Received-Scheduled-EDCH-Power-Share-Value,
	id-Received-Scheduled-EDCH-Power-Share-For-CellPortion-Value,
	id-Received-Scheduled-EDCH-Power-Share,
	id-Received-Scheduled-EDCH-Power-Share-For-CellPortion,
	id-ueCapability-Info,
	id-MAChs-ResetIndicator,
	id-SYNC-UL-Partition-LCR,
	id-E-DCH-LCR-Information,
	id-E-DCH-LCR-Information-Reconfig,
	id-E-PUCH-Information-LCR-PSCH-ReconfRqst,
	id-Add-To-E-AGCH-Resource-Pool-LCR-PSCH-ReconfRqst,
	id-Modify-E-AGCH-Resource-Pool-LCR-PSCH-ReconfRqst,
	id-Add-To-E-HICH-Resource-Pool-LCR-PSCH-ReconfRqst,
	id-Modify-E-HICH-Resource-Pool-LCR-PSCH-ReconfRqst,
	id-Delete-From-E-HICH-Resource-Pool-PSCH-ReconfRqst,
	id-E-HICH-TimeOffsetLCR,
	id-HSDSCH-MACdPDU-SizeCapability,
	id-ModulationPO-MBSFN,
	id-Secondary-CCPCH-SlotFormat-Extended,
	id-MBSFN-Only-Mode-Indicator-Cell-SetupRqstTDD-LCR,
	id-Time-Slot-Parameter-ID,
	id-MBSFN-Only-Mode-Capability,
	id-MBSFN-Cell-ParameterID-Cell-SetupRqstTDD,
	id-MBSFN-Cell-ParameterID-Cell-ReconfRqstTDD,
	id-S-CCPCH-Modulation,
	id-TimeSlotConfigurationList-LCR-CTCH-SetupRqstTDD,
	id-Cell-Frequency-List-Information-LCR-MulFreq-AuditRsp,
	id-Cell-Frequency-List-InformationItem-LCR-MulFreq-AuditRsp, 
	id-Cell-Frequency-List-LCR-MulFreq-Cell-SetupRqstTDD,
	id-UARFCN-Adjustment,
	id-Cell-Frequency-List-Information-LCR-MulFreq-ResourceStatusInd,
	id-Cell-Frequency-List-InformationItem-LCR-MulFreq-ResourceStatusInd,
	id-UPPCHPositionLCR,
	id-UPPCH-LCR-Parameters-CTCH-ReconfRqstTDD,
	id-UPPCH-LCR-InformationList-AuditRsp,
	id-UPPCH-LCR-InformationItem-AuditRsp,
	id-UPPCH-LCR-InformationList-ResourceStatusInd,
	id-UPPCH-LCR-InformationItem-ResourceStatusInd,
	id-multipleFreq-dL-HS-PDSCH-Timeslot-Information-LCR-PSCH-ReconfRqst,
	id-multipleFreq-HS-DSCH-Resources-InformationList-AuditRsp,
	id-multipleFreq-HS-DSCH-Resources-InformationList-ResourceStatusInd,
	id-UARFCNSpecificCauseList,id-Unsuccessful-UARFCNItem-PSCH-ReconfFailureTDD,
	id-MultipleFreq-DL-HS-PDSCH-Timeslot-Information-LCRItem-PSCH-ReconfRqst,
	id-Extended-HS-SCCH-ID,
	id-Extended-HS-SICH-ID,
	id-HSSICH-InfoExt-DM-Rqst,
	id-Delete-From-HS-SCCH-Resource-PoolExt-PSCH-ReconfRqst,
	id-HS-SCCH-InformationExt-LCR-PSCH-ReconfRqst,
	id-HS-SCCH-InformationModifyExt-LCR-PSCH-ReconfRqst,
	id-PowerControlGAP,
	id-MBSFN-SpecialTimeSlot-LCR,
	id-MultipleFreq-E-DCH-Resources-InformationList-AuditRsp,
	id-MultipleFreq-E-DCH-Resources-InformationList-ResourceStatusInd,
	id-MultipleFreq-E-PUCH-Timeslot-InformationList-LCR-PSCH-ReconfRqst,
	id-MultipleFreq-E-PUCH-Timeslot-Information-LCRItem-PSCH-ReconfRqst,
	id-Extended-E-HICH-ID-TDD,
	id-E-DCH-MACdPDU-SizeCapability,
	id-E-HICH-TimeOffset-Extension,
	id-MultipleFreq-E-HICH-TimeOffsetLCR,
	id-PLCCH-parameters,
	id-E-RUCCH-parameters,
	id-E-RUCCH-768-parameters,
	id-HS-Cause,
	id-E-Cause,
	id-AdditionalTimeSlotListLCR,
	id-AdditionalMeasurementValueList,
	id-HSDSCH-Paging-System-InformationLCR,
	id-HSDSCH-Paging-System-Information-ResponseLCR,
	id-HSDSCH-Common-System-InformationLCR,
	id-HSDSCH-Common-System-Information-ResponseLCR,
	id-Paging-MACFlows-to-DeleteLCR,
	id-Enhanced-UE-DRX-CapabilityLCR,
	id-Enhanced-UE-DRX-InformationLCR,
	id-Common-EDCH-MACdFlows-to-DeleteLCR,
	id-Common-EDCH-System-InformationLCR,
	id-Common-EDCH-System-Information-ResponseLCR,
	id-Common-MACFlows-to-DeleteLCR,
	id-Common-UL-MACFlows-to-DeleteLCR,
	id-HSDSCH-PreconfigurationSetup,
	id-HSDSCH-PreconfigurationInfo,
	id-NoOfTargetCellHS-SCCH-Order,
	id-EnhancedHSServingCC-Abort,
	id-GANSS-Time-ID,
	id-Additional-HS-Cell-Information-RL-Setup,
	id-Additional-HS-Cell-Information-Response,
	id-Additional-HS-Cell-Information-RL-Addition,
	id-Additional-HS-Cell-Change-Information-Response,
	id-Additional-HS-Cell-Information-RL-Reconf-Prep,
	id-Additional-HS-Cell-Information-RL-Reconf-Req,
	id-Additional-HS-Cell-Information-RL-Param-Upd,
	id-Multi-Cell-Capability-Info,
	id-MinimumReducedE-DPDCH-GainFactor,
	id-IMB-Parameters,
	id-E-RNTI,


	maxNrOfCCTrCHs,
	maxNrOfCellSyncBursts,
	maxNrOfCodes,
	maxNrOfDCHs,
	maxNrOfDLTSs,
	maxNrOfDLTSLCRs,
	maxNrOfDPCHs,
	maxNrOfDPCHsPerRL-1,
	maxNrOfDPCHLCRs,
	maxNrOfDPCHsLCRPerRL-1,
	maxNrOfDPCHs768,
	maxNrOfDPCHs768PerRL-1,
	maxNrOfDSCHs,
	maxNrOfFACHs,
	maxNrOfRLs,
	maxNrOfRLs-1,
	maxNrOfRLs-2,
	maxNrOfRLSets,
	maxNrOfPDSCHs,
	maxNrOfPUSCHs,
	maxNrOfPUSCHs-1,
	maxNrOfPRACHLCRs,
	maxNrOfPDSCHSets,
	maxNrOfPUSCHSets,
	maxNrOfReceptsPerSyncFrame,
	maxNrOfSCCPCHs,
	maxNrOfSCCPCHsinExt,
	maxNrOfSCCPCHLCRs,
	maxNrOfSCCPCHsLCRinExt,
	maxNrOfSCCPCHs768,
	maxNrOfULTSs,
	maxNrOfULTSLCRs,
	maxNrOfUSCHs,
	maxFACHCell,
	maxFPACHCell,
	maxRACHCell,
	maxPLCCHCell,
	maxPRACHCell,
	maxSCCPCHCell,
	maxSCCPCHCell768,
	maxSCCPCHCellinExt,
	maxSCCPCHCellinExtLCR,
	maxSCPICHCell,
	maxCellinNodeB,
	maxCCPinNodeB,
	maxCommunicationContext,
	maxLocalCellinNodeB,
	maxNrOfSlotFormatsPRACH,
	maxIB,
	maxIBSEG,
	maxNrOfCellPortionsPerCell,
	maxNrOfHSSCCHs,
	maxNrOfHSSICHs,
	maxNrOfHSSICHs-1,
	maxNrOfHSPDSCHs,
	maxNrOfHSPDSCHs768,
	maxNrOfSyncFramesLCR,
	maxNrOfReceptionsperSyncFrameLCR,
	maxNrOfSyncDLCodesLCR,
	maxNrOfMACdFlows,
	maxNrOfEDCHMACdFlows,
	maxE-RUCCHCell,
	maxNrOfE-PUCHSlots,
	maxNrOfEAGCHs,
	maxNrOfEAGCHCodes,
	maxNrOfE-PUCHSlotsLCR,
	maxNrOfEPUCHcodes,
	maxNrOfEHICHs,
	maxFrequencyinCell,
	maxFrequencyinCell-1,
	maxNrOfHSSCCHsinExt,
	maxNrOfHSSCCHsLCR,
	maxNrOfEAGCHsLCR,
	maxNrOfEHICHsLCR,
	maxNrOfHSDSCH-1


FROM NBAP-Constants;

-- **************************************************************
--
-- COMMON TRANSPORT CHANNEL SETUP REQUEST FDD
--
-- **************************************************************

CommonTransportChannelSetupRequestFDD ::= SEQUENCE {
	protocolIEs				ProtocolIE-Container		{{CommonTransportChannelSetupRequestFDD-IEs}},
	protocolExtensions		ProtocolExtensionContainer	{{CommonTransportChannelSetupRequestFDD-Extensions}}     OPTIONAL,
	...
}

CommonTransportChannelSetupRequestFDD-Extensions NBAP-PROTOCOL-EXTENSION ::= {
	...
}

CommonTransportChannelSetupRequestFDD-IEs NBAP-PROTOCOL-IES ::= {
	{ ID	id-C-ID												CRITICALITY reject		TYPE	C-ID				PRESENCE mandatory	}|
	{ ID	id-ConfigurationGenerationID						CRITICALITY reject		TYPE	ConfigurationGenerationID		PRESENCE mandatory	}|
	{ ID	id-CommonPhysicalChannelType-CTCH-SetupRqstFDD		CRITICALITY ignore		TYPE	CommonPhysicalChannelType-CTCH-SetupRqstFDD		PRESENCE 	mandatory	},
	...
}

CommonPhysicalChannelType-CTCH-SetupRqstFDD ::= CHOICE {
	secondary-CCPCH-parameters		Secondary-CCPCH-CTCH-SetupRqstFDD,
	pRACH-parameters				PRACH-CTCH-SetupRqstFDD,
	notUsed-pCPCHes-parameters		NULL,
	...
}

Secondary-CCPCH-CTCH-SetupRqstFDD ::= SEQUENCE {
	commonPhysicalChannelID					CommonPhysicalChannelID,
	fdd-S-CCPCH-Offset						FDD-S-CCPCH-Offset,
	dl-ScramblingCode						DL-ScramblingCode							OPTIONAL,
	-- This IE shall be present if the PCH Parameters IE is not present
	fdd-DL-ChannelisationCodeNumber			FDD-DL-ChannelisationCodeNumber,
	tFCS									TFCS,
	secondary-CCPCH-SlotFormat				SecondaryCCPCH-SlotFormat,
	tFCI-Presence							TFCI-Presence								OPTIONAL,
	-- This IE shall be present if the Secondary CCPCH Slot Format is set to any of the values from 8 to 17 or if 3.84Mcps TDD IMB is used
	multiplexingPosition					MultiplexingPosition,
	powerOffsetInformation					PowerOffsetInformation-CTCH-SetupRqstFDD,
	sTTD-Indicator							STTD-Indicator,
	fACH-Parameters							FACH-ParametersList-CTCH-SetupRqstFDD		OPTIONAL,
	pCH-Parameters							PCH-Parameters-CTCH-SetupRqstFDD			OPTIONAL,
	iE-Extensions							ProtocolExtensionContainer  { { Secondary-CCPCHItem-CTCH-SetupRqstFDD-ExtIEs} }		OPTIONAL,
	...
}

Secondary-CCPCHItem-CTCH-SetupRqstFDD-ExtIEs NBAP-PROTOCOL-EXTENSION ::= {
	{ ID id-MICH-Parameters-CTCH-SetupRqstFDD			CRITICALITY reject	EXTENSION MICH-Parameters-CTCH-SetupRqstFDD		PRESENCE optional	}|
	{ ID id-FDD-S-CCPCH-FrameOffset-CTCH-SetupRqstFDD	CRITICALITY reject	EXTENSION FDD-S-CCPCH-FrameOffset						PRESENCE optional	}|
	{ ID id-ModulationPO-MBSFN							CRITICALITY reject	EXTENSION ModulationPO-MBSFN							PRESENCE optional	}|
	{ ID id-Secondary-CCPCH-SlotFormat-Extended			CRITICALITY reject	EXTENSION Secondary-CCPCH-SlotFormat-Extended		PRESENCE optional	}|
	{ ID id-IMB-Parameters								CRITICALITY reject	EXTENSION IMB-Parameters				PRESENCE optional	},
	...
}

PowerOffsetInformation-CTCH-SetupRqstFDD ::= SEQUENCE {
	pO1-ForTFCI-Bits						PowerOffset,
	pO3-ForPilotBits						PowerOffset,
	iE-Extensions							ProtocolExtensionContainer { { PowerOffsetInformation-CTCH-SetupRqstFDD-ExtIEs} }	OPTIONAL,
	...
}

PowerOffsetInformation-CTCH-SetupRqstFDD-ExtIEs NBAP-PROTOCOL-EXTENSION ::= {
	...
}

FACH-ParametersList-CTCH-SetupRqstFDD ::= ProtocolIE-Single-Container {{ FACH-ParametersListIEs-CTCH-SetupRqstFDD }}

FACH-ParametersListIEs-CTCH-SetupRqstFDD NBAP-PROTOCOL-IES ::= {
	{ ID id-FACH-ParametersListIE-CTCH-SetupRqstFDD   CRITICALITY reject	TYPE FACH-ParametersListIE-CTCH-SetupRqstFDD	PRESENCE mandatory }
}

FACH-ParametersListIE-CTCH-SetupRqstFDD ::= SEQUENCE (SIZE (1..maxNrOfFACHs)) OF FACH-ParametersItem-CTCH-SetupRqstFDD

FACH-ParametersItem-CTCH-SetupRqstFDD ::= SEQUENCE {
	commonTransportChannelID			CommonTransportChannelID,
	transportFormatSet					TransportFormatSet,
	toAWS								ToAWS,
	toAWE								ToAWE,
	maxFACH-Power						DL-Power,
	iE-Extensions						ProtocolExtensionContainer  { { FACH-ParametersItem-CTCH-SetupRqstFDD-ExtIEs} }		OPTIONAL,
	...
}

FACH-ParametersItem-CTCH-SetupRqstFDD-ExtIEs NBAP-PROTOCOL-EXTENSION ::= {
	{ ID	id-bindingID						CRITICALITY	ignore		EXTENSION 	BindingID			PRESENCE optional	}|
	{ ID	id-transportlayeraddress			CRITICALITY	ignore		EXTENSION 	TransportLayerAddress		PRESENCE optional	}|
	{ ID	id-TnlQos							CRITICALITY ignore		EXTENSION	TnlQos				PRESENCE optional	}|
	{ ID	id-BroadcastReference				CRITICALITY	ignore		EXTENSION	BroadcastReference						PRESENCE optional	}|
	{ ID	id-IPMulticastIndication			CRITICALITY ignore		EXTENSION	IPMulticastIndication		PRESENCE optional	},
	...
}

PCH-Parameters-CTCH-SetupRqstFDD ::= ProtocolIE-Single-Container {{ PCH-ParametersIE-CTCH-SetupRqstFDD }}

PCH-ParametersIE-CTCH-SetupRqstFDD NBAP-PROTOCOL-IES ::= {
	{ ID id-PCH-ParametersItem-CTCH-SetupRqstFDD   CRITICALITY reject	TYPE PCH-ParametersItem-CTCH-SetupRqstFDD	PRESENCE mandatory }
}

PCH-ParametersItem-CTCH-SetupRqstFDD ::= SEQUENCE {
	commonTransportChannelID			CommonTransportChannelID,
	transportFormatSet					TransportFormatSet,
	toAWS								ToAWS,
	toAWE								ToAWE,	
	pCH-Power							DL-Power,
	pICH-Parameters						PICH-Parameters-CTCH-SetupRqstFDD,
	iE-Extensions						ProtocolExtensionContainer  { { PCH-ParametersItem-CTCH-SetupRqstFDD-ExtIEs} }		OPTIONAL,
	...
}

PCH-ParametersItem-CTCH-SetupRqstFDD-ExtIEs NBAP-PROTOCOL-EXTENSION ::= {
	{ ID	id-bindingID						CRITICALITY ignore		EXTENSION 	BindingID		PRESENCE optional	}|
	{ ID	id-transportlayeraddress			CRITICALITY ignore		EXTENSION 	TransportLayerAddress	PRESENCE optional	}|
	{ ID	id-TnlQos							CRITICALITY ignore		EXTENSION	TnlQos			PRESENCE optional	},
	...
}

PICH-Parameters-CTCH-SetupRqstFDD ::= SEQUENCE {
	commonPhysicalChannelID						CommonPhysicalChannelID,
	fdd-dl-ChannelisationCodeNumber				FDD-DL-ChannelisationCodeNumber,
	pICH-Power									PICH-Power,
	pICH-Mode									PICH-Mode,	
	sTTD-Indicator								STTD-Indicator,
	iE-Extensions								ProtocolExtensionContainer { { PICH-Parameters-CTCH-SetupRqstFDD-ExtIEs} }		OPTIONAL,
	...
}

PICH-Parameters-CTCH-SetupRqstFDD-ExtIEs NBAP-PROTOCOL-EXTENSION ::= {
	...
}

MICH-Parameters-CTCH-SetupRqstFDD ::= SEQUENCE {
	commonPhysicalChannelID						CommonPhysicalChannelID,
	fdd-dl-ChannelisationCodeNumber				FDD-DL-ChannelisationCodeNumber,
	mICH-Power									PICH-Power,
	mICH-Mode									MICH-Mode,
	sTTD-Indicator								STTD-Indicator,
	iE-Extensions								ProtocolExtensionContainer { { MICH-Parameters-CTCH-SetupRqstFDD-ExtIEs} }		OPTIONAL,
	...
}

MICH-Parameters-CTCH-SetupRqstFDD-ExtIEs NBAP-PROTOCOL-EXTENSION ::= {
	...
}

PRACH-CTCH-SetupRqstFDD ::= SEQUENCE {
	commonPhysicalChannelID						CommonPhysicalChannelID,
	scramblingCodeNumber						ScramblingCodeNumber,
	tFCS										TFCS,
	preambleSignatures							PreambleSignatures,
	allowedSlotFormatInformation				AllowedSlotFormatInformationList-CTCH-SetupRqstFDD,
	rACH-SubChannelNumbers						RACH-SubChannelNumbers,
	ul-punctureLimit							PunctureLimit,
	preambleThreshold							PreambleThreshold,
	rACH-Parameters								RACH-Parameters-CTCH-SetupRqstFDD,
    aICH-Parameters                             AICH-Parameters-CTCH-SetupRqstFDD,
	iE-Extensions								ProtocolExtensionContainer { { PRACHItem-CTCH-SetupRqstFDD-ExtIEs} }		OPTIONAL,
	...
}

PRACHItem-CTCH-SetupRqstFDD-ExtIEs NBAP-PROTOCOL-EXTENSION ::= {
	...
}

AllowedSlotFormatInformationList-CTCH-SetupRqstFDD ::= SEQUENCE (SIZE (1.. maxNrOfSlotFormatsPRACH)) OF AllowedSlotFormatInformationItem-CTCH-SetupRqstFDD

AllowedSlotFormatInformationItem-CTCH-SetupRqstFDD ::= SEQUENCE {
	rACHSlotFormat								RACH-SlotFormat,
	iE-Extensions								ProtocolExtensionContainer  { { AllowedSlotFormatInformationItem-CTCH-SetupRqstFDD-ExtIEs} }		OPTIONAL,
	...
}

AllowedSlotFormatInformationItem-CTCH-SetupRqstFDD-ExtIEs NBAP-PROTOCOL-EXTENSION ::= {
	...
}

RACH-Parameters-CTCH-SetupRqstFDD ::= ProtocolIE-Single-Container {{ RACH-ParametersIE-CTCH-SetupRqstFDD }}

RACH-ParametersIE-CTCH-SetupRqstFDD NBAP-PROTOCOL-IES ::= {
	{ ID id-RACH-ParametersItem-CTCH-SetupRqstFDD   CRITICALITY reject	TYPE RACH-ParametersItem-CTCH-SetupRqstFDD	PRESENCE mandatory }
}

RACH-ParametersItem-CTCH-SetupRqstFDD ::= SEQUENCE {
 	commonTransportChannelID					CommonTransportChannelID,
 	transportFormatSet							TransportFormatSet,
	iE-Extensions								ProtocolExtensionContainer  { { RACH-ParametersItem-CTCH-SetupRqstFDD-ExtIEs} }		OPTIONAL,
	...
 }

RACH-ParametersItem-CTCH-SetupRqstFDD-ExtIEs NBAP-PROTOCOL-EXTENSION ::= {
	{ ID	id-bindingID						CRITICALITY ignore		EXTENSION 	BindingID		PRESENCE optional	}|
	{ ID	id-transportlayeraddress			CRITICALITY ignore		EXTENSION 	TransportLayerAddress	PRESENCE optional	}|
	{ ID	id-TnlQos							CRITICALITY ignore		EXTENSION	TnlQos			PRESENCE optional	},
	...
}

AICH-Parameters-CTCH-SetupRqstFDD ::= SEQUENCE {
	commonPhysicalChannelID						CommonPhysicalChannelID,
	aICH-TransmissionTiming						AICH-TransmissionTiming,
	fdd-dl-ChannelisationCodeNumber				FDD-DL-ChannelisationCodeNumber,
	aICH-Power									AICH-Power,
	sTTD-Indicator								STTD-Indicator,
	iE-Extensions								ProtocolExtensionContainer  { { AICH-Parameters-CTCH-SetupRqstFDD-ExtIEs} }		OPTIONAL,
	...
}

AICH-Parameters-CTCH-SetupRqstFDD-ExtIEs NBAP-PROTOCOL-EXTENSION ::= {
	...
}

-- **************************************************************
--
-- COMMON TRANSPORT CHANNEL SETUP REQUEST TDD
--
-- **************************************************************

CommonTransportChannelSetupRequestTDD ::= SEQUENCE {
	protocolIEs				ProtocolIE-Container		{{CommonTransportChannelSetupRequestTDD-IEs}},
	protocolExtensions 		ProtocolExtensionContainer	{{CommonTransportChannelSetupRequestTDD-Extensions}}		OPTIONAL,
	...
}

CommonTransportChannelSetupRequestTDD-IEs NBAP-PROTOCOL-IES ::= {
	{ ID	id-C-ID											CRITICALITY reject	TYPE C-ID					PRESENCE mandatory	}|
	{ ID	id-ConfigurationGenerationID					CRITICALITY reject	TYPE ConfigurationGenerationID			PRESENCE mandatory	}|
	{ ID	id-CommonPhysicalChannelType-CTCH-SetupRqstTDD	CRITICALITY ignore	TYPE CommonPhysicalChannelType-CTCH-SetupRqstTDD		PRESENCE 	mandatory	},
	...
}

CommonTransportChannelSetupRequestTDD-Extensions NBAP-PROTOCOL-EXTENSION ::= {
	...
}

CommonPhysicalChannelType-CTCH-SetupRqstTDD ::= CHOICE {
	secondary-CCPCH-parameters					Secondary-CCPCH-CTCH-SetupRqstTDD,
	pRACH-parameters							PRACH-CTCH-SetupRqstTDD,
	...,
	extension-CommonPhysicalChannelType-CTCH-SetupRqstTDD	Extension-CommonPhysicalChannelType-CTCH-SetupRqstTDD
}

Extension-CommonPhysicalChannelType-CTCH-SetupRqstTDD ::= ProtocolIE-Single-Container {{ Extension-CommonPhysicalChannelType-CTCH-SetupRqstTDDIE }}

Extension-CommonPhysicalChannelType-CTCH-SetupRqstTDDIE NBAP-PROTOCOL-IES ::= {
	{ ID id-PLCCH-parameters			CRITICALITY ignore	TYPE PLCCH-parameters		PRESENCE mandatory }|
	{ ID id-E-RUCCH-parameters		CRITICALITY ignore		TYPE E-RUCCH-parameters		PRESENCE mandatory }|
	{ ID id-E-RUCCH-768-parameters	CRITICALITY ignore		TYPE E-RUCCH-768-parameters	PRESENCE mandatory },
	...
}

Secondary-CCPCH-CTCH-SetupRqstTDD ::= SEQUENCE {
	sCCPCH-CCTrCH-ID							CCTrCH-ID,	-- For DL CCTrCH supporting one or several Secondary CCPCHs
	tFCS										TFCS,		-- For DL CCTrCH supporting one or several Secondary CCPCHs
	tFCI-Coding									TFCI-Coding,
	punctureLimit								PunctureLimit,
	secondaryCCPCH-parameterList				Secondary-CCPCH-parameterList-CTCH-SetupRqstTDD,
	fACH-ParametersList							FACH-ParametersList-CTCH-SetupRqstTDD		OPTIONAL,
	pCH-Parameters								PCH-Parameters-CTCH-SetupRqstTDD			OPTIONAL,
	iE-Extensions								ProtocolExtensionContainer	{{Secondary-CCPCHItem-CTCH-SetupRqstTDD-ExtIEs}}		OPTIONAL,
	...
}

Secondary-CCPCHItem-CTCH-SetupRqstTDD-ExtIEs NBAP-PROTOCOL-EXTENSION ::= {
	{ ID id-Tstd-indicator										CRITICALITY reject	EXTENSION TSTD-Indicator				PRESENCE optional	}|
	{ ID id-MICH-Parameters-CTCH-SetupRqstTDD					CRITICALITY reject	EXTENSION MICH-Parameters-CTCH-SetupRqstTDD		PRESENCE optional	}|
	{ ID id-Additional-S-CCPCH-Parameters-CTCH-SetupRqstTDD		CRITICALITY reject	EXTENSION Secondary-CCPCH-parameterExtendedList-CTCH-SetupRqstTDD		PRESENCE optional	}|
	-- Applicable to 3.84Mcps TDD only, used when more than maxNrOfSCCPCHs SCCPCHs are to be established.
	{ ID id-Additional-S-CCPCH-LCR-Parameters-CTCH-SetupRqstTDD	CRITICALITY reject	EXTENSION Secondary-CCPCH-LCR-parameterExtendedList-CTCH-SetupRqstTDD		PRESENCE optional	}|
	-- Applicable to 1.28Mcps TDD only, used when more than maxNrOfSCCPCHLCRs SCCPCHs are to be established.
	{ ID id-S-CCPCH-768-Parameters-CTCH-SetupRqstTDD			CRITICALITY reject	EXTENSION Secondary-CCPCH-768-parameterList-CTCH-SetupRqstTDD		PRESENCE optional	}|
	{ ID id-S-CCPCH-Modulation									CRITICALITY reject	EXTENSION ModulationMBSFN								PRESENCE optional	}|	-- Applicable to 1.28Mcps TDD, Not Applicable to 3.84Mcps TDD or 7.68Mcps TDD
	{ ID id-TimeSlotConfigurationList-LCR-CTCH-SetupRqstTDD		CRITICALITY reject	EXTENSION TimeSlotConfigurationList-LCR-CTCH-SetupRqstTDD		PRESENCE optional }|
	{ ID id-UARFCNforNt		CRITICALITY reject	EXTENSION UARFCN		PRESENCE optional },
	-- Applicable to 1.28Mcps TDD when using multiple frequencies. This IE indicates the frequency of Secondary Frequency on which SCCPCH to be set up
	...
}

Secondary-CCPCH-parameterList-CTCH-SetupRqstTDD ::= ProtocolIE-Single-Container {{ Secondary-CCPCH-parameterListIEs-CTCH-SetupRqstTDD }}

Secondary-CCPCH-parameterListIEs-CTCH-SetupRqstTDD NBAP-PROTOCOL-IES ::= {
	{ ID id-Secondary-CCPCH-parameterListIE-CTCH-SetupRqstTDD	CRITICALITY reject	TYPE Secondary-CCPCH-parameterListIE-CTCH-SetupRqstTDD		PRESENCE optional }|
	{ ID id-Secondary-CCPCH-LCR-parameterList-CTCH-SetupRqstTDD	CRITICALITY reject	TYPE Secondary-CCPCH-LCR-parameterList-CTCH-SetupRqstTDD	PRESENCE optional }
}

Secondary-CCPCH-parameterListIE-CTCH-SetupRqstTDD ::= SEQUENCE (SIZE (1..maxNrOfSCCPCHs)) OF Secondary-CCPCH-parameterItem-CTCH-SetupRqstTDD

Secondary-CCPCH-parameterItem-CTCH-SetupRqstTDD ::= SEQUENCE {
	commonPhysicalChannelID						CommonPhysicalChannelID,
	tdd-ChannelisationCode						TDD-ChannelisationCode,
	timeslot									TimeSlot,
	midambleShiftandBurstType					MidambleShiftAndBurstType,
	tdd-PhysicalChannelOffset					TDD-PhysicalChannelOffset,
	repetitionPeriod							RepetitionPeriod,
	repetitionLength							RepetitionLength,
	s-CCPCH-Power								DL-Power,
	iE-Extensions								ProtocolExtensionContainer { { Secondary-CCPCH-parameterItem-CTCH-SetupRqstTDD-ExtIEs} }		OPTIONAL,
	...
}

Secondary-CCPCH-parameterItem-CTCH-SetupRqstTDD-ExtIEs NBAP-PROTOCOL-EXTENSION ::= {
	{ ID id-tFCI-Presence						CRITICALITY notify	EXTENSION TFCI-Presence		PRESENCE optional},
	...
}

Secondary-CCPCH-LCR-parameterList-CTCH-SetupRqstTDD ::= SEQUENCE (SIZE (1..maxNrOfSCCPCHLCRs)) OF Secondary-CCPCH-LCR-parameterItem-CTCH-SetupRqstTDD

Secondary-CCPCH-LCR-parameterItem-CTCH-SetupRqstTDD ::= SEQUENCE {
	commonPhysicalChannelID						CommonPhysicalChannelID,
	tdd-ChannelisationCodeLCR					TDD-ChannelisationCodeLCR,
	timeslotLCR									TimeSlotLCR,
	midambleShiftLCR							MidambleShiftLCR,
	-- For 1.28 Mcps TDD, if the cell is operating in MBSFN only mode, NodeB shall ignore the contents of this IE.
	tdd-PhysicalChannelOffset					TDD-PhysicalChannelOffset,
	repetitionPeriod							RepetitionPeriod,
	repetitionLength							RepetitionLength,
	s-CCPCH-Power								DL-Power,
	s-CCPCH-TimeSlotFormat-LCR					TDD-DL-DPCH-TimeSlotFormat-LCR,
	iE-Extensions								ProtocolExtensionContainer { { Secondary-CCPCH-LCR-parameterItem-CTCH-SetupRqstTDD-ExtIEs} }		OPTIONAL,
	...
}

Secondary-CCPCH-LCR-parameterItem-CTCH-SetupRqstTDD-ExtIEs NBAP-PROTOCOL-EXTENSION ::= {
	{ ID	id-MBSFN-SpecialTimeSlot-LCR			CRITICALITY ignore		EXTENSION	TimeslotLCR-Extension			PRESENCE optional },
	-- Only for 1.28 Mcps TDD MBSFN only mode, this IE indicates the MBSFN Special Time Slot [19]. The IE ”Time Slot LCR” shall be ignored if this IE appears
	...
}

Secondary-CCPCH-768-parameterList-CTCH-SetupRqstTDD ::= SEQUENCE (SIZE (1..maxNrOfSCCPCHs768)) OF Secondary-CCPCH-768-parameterItem-CTCH-SetupRqstTDD

Secondary-CCPCH-768-parameterItem-CTCH-SetupRqstTDD ::= SEQUENCE {
	commonPhysicalChannelID768					CommonPhysicalChannelID768,
	tdd-ChannelisationCode768					TDD-ChannelisationCode768,
	timeslot									TimeSlot,
	tFCI-Presence768							TFCI-Presence		OPTIONAL,
	midambleShiftandBurstType768				MidambleShiftAndBurstType768,
	tdd-PhysicalChannelOffset					TDD-PhysicalChannelOffset,
	repetitionPeriod							RepetitionPeriod,
	repetitionLength							RepetitionLength,
	s-CCPCH-Power								DL-Power,
	iE-Extensions								ProtocolExtensionContainer { { Secondary-CCPCH-parameterItem-768-CTCH-SetupRqstTDD-ExtIEs} }		OPTIONAL,
	...
}

Secondary-CCPCH-parameterItem-768-CTCH-SetupRqstTDD-ExtIEs NBAP-PROTOCOL-EXTENSION ::= {
	...
}

FACH-ParametersList-CTCH-SetupRqstTDD ::= ProtocolIE-Single-Container {{ FACH-ParametersListIEs-CTCH-SetupRqstTDD }}

FACH-ParametersListIEs-CTCH-SetupRqstTDD NBAP-PROTOCOL-IES ::= {
	{ ID id-FACH-ParametersListIE-CTCH-SetupRqstTDD   CRITICALITY reject	TYPE FACH-ParametersListIE-CTCH-SetupRqstTDD	PRESENCE mandatory }
}

FACH-ParametersListIE-CTCH-SetupRqstTDD ::= SEQUENCE (SIZE (1..maxNrOfFACHs)) OF FACH-ParametersItem-CTCH-SetupRqstTDD

FACH-ParametersItem-CTCH-SetupRqstTDD ::= SEQUENCE {
	commonTransportChannelID				CommonTransportChannelID,
	fACH-CCTrCH-ID							CCTrCH-ID,
	dl-TransportFormatSet					TransportFormatSet,
	toAWS									ToAWS,
	toAWE									ToAWE,
	iE-Extensions							ProtocolExtensionContainer  { { FACH-ParametersItem-CTCH-SetupRqstTDD-ExtIEs} }		OPTIONAL,
	...
}

FACH-ParametersItem-CTCH-SetupRqstTDD-ExtIEs NBAP-PROTOCOL-EXTENSION ::= {
	{ ID	id-maxFACH-Power-LCR-CTCH-SetupRqstTDD	CRITICALITY	reject	EXTENSION DL-Power			PRESENCE optional	}|
	-- Applicable to 1.28Mcps TDD only
	{ ID	id-bindingID							CRITICALITY	ignore	EXTENSION BindingID			PRESENCE optional	}|
	-- Shall be ignored if bearer establishment with ALCAP.
	{ ID	id-transportlayeraddress				CRITICALITY	ignore	EXTENSION TransportLayerAddress	PRESENCE optional	}|
	-- Shall be ignored if bearer establishment with ALCAP.
	{ ID	id-TnlQos								CRITICALITY ignore	EXTENSION	TnlQos			PRESENCE optional	}|
	-- Shall be ignored if bearer establishment with ALCAP.
	{ ID	id-BroadcastReference					CRITICALITY	ignore	EXTENSION	BroadcastReference 	PRESENCE	optional	}|
	{ ID	id-IPMulticastIndication				CRITICALITY	ignore	EXTENSION	IPMulticastIndication	PRESENCE	optional	},
	...
}

PCH-Parameters-CTCH-SetupRqstTDD ::= ProtocolIE-Single-Container {{ PCH-ParametersIE-CTCH-SetupRqstTDD }}

PCH-ParametersIE-CTCH-SetupRqstTDD NBAP-PROTOCOL-IES ::= {
	{ ID id-PCH-ParametersItem-CTCH-SetupRqstTDD   CRITICALITY reject	TYPE PCH-ParametersItem-CTCH-SetupRqstTDD	PRESENCE mandatory }
}

PCH-ParametersItem-CTCH-SetupRqstTDD ::= SEQUENCE {
	commonTransportChannelID				CommonTransportChannelID,
	pCH-CCTrCH-ID							CCTrCH-ID,
	dl-TransportFormatSet					TransportFormatSet,	-- For the DL.
	toAWS									ToAWS,
	toAWE									ToAWE,
	pICH-Parameters							PICH-Parameters-CTCH-SetupRqstTDD,
	iE-Extensions							ProtocolExtensionContainer  { { PCH-ParametersItem-CTCH-SetupRqstTDD-ExtIEs} }		OPTIONAL,
	...
}

PCH-ParametersItem-CTCH-SetupRqstTDD-ExtIEs NBAP-PROTOCOL-EXTENSION ::= {
	{ ID	id-PCH-Power-LCR-CTCH-SetupRqstTDD			CRITICALITY	reject	EXTENSION DL-Power							PRESENCE optional	}|
	{ ID	id-bindingID								CRITICALITY	ignore	EXTENSION BindingID							PRESENCE optional	}|
	-- Shall be ignored if bearer establishment with ALCAP.
	{ ID	id-transportlayeraddress					CRITICALITY	ignore	EXTENSION TransportLayerAddress						PRESENCE optional	}|
	-- Shall be ignored if bearer establishment with ALCAP.
	{ ID id-PICH-768-Parameters-CTCH-SetupRqstTDD		CRITICALITY reject	EXTENSION PICH-768-ParametersItem-CTCH-SetupRqstTDD		PRESENCE optional	}|
	{ ID id-TnlQos										CRITICALITY ignore	EXTENSION TnlQos							PRESENCE optional	},
	-- Shall be ignored if bearer establishment with ALCAP.
	...
}

PICH-Parameters-CTCH-SetupRqstTDD ::= ProtocolIE-Single-Container {{ PICH-ParametersIE-CTCH-SetupRqstTDD }}

PICH-ParametersIE-CTCH-SetupRqstTDD NBAP-PROTOCOL-IES ::= {
	{ ID id-PICH-ParametersItem-CTCH-SetupRqstTDD	CRITICALITY reject	TYPE PICH-ParametersItem-CTCH-SetupRqstTDD	PRESENCE optional }|
	{ ID id-PICH-LCR-Parameters-CTCH-SetupRqstTDD	CRITICALITY reject	TYPE PICH-LCR-Parameters-CTCH-SetupRqstTDD	PRESENCE optional }
}

PICH-ParametersItem-CTCH-SetupRqstTDD ::= SEQUENCE {
	commonPhysicalChannelID					CommonPhysicalChannelID,
 	tdd-ChannelisationCode					TDD-ChannelisationCode,
 	timeSlot  								TimeSlot,
	midambleshiftAndBurstType				MidambleShiftAndBurstType,
 	tdd-PhysicalChannelOffset				TDD-PhysicalChannelOffset,
 	repetitionPeriod						RepetitionPeriod,
 	repetitionLength						RepetitionLength,
 	pagingIndicatorLength					PagingIndicatorLength,
	pICH-Power								PICH-Power,
	iE-Extensions							ProtocolExtensionContainer  { { PICH-ParametersItem-CTCH-SetupRqstTDD-ExtIEs} }		OPTIONAL,
	...
}

PICH-ParametersItem-CTCH-SetupRqstTDD-ExtIEs NBAP-PROTOCOL-EXTENSION ::= {
	...
}

PICH-LCR-Parameters-CTCH-SetupRqstTDD ::= SEQUENCE {
	commonPhysicalChannelID					CommonPhysicalChannelID,
 	tdd-ChannelisationCodeLCR				TDD-ChannelisationCodeLCR,
 	timeSlotLCR  							TimeSlotLCR,
	midambleShiftLCR						MidambleShiftLCR,
	tdd-PhysicalChannelOffset				TDD-PhysicalChannelOffset,
 	repetitionPeriod						RepetitionPeriod,
 	repetitionLength						RepetitionLength,
 	pagingIndicatorLength					PagingIndicatorLength,
	pICH-Power								PICH-Power,
	second-TDD-ChannelisationCodeLCR		TDD-ChannelisationCodeLCR,
	iE-Extensions							ProtocolExtensionContainer  { { PICH-LCR-ParametersItem-CTCH-SetupRqstTDD-ExtIEs} }		OPTIONAL,
	...
}

PICH-LCR-ParametersItem-CTCH-SetupRqstTDD-ExtIEs NBAP-PROTOCOL-EXTENSION ::= {
	{ ID	id-Tstd-indicator			CRITICALITY	reject		EXTENSION 	TSTD-Indicator		PRESENCE 	optional	},
	-- Applicable to 1.28 Mcps TDD only
	...
}

PICH-768-ParametersItem-CTCH-SetupRqstTDD ::= SEQUENCE {
	commonPhysicalChannelID768				CommonPhysicalChannelID768,
	tdd-ChannelisationCode768				TDD-ChannelisationCode768,
	timeSlot  								TimeSlot,
	midambleshiftAndBurstType78				MidambleShiftAndBurstType768,
	tdd-PhysicalChannelOffset				TDD-PhysicalChannelOffset,
	repetitionPeriod						RepetitionPeriod,
	repetitionLength						RepetitionLength,
	pagingIndicatorLength					PagingIndicatorLength,
	pICH-Power								PICH-Power,
	iE-Extensions							ProtocolExtensionContainer  { { PICH-768-ParametersItem-CTCH-SetupRqstTDD-ExtIEs} }		OPTIONAL,
	...
}

PICH-768-ParametersItem-CTCH-SetupRqstTDD-ExtIEs NBAP-PROTOCOL-EXTENSION ::= {
	...
}


MICH-Parameters-CTCH-SetupRqstTDD ::= SEQUENCE {
	commonPhysicalChannelID					CommonPhysicalChannelID,
	tdd-PhysicalChannelOffset				TDD-PhysicalChannelOffset,
	repetitionPeriod						RepetitionPeriod,
	repetitionLength						RepetitionLength,
	notificationIndicatorLength				NotificationIndicatorLength,
	mICH-Power								PICH-Power,
	mICH-TDDOption-Specific-Parameters		MICH-TDDOption-Specific-Parameters-CTCH-SetupRqstTDD,
	iE-Extensions							ProtocolExtensionContainer  { { MICH-Parameters-CTCH-SetupRqstTDD-ExtIEs} }		OPTIONAL,
	...
}

MICH-Parameters-CTCH-SetupRqstTDD-ExtIEs NBAP-PROTOCOL-EXTENSION ::= {
	...
}

MICH-TDDOption-Specific-Parameters-CTCH-SetupRqstTDD ::= CHOICE {
	hCR-TDD									MICH-HCR-Parameters-CTCH-SetupRqstTDD,
	lCR-TDD									MICH-LCR-Parameters-CTCH-SetupRqstTDD,
	...,
	cHipRate768-TDD							MICH-768-Parameters-CTCH-SetupRqstTDD
}

MICH-HCR-Parameters-CTCH-SetupRqstTDD ::= SEQUENCE {
	tdd-ChannelisationCode					TDD-ChannelisationCode,
	timeSlot								TimeSlot,
	midambleshiftAndBurstType				MidambleShiftAndBurstType,
	iE-Extensions							ProtocolExtensionContainer { { MICH-HCR-Parameters-CTCH-SetupRqstTDD-ExtIEs } }		OPTIONAL,
	...
}

MICH-HCR-Parameters-CTCH-SetupRqstTDD-ExtIEs NBAP-PROTOCOL-EXTENSION ::= {
	...
}

MICH-LCR-Parameters-CTCH-SetupRqstTDD ::= SEQUENCE {
	tdd-ChannelisationCodeLCR				TDD-ChannelisationCodeLCR,
	timeSlotLCR								TimeSlotLCR,
	midambleShiftLCR						MidambleShiftLCR,
	-- For 1.28 Mcps TDD, if the cell is operating in MBSFN only mode, NodeB shall ignore the contents of this IE.
	second-TDD-ChannelisationCodeLCR		TDD-ChannelisationCodeLCR,
	tSTD-Indicator							TSTD-Indicator,
	iE-Extensions							ProtocolExtensionContainer { { MICH-LCR-Parameters-CTCH-SetupRqstTDD-ExtIEs } }		OPTIONAL,
	...
}

MICH-LCR-Parameters-CTCH-SetupRqstTDD-ExtIEs NBAP-PROTOCOL-EXTENSION ::= {
	{ ID	id-MBSFN-SpecialTimeSlot-LCR			CRITICALITY ignore		EXTENSION TimeslotLCR-Extension			PRESENCE optional },
	-- Only for 1.28 Mcps TDD MBSFN only mode, this IE indicates the MBSFN Special Time Slot [19]. The IE ”Time Slot LCR” shall be ignored if this IE appears
	...
}

MICH-768-Parameters-CTCH-SetupRqstTDD ::= SEQUENCE {
	tdd-ChannelisationCode768				TDD-ChannelisationCode768,
	timeSlot								TimeSlot,
	midambleshiftAndBurstType768			MidambleShiftAndBurstType768,
	iE-Extensions							ProtocolExtensionContainer { { MICH-768-Parameters-CTCH-SetupRqstTDD-ExtIEs } }		OPTIONAL,
	...
}

MICH-768-Parameters-CTCH-SetupRqstTDD-ExtIEs NBAP-PROTOCOL-EXTENSION ::= {
	...
}

TimeSlotConfigurationList-LCR-CTCH-SetupRqstTDD ::= SEQUENCE (SIZE (1..7)) OF TimeSlotConfigurationItem-LCR-CTCH-SetupRqstTDD

TimeSlotConfigurationItem-LCR-CTCH-SetupRqstTDD ::= SEQUENCE {
	timeslotLCR								TimeSlotLCR,
	timeslotLCR-Parameter-ID				CellParameterID,
	iE-Extensions							ProtocolExtensionContainer { { TimeSlotConfigurationItem-LCR-CTCH-SetupRqstTDD-ExtIEs} }		OPTIONAL,
	...
}

TimeSlotConfigurationItem-LCR-CTCH-SetupRqstTDD-ExtIEs NBAP-PROTOCOL-EXTENSION ::= {
	...
}

Secondary-CCPCH-parameterExtendedList-CTCH-SetupRqstTDD ::= SEQUENCE (SIZE (1..maxNrOfSCCPCHsinExt)) OF Secondary-CCPCH-parameterItem-CTCH-SetupRqstTDD
	-- Applicable to 3.84Mcps TDD only, used when more than maxNrOfSCCPCHs SCCPCHs are to be established.

Secondary-CCPCH-LCR-parameterExtendedList-CTCH-SetupRqstTDD ::= SEQUENCE (SIZE (1..maxNrOfSCCPCHsLCRinExt)) OF Secondary-CCPCH-LCR-parameterItem-CTCH-SetupRqstTDD
	-- Applicable to 1.28Mcps TDD only, used when more than maxNrOfSCCPCHLCRs SCCPCHs are to be established.

PRACH-CTCH-SetupRqstTDD ::= SEQUENCE {
	pRACH-Parameters-CTCH-SetupRqstTDD			PRACH-Parameters-CTCH-SetupRqstTDD,
	iE-Extensions								ProtocolExtensionContainer  { { PRACH-CTCH-SetupRqstTDD-ExtIEs } }		OPTIONAL,
	...
}

PRACH-CTCH-SetupRqstTDD-ExtIEs NBAP-PROTOCOL-EXTENSION ::= {
	{ ID id-FPACH-LCR-Parameters-CTCH-SetupRqstTDD	CRITICALITY reject	EXTENSION FPACH-LCR-Parameters-CTCH-SetupRqstTDD	PRESENCE optional	}|
	-- Mandatory for 1.28Mcps TDD, Not Applicable to 3.84Mcps TDD or 7.68Mcps TDD
	{ ID id-PRACH-768-Parameters-CTCH-SetupRqstTDD	CRITICALITY reject	EXTENSION PRACH-768-ParametersItem-CTCH-SetupRqstTDD	PRESENCE optional	},
	...
}

PRACH-Parameters-CTCH-SetupRqstTDD ::= ProtocolIE-Single-Container {{ PRACH-ParametersIE-CTCH-SetupRqstTDD }}

PRACH-ParametersIE-CTCH-SetupRqstTDD NBAP-PROTOCOL-IES ::= {
	{ ID id-PRACH-ParametersItem-CTCH-SetupRqstTDD		CRITICALITY reject	TYPE PRACH-ParametersItem-CTCH-SetupRqstTDD		PRESENCE optional }|
	{ ID id-PRACH-LCR-ParametersList-CTCH-SetupRqstTDD	CRITICALITY reject	TYPE PRACH-LCR-ParametersList-CTCH-SetupRqstTDD	PRESENCE optional }
}


PRACH-ParametersItem-CTCH-SetupRqstTDD ::= SEQUENCE {
	commonPhysicalChannelID						CommonPhysicalChannelID,
	tFCS										TFCS,
	timeslot									TimeSlot,
	tdd-ChannelisationCode						TDD-ChannelisationCode,
	maxPRACH-MidambleShifts						MaxPRACH-MidambleShifts,
	pRACH-Midamble 								PRACH-Midamble,
	rACH										RACH-Parameter-CTCH-SetupRqstTDD,
	iE-Extensions								ProtocolExtensionContainer  { { PRACH-ParametersItem-CTCH-SetupRqstTDD-ExtIEs} }		OPTIONAL,
	...
}

PRACH-ParametersItem-CTCH-SetupRqstTDD-ExtIEs NBAP-PROTOCOL-EXTENSION ::= {
	...
}

RACH-Parameter-CTCH-SetupRqstTDD ::= ProtocolIE-Single-Container {{ RACH-ParameterIE-CTCH-SetupRqstTDD }}

RACH-ParameterIE-CTCH-SetupRqstTDD NBAP-PROTOCOL-IES ::= {
	{ ID id-RACH-ParameterItem-CTCH-SetupRqstTDD   CRITICALITY reject	TYPE RACH-ParameterItem-CTCH-SetupRqstTDD	PRESENCE mandatory }
}

RACH-ParameterItem-CTCH-SetupRqstTDD ::= SEQUENCE {
	commonTransportChannelID					CommonTransportChannelID,
	uL-TransportFormatSet						TransportFormatSet,	-- For the UL
	iE-Extensions								ProtocolExtensionContainer  { { RACH-ParameterItem-CTCH-SetupRqstTDD-ExtIEs} }		OPTIONAL,
	...
}

RACH-ParameterItem-CTCH-SetupRqstTDD-ExtIEs NBAP-PROTOCOL-EXTENSION ::= {
	{ ID id-bindingID					CRITICALITY ignore	EXTENSION BindingID					PRESENCE optional }|
		-- Shall be ignored if bearer establishment with ALCAP.
	{ ID id-transportlayeraddress		CRITICALITY ignore	EXTENSION TransportLayerAddress		PRESENCE optional }|
		-- Shall be ignored if bearer establishment with ALCAP.
	{ ID	id-TnlQos					CRITICALITY ignore	EXTENSION TnlQos					PRESENCE optional },
	-- Shall be ignored if bearer establishment with ALCAP.
	...
}

PRACH-LCR-ParametersList-CTCH-SetupRqstTDD ::= SEQUENCE (SIZE (1..maxNrOfPRACHLCRs)) OF PRACH-LCR-ParametersItem-CTCH-SetupRqstTDD 

PRACH-LCR-ParametersItem-CTCH-SetupRqstTDD ::= SEQUENCE {
	commonPhysicalChannelID						CommonPhysicalChannelID,
	tFCS										TFCS,
	timeslotLCR									TimeSlotLCR,
	tdd-ChannelisationCodeLCR					TDD-ChannelisationCodeLCR,
	midambleShiftLCR							MidambleShiftLCR,
	rACH										RACH-Parameter-CTCH-SetupRqstTDD,
	iE-Extensions								ProtocolExtensionContainer  { { PRACH-LCR-ParametersItem-CTCH-SetupRqstTDD-ExtIEs} }		OPTIONAL,
	...
}

PRACH-LCR-ParametersItem-CTCH-SetupRqstTDD-ExtIEs NBAP-PROTOCOL-EXTENSION ::= {
	 { ID id-UARFCNforNt	CRITICALITY reject		EXTENSION UARFCN		PRESENCE optional },
	-- Applicable to 1.28Mcps TDD when using multiple frequencies. This IE indicates the frequency of secondary on which PRACH to be set up.
	...
}

PRACH-768-ParametersItem-CTCH-SetupRqstTDD ::= SEQUENCE {
	commonPhysicalChannelID768					CommonPhysicalChannelID768,
	tFCS										TFCS,
	timeslot									TimeSlot,
	tdd-ChannelisationCode768					TDD-ChannelisationCode768,
	maxPRACH-MidambleShifts						MaxPRACH-MidambleShifts,
	pRACH-Midamble 								PRACH-Midamble,
	rACH										RACH-Parameter-CTCH-SetupRqstTDD,
	iE-Extensions								ProtocolExtensionContainer  { { PRACH-768-ParametersItem-CTCH-SetupRqstTDD-ExtIEs} }		OPTIONAL,
	...
}

PRACH-768-ParametersItem-CTCH-SetupRqstTDD-ExtIEs NBAP-PROTOCOL-EXTENSION ::= {
	...
}

FPACH-LCR-Parameters-CTCH-SetupRqstTDD ::= SEQUENCE {
	commonPhysicalChannelID						CommonPhysicalChannelID,
 	tdd-ChannelisationCodeLCR					TDD-ChannelisationCodeLCR,
	timeslotLCR									TimeSlotLCR,
	midambleShiftLCR							MidambleShiftLCR,
	fPACH-Power									FPACH-Power,
	iE-Extensions								ProtocolExtensionContainer  { { FPACH-LCR-ParametersItem-CTCH-SetupRqstTDD-ExtIEs} }		OPTIONAL,
	...
}

FPACH-LCR-ParametersItem-CTCH-SetupRqstTDD-ExtIEs NBAP-PROTOCOL-EXTENSION ::= {
	{ ID id-UARFCNforNt		CRITICALITY reject		EXTENSION UARFCN		PRESENCE optional },
	--  Applicable to 1.28Mcps TDD when using multiple frequencies. This IE indicates the frequency of Secondary Frequency on which FPACH to be set up.
	...
}

PLCCH-parameters  ::= SEQUENCE {
	maxPowerPLCCH								DL-Power,
	commonPhysicalChannelID						CommonPhysicalChannelID,
 	tdd-ChannelisationCode						TDD-ChannelisationCode,
	timeslotLCR									TimeSlotLCR,
	midambleShiftLCR							MidambleShiftLCR,
	iE-Extensions								ProtocolExtensionContainer  { { PLCCH-ParametersItem-CTCH-SetupRqstTDD-ExtIEs} }		OPTIONAL,
	...
}

PLCCH-ParametersItem-CTCH-SetupRqstTDD-ExtIEs NBAP-PROTOCOL-EXTENSION ::= {
	...
}

E-RUCCH-parameters  ::= SEQUENCE {
	commonPhysicalChannelID						CommonPhysicalChannelID,
	timeslot									TimeSlot,
	tdd-ChannelisationCode						TDD-ChannelisationCode,
	maxE-RUCCH-MidambleShifts					MaxPRACH-MidambleShifts,
	e-RUCCH-Midamble							PRACH-Midamble,
	iE-Extensions								ProtocolExtensionContainer  { { E-RUCCH-ParametersItem-CTCH-SetupRqstTDD-ExtIEs} }		OPTIONAL,
	...
}

E-RUCCH-ParametersItem-CTCH-SetupRqstTDD-ExtIEs NBAP-PROTOCOL-EXTENSION ::= {
	...
}

E-RUCCH-768-parameters  ::= SEQUENCE {
	commonPhysicalChannelID768					CommonPhysicalChannelID768,
	timeslot									TimeSlot,
	tdd-ChannelisationCode768					TDD-ChannelisationCode768,
	maxE-RUCCH-MidambleShifts					MaxPRACH-MidambleShifts,
	e-RUCCH-Midamble							PRACH-Midamble,
	iE-Extensions								ProtocolExtensionContainer  { { E-RUCCH-768-ParametersItem-CTCH-SetupRqstTDD-ExtIEs} }		OPTIONAL,
	...
}

E-RUCCH-768-ParametersItem-CTCH-SetupRqstTDD-ExtIEs NBAP-PROTOCOL-EXTENSION ::= {
	...
}

-- **************************************************************
--
-- COMMON TRANSPORT CHANNEL SETUP RESPONSE
--
-- **************************************************************

CommonTransportChannelSetupResponse ::= SEQUENCE {
	protocolIEs				ProtocolIE-Container		{{CommonTransportChannelSetupResponse-IEs}},
	protocolExtensions		ProtocolExtensionContainer	{{CommonTransportChannelSetupResponse-Extensions}}    OPTIONAL,
	...
}

CommonTransportChannelSetupResponse-IEs NBAP-PROTOCOL-IES ::= {
	{ ID id-FACH-ParametersList-CTCH-SetupRsp	CRITICALITY ignore	TYPE FACH-CommonTransportChannel-InformationResponse		PRESENCE	optional	}|
	{ ID id-PCH-Parameters-CTCH-SetupRsp		CRITICALITY ignore	TYPE CommonTransportChannel-InformationResponse				PRESENCE	optional	}|
	{ ID id-RACH-Parameters-CTCH-SetupRsp		CRITICALITY ignore	TYPE CommonTransportChannel-InformationResponse				PRESENCE	optional	}|
	{ ID id-CriticalityDiagnostics				CRITICALITY ignore	TYPE CriticalityDiagnostics					PRESENCE	optional	},
	...
}

CommonTransportChannelSetupResponse-Extensions NBAP-PROTOCOL-EXTENSION ::= {
	...
}

FACH-CommonTransportChannel-InformationResponse ::= SEQUENCE (SIZE (1..maxNrOfFACHs)) OF CommonTransportChannel-InformationResponse

-- **************************************************************
--
-- COMMON TRANSPORT CHANNEL SETUP FAILURE
--
-- **************************************************************

CommonTransportChannelSetupFailure ::= SEQUENCE {
	protocolIEs				ProtocolIE-Container		{{CommonTransportChannelSetupFailure-IEs}},
	protocolExtensions		ProtocolExtensionContainer	{{CommonTransportChannelSetupFailure-Extensions}}     OPTIONAL,
	...
}

CommonTransportChannelSetupFailure-IEs NBAP-PROTOCOL-IES ::= {
	{ ID	id-Cause					CRITICALITY	ignore		TYPE	Cause						PRESENCE	mandatory	}|
	{ ID	id-CriticalityDiagnostics	CRITICALITY	ignore		TYPE	CriticalityDiagnostics		PRESENCE	optional		},
	...
}

CommonTransportChannelSetupFailure-Extensions NBAP-PROTOCOL-EXTENSION ::= {
	...
}

-- **************************************************************
--
-- COMMON TRANSPORT CHANNEL RECONFIGURATION REQUEST FDD
--
-- **************************************************************

CommonTransportChannelReconfigurationRequestFDD ::= SEQUENCE {
	protocolIEs				ProtocolIE-Container		{{CommonTransportChannelReconfigurationRequestFDD-IEs}},
	protocolExtensions		ProtocolExtensionContainer	{{CommonTransportChannelReconfigurationRequestFDD-Extensions}}		OPTIONAL,
	...
}

CommonTransportChannelReconfigurationRequestFDD-IEs NBAP-PROTOCOL-IES ::= {
	{ ID id-C-ID											CRITICALITY reject	TYPE C-ID							PRESENCE mandatory }|
	{ ID id-ConfigurationGenerationID						CRITICALITY reject	TYPE ConfigurationGenerationID					PRESENCE mandatory }|
	{ ID id-CommonPhysicalChannelType-CTCH-ReconfRqstFDD	CRITICALITY reject	TYPE CommonPhysicalChannelType-CTCH-ReconfRqstFDD	PRESENCE mandatory },
	...
}

CommonTransportChannelReconfigurationRequestFDD-Extensions NBAP-PROTOCOL-EXTENSION ::= {
	...
}

CommonPhysicalChannelType-CTCH-ReconfRqstFDD ::= CHOICE {
	secondary-CCPCH-parameters		Secondary-CCPCHList-CTCH-ReconfRqstFDD,
	pRACH-parameters				PRACHList-CTCH-ReconfRqstFDD,
	notUsed-cPCH-parameters			NULL,
	...
}

Secondary-CCPCHList-CTCH-ReconfRqstFDD ::= SEQUENCE {
	fACH-ParametersList-CTCH-ReconfRqstFDD		FACH-ParametersList-CTCH-ReconfRqstFDD	OPTIONAL,
	pCH-Parameters-CTCH-ReconfRqstFDD			PCH-Parameters-CTCH-ReconfRqstFDD		OPTIONAL,
	pICH-Parameters-CTCH-ReconfRqstFDD			PICH-Parameters-CTCH-ReconfRqstFDD		OPTIONAL,
	iE-Extensions								ProtocolExtensionContainer { { Secondary-CCPCH-CTCH-ReconfRqstFDD-ExtIEs} } OPTIONAL,
	...
}

Secondary-CCPCH-CTCH-ReconfRqstFDD-ExtIEs NBAP-PROTOCOL-EXTENSION ::= {
	{ ID id-MICH-Parameters-CTCH-ReconfRqstFDD		CRITICALITY reject	EXTENSION MICH-Parameters-CTCH-ReconfRqstFDD			PRESENCE optional	},
	...
}

FACH-ParametersList-CTCH-ReconfRqstFDD ::= ProtocolIE-Single-Container {{ FACH-ParametersListIEs-CTCH-ReconfRqstFDD }}

FACH-ParametersListIEs-CTCH-ReconfRqstFDD NBAP-PROTOCOL-IES ::= {
	{ ID id-FACH-ParametersListIE-CTCH-ReconfRqstFDD	CRITICALITY reject	TYPE FACH-ParametersListIE-CTCH-ReconfRqstFDD 	PRESENCE	mandatory }
}

FACH-ParametersListIE-CTCH-ReconfRqstFDD ::= SEQUENCE (SIZE (1..maxFACHCell)) OF FACH-ParametersItem-CTCH-ReconfRqstFDD

FACH-ParametersItem-CTCH-ReconfRqstFDD ::= SEQUENCE {
	commonTransportChannelID				CommonTransportChannelID,
	maxFACH-Power							DL-Power		OPTIONAL,
	toAWS									ToAWS			OPTIONAL,
	toAWE									ToAWE			OPTIONAL,
	iE-Extensions							ProtocolExtensionContainer  { { FACH-ParametersItem-CTCH-ReconfRqstFDD-ExtIEs} }		OPTIONAL,
	...
}

FACH-ParametersItem-CTCH-ReconfRqstFDD-ExtIEs NBAP-PROTOCOL-EXTENSION ::= {
	{ ID	id-TnlQos			CRITICALITY ignore		EXTENSION TnlQos	PRESENCE optional },
	...
}

PCH-Parameters-CTCH-ReconfRqstFDD ::= ProtocolIE-Single-Container {{ PCH-ParametersIE-CTCH-ReconfRqstFDD }}

PCH-ParametersIE-CTCH-ReconfRqstFDD NBAP-PROTOCOL-IES ::= {
	{ ID id-PCH-ParametersItem-CTCH-ReconfRqstFDD	CRITICALITY reject	TYPE PCH-ParametersItem-CTCH-ReconfRqstFDD 	PRESENCE	mandatory }
}

PCH-ParametersItem-CTCH-ReconfRqstFDD ::= SEQUENCE {
	commonTransportChannelID				CommonTransportChannelID,
	pCH-Power								DL-Power		OPTIONAL,
	toAWS									ToAWS			OPTIONAL,
	toAWE									ToAWE			OPTIONAL,
	iE-Extensions							ProtocolExtensionContainer  { { PCH-ParametersItem-CTCH-ReconfRqstFDD-ExtIEs} }			OPTIONAL,
	...
}

PCH-ParametersItem-CTCH-ReconfRqstFDD-ExtIEs NBAP-PROTOCOL-EXTENSION ::= {
	{ ID	id-TnlQos			CRITICALITY ignore		EXTENSION TnlQos	PRESENCE optional },
	...
}

PICH-Parameters-CTCH-ReconfRqstFDD ::= ProtocolIE-Single-Container {{ PICH-ParametersIE-CTCH-ReconfRqstFDD }}

PICH-ParametersIE-CTCH-ReconfRqstFDD NBAP-PROTOCOL-IES ::= {
	{ ID id-PICH-ParametersItem-CTCH-ReconfRqstFDD	CRITICALITY reject	TYPE PICH-ParametersItem-CTCH-ReconfRqstFDD 	PRESENCE	mandatory }
}

PICH-ParametersItem-CTCH-ReconfRqstFDD ::= SEQUENCE {
	commonPhysicalChannelID				CommonPhysicalChannelID,
	pICH-Power							PICH-Power		OPTIONAL,
	iE-Extensions						ProtocolExtensionContainer  { { PICH-ParametersItem-CTCH-ReconfRqstFDD-ExtIEs} }		OPTIONAL,
	...
}

PICH-ParametersItem-CTCH-ReconfRqstFDD-ExtIEs NBAP-PROTOCOL-EXTENSION ::= {
	...
}

MICH-Parameters-CTCH-ReconfRqstFDD ::= SEQUENCE {
	commonPhysicalChannelID				CommonPhysicalChannelID,
	mICH-Power							PICH-Power															OPTIONAL,
	iE-Extensions						ProtocolExtensionContainer  { { MICH-Parameters-CTCH-ReconfRqstFDD-ExtIEs} }		OPTIONAL,
	...
}

MICH-Parameters-CTCH-ReconfRqstFDD-ExtIEs NBAP-PROTOCOL-EXTENSION ::= {
	...
}

PRACHList-CTCH-ReconfRqstFDD ::= SEQUENCE {
	pRACH-ParametersList-CTCH-ReconfRqstFDD		PRACH-ParametersList-CTCH-ReconfRqstFDD	OPTIONAL,
	aICH-ParametersList-CTCH-ReconfRqstFDD		AICH-ParametersList-CTCH-ReconfRqstFDD	OPTIONAL,
	iE-Extensions								ProtocolExtensionContainer { { PRACH-CTCH-ReconfRqstFDD-ExtIEs} } OPTIONAL,
	...
}

PRACH-CTCH-ReconfRqstFDD-ExtIEs NBAP-PROTOCOL-EXTENSION ::= {
	...
}

PRACH-ParametersList-CTCH-ReconfRqstFDD ::= ProtocolIE-Single-Container {{ PRACH-ParametersListIEs-CTCH-ReconfRqstFDD }}

PRACH-ParametersListIEs-CTCH-ReconfRqstFDD NBAP-PROTOCOL-IES ::= {
	{ ID id-PRACH-ParametersListIE-CTCH-ReconfRqstFDD	CRITICALITY reject	TYPE PRACH-ParametersListIE-CTCH-ReconfRqstFDD 	PRESENCE	mandatory }
}

PRACH-ParametersListIE-CTCH-ReconfRqstFDD ::= SEQUENCE (SIZE (1..maxPRACHCell)) OF PRACH-ParametersItem-CTCH-ReconfRqstFDD

PRACH-ParametersItem-CTCH-ReconfRqstFDD ::= SEQUENCE {
	commonPhysicalChannelID					CommonPhysicalChannelID,
	preambleSignatures						PreambleSignatures														OPTIONAL,
	allowedSlotFormatInformation			AllowedSlotFormatInformationList-CTCH-ReconfRqstFDD						OPTIONAL,
	rACH-SubChannelNumbers					RACH-SubChannelNumbers													OPTIONAL,
	iE-Extensions							ProtocolExtensionContainer  { { PRACH-ParametersItem-CTCH-ReconfRqstFDD-ExtIEs} }	OPTIONAL,
	...
}

PRACH-ParametersItem-CTCH-ReconfRqstFDD-ExtIEs NBAP-PROTOCOL-EXTENSION ::= {
{ ID	id-TnlQos			CRITICALITY ignore		EXTENSION TnlQos	PRESENCE optional },
	...
}

AllowedSlotFormatInformationList-CTCH-ReconfRqstFDD ::= SEQUENCE (SIZE (1.. maxNrOfSlotFormatsPRACH)) OF AllowedSlotFormatInformationItem-CTCH-ReconfRqstFDD

AllowedSlotFormatInformationItem-CTCH-ReconfRqstFDD ::= SEQUENCE {
	rACH-SlotFormat							RACH-SlotFormat,
	iE-Extensions							ProtocolExtensionContainer  { { AllowedSlotFormatInformationItem-CTCH-ReconfRqstFDD-ExtIEs} }		OPTIONAL,
	...
}

AllowedSlotFormatInformationItem-CTCH-ReconfRqstFDD-ExtIEs NBAP-PROTOCOL-EXTENSION ::= {
	...
}

AICH-ParametersList-CTCH-ReconfRqstFDD ::= ProtocolIE-Single-Container {{ AICH-ParametersListIEs-CTCH-ReconfRqstFDD }}

AICH-ParametersListIEs-CTCH-ReconfRqstFDD NBAP-PROTOCOL-IES ::= {
	{ ID id-AICH-ParametersListIE-CTCH-ReconfRqstFDD	CRITICALITY reject	TYPE AICH-ParametersListIE-CTCH-ReconfRqstFDD 	PRESENCE	mandatory }
}

AICH-ParametersListIE-CTCH-ReconfRqstFDD ::= SEQUENCE (SIZE (1..maxPRACHCell)) OF AICH-ParametersItem-CTCH-ReconfRqstFDD

AICH-ParametersItem-CTCH-ReconfRqstFDD ::= SEQUENCE {
	commonPhysicalChannelID				CommonPhysicalChannelID,
	aICH-Power							AICH-Power		OPTIONAL,
	iE-Extensions						ProtocolExtensionContainer  { { AICH-ParametersItemIE-CTCH-ReconfRqstFDD-ExtIEs} }		OPTIONAL,
	...
}

AICH-ParametersItemIE-CTCH-ReconfRqstFDD-ExtIEs NBAP-PROTOCOL-EXTENSION ::= {
	...
}

-- **************************************************************
--
-- COMMON TRANSPORT CHANNEL RECONFIGURATION REQUEST TDD
--
-- **************************************************************

CommonTransportChannelReconfigurationRequestTDD ::= SEQUENCE {
	protocolIEs				ProtocolIE-Container		{{CommonTransportChannelReconfigurationRequestTDD-IEs}},
	protocolExtensions		ProtocolExtensionContainer	{{CommonTransportChannelReconfigurationRequestTDD-Extensions}}		OPTIONAL,
	...
}

CommonTransportChannelReconfigurationRequestTDD-IEs NBAP-PROTOCOL-IES ::= {
	{ ID id-C-ID									CRITICALITY reject	TYPE C-ID						PRESENCE mandatory }|
	{ ID id-ConfigurationGenerationID				CRITICALITY reject	TYPE ConfigurationGenerationID		PRESENCE mandatory }|
	{ ID id-Secondary-CCPCH-Parameters-CTCH-ReconfRqstTDD	CRITICALITY reject	TYPE Secondary-CCPCH-Parameters-CTCH-ReconfRqstTDD		PRESENCE optional	}|
	{ ID id-PICH-Parameters-CTCH-ReconfRqstTDD		CRITICALITY reject	TYPE PICH-Parameters-CTCH-ReconfRqstTDD		PRESENCE optional }|
	{ ID id-FACH-ParametersList-CTCH-ReconfRqstTDD	CRITICALITY reject	TYPE FACH-ParametersList-CTCH-ReconfRqstTDD		PRESENCE optional }|
	{ ID id-PCH-Parameters-CTCH-ReconfRqstTDD		CRITICALITY reject	TYPE PCH-Parameters-CTCH-ReconfRqstTDD		PRESENCE optional },
	...
}

CommonTransportChannelReconfigurationRequestTDD-Extensions NBAP-PROTOCOL-EXTENSION ::= {
	{ ID id-FPACH-LCR-Parameters-CTCH-ReconfRqstTDD			CRITICALITY reject	EXTENSION FPACH-LCR-Parameters-CTCH-ReconfRqstTDD						PRESENCE optional }|
	-- Applicable to 1.28Mcps TDD only
	{ ID id-MICH-Parameters-CTCH-ReconfRqstTDD				CRITICALITY reject	EXTENSION MICH-Parameters-CTCH-ReconfRqstTDD							PRESENCE optional }|
	{ ID id-PLCCH-Parameters-CTCH-ReconfRqstTDD				CRITICALITY ignore	EXTENSION PLCCH-Parameters-CTCH-ReconfRqstTDD						PRESENCE optional }|
	{ ID id-S-CCPCH-768-Parameters-CTCH-ReconfRqstTDD		CRITICALITY reject	EXTENSION Secondary-CCPCH-768-Parameters-CTCH-ReconfRqstTDD		PRESENCE optional }|
	{ ID id-PICH-768-Parameters-CTCH-ReconfRqstTDD			CRITICALITY reject	EXTENSION PICH-768-Parameters-CTCH-ReconfRqstTDD					PRESENCE optional }|
	{ ID id-MICH-768-Parameters-CTCH-ReconfRqstTDD			CRITICALITY reject	EXTENSION MICH-768-Parameters-CTCH-ReconfRqstTDD					PRESENCE optional }|
	{ ID id-UPPCH-LCR-Parameters-CTCH-ReconfRqstTDD			CRITICALITY reject	EXTENSION UPPCH-LCR-Parameters-CTCH-ReconfRqstTDD				PRESENCE optional },	-- Applicable to 1.28Mcps TDD only	
	...
}

Secondary-CCPCH-Parameters-CTCH-ReconfRqstTDD::= SEQUENCE {
	cCTrCH-ID						CCTrCH-ID,
	secondaryCCPCHList				Secondary-CCPCHList-CTCH-ReconfRqstTDD			OPTIONAL,
	iE-Extensions					ProtocolExtensionContainer  { { Secondary-CCPCH-CTCH-ReconfRqstTDD-ExtIEs} }		OPTIONAL,
	...
}

Secondary-CCPCH-CTCH-ReconfRqstTDD-ExtIEs NBAP-PROTOCOL-EXTENSION ::= {
	{ ID id-Additional-S-CCPCH-Parameters-CTCH-ReconfRqstTDD			CRITICALITY reject	EXTENSION Secondary-CCPCH-parameterExtendedList-CTCH-ReconfRqstTDD		PRESENCE optional	}|
	-- Applicable to 3.84Mcps TDD only, used when more than maxNrOfSCCPCHs SCCPCHs are to be reconfigured.
	{ ID id-Additional-S-CCPCH-LCR-Parameters-CTCH-ReconfRqstTDD		CRITICALITY reject	EXTENSION Secondary-CCPCH-LCR-parameterExtendedList-CTCH-ReconfRqstTDD	PRESENCE optional	},
	-- Applicable to 1.28Mcps TDD only, used when more than maxNrOfSCCPCHs SCCPCHs are to be reconfigured.
	...
}

Secondary-CCPCHList-CTCH-ReconfRqstTDD ::= ProtocolIE-Single-Container {{ Secondary-CCPCHListIEs-CTCH-ReconfRqstTDD }}

Secondary-CCPCHListIEs-CTCH-ReconfRqstTDD NBAP-PROTOCOL-IES ::= {
	{ ID id-Secondary-CCPCHListIE-CTCH-ReconfRqstTDD	CRITICALITY reject	TYPE Secondary-CCPCHListIE-CTCH-ReconfRqstTDD 	PRESENCE	mandatory }
}

Secondary-CCPCHListIE-CTCH-ReconfRqstTDD ::= SEQUENCE (SIZE (1..maxNrOfSCCPCHs)) OF Secondary-CCPCHItem-CTCH-ReconfRqstTDD

Secondary-CCPCHItem-CTCH-ReconfRqstTDD ::= SEQUENCE {
	commonPhysicalChannelID				CommonPhysicalChannelID,
	sCCPCH-Power						DL-Power		OPTIONAL,
	iE-Extensions						ProtocolExtensionContainer  { { Secondary-CCPCHItem-CTCH-ReconfRqstTDD-ExtIEs} }		OPTIONAL,
	...
}

Secondary-CCPCHItem-CTCH-ReconfRqstTDD-ExtIEs NBAP-PROTOCOL-EXTENSION ::= {
	...
}

Secondary-CCPCH-parameterExtendedList-CTCH-ReconfRqstTDD ::= SEQUENCE (SIZE (1..maxNrOfSCCPCHsinExt)) OF Secondary-CCPCHItem-CTCH-ReconfRqstTDD
	-- Applicable to 3.84Mcps TDD only, used when more than maxNrOfSCCPCHs SCCPCHs are to be reconfigured.

Secondary-CCPCH-LCR-parameterExtendedList-CTCH-ReconfRqstTDD ::= SEQUENCE (SIZE (1..maxNrOfSCCPCHsLCRinExt)) OF Secondary-CCPCHItem-CTCH-ReconfRqstTDD
	-- Applicable to 1.28Mcps TDD only, used when more than maxNrOfSCCPCHs SCCPCHs are to be reconfigured.

PICH-Parameters-CTCH-ReconfRqstTDD	 ::= SEQUENCE {
	commonPhysicalChannelID				CommonPhysicalChannelID,
	pICH-Power							PICH-Power		OPTIONAL,
	iE-Extensions						ProtocolExtensionContainer  { { PICH-Parameters-CTCH-ReconfRqstTDD-ExtIEs} }		OPTIONAL,
	...
}

PICH-Parameters-CTCH-ReconfRqstTDD-ExtIEs NBAP-PROTOCOL-EXTENSION ::= {
	...
}

FACH-ParametersList-CTCH-ReconfRqstTDD ::= SEQUENCE (SIZE (0..maxNrOfFACHs)) OF FACH-ParametersItem-CTCH-ReconfRqstTDD

FACH-ParametersItem-CTCH-ReconfRqstTDD ::= SEQUENCE {
 	commonTransportChannelID		CommonTransportChannelID,
	toAWS							ToAWS			OPTIONAL,
 	toAWE							ToAWE			OPTIONAL,
	iE-Extensions					ProtocolExtensionContainer  { { FACH-ParametersItem-CTCH-ReconfRqstTDD-ExtIEs} }		OPTIONAL,
	...
}

FACH-ParametersItem-CTCH-ReconfRqstTDD-ExtIEs NBAP-PROTOCOL-EXTENSION ::= {
	{ ID	id-maxFACH-Power-LCR-CTCH-ReconfRqstTDD			CRITICALITY	reject		EXTENSION DL-Power		PRESENCE optional	}|
	--  Applicable to 1.28Mcps TDD only
	{ ID	id-TnlQos										CRITICALITY ignore		EXTENSION TnlQos		PRESENCE optional },
	...
}

PCH-Parameters-CTCH-ReconfRqstTDD ::= SEQUENCE {
	commonTransportChannelID		CommonTransportChannelID,
	toAWS							ToAWS			OPTIONAL,
	toAWE							ToAWE			OPTIONAL,
	iE-Extensions					ProtocolExtensionContainer  { { PCH-Parameters-CTCH-ReconfRqstTDD-ExtIEs} }		OPTIONAL,
	...
}

PCH-Parameters-CTCH-ReconfRqstTDD-ExtIEs NBAP-PROTOCOL-EXTENSION ::= {
	{ ID id-PCH-Power-LCR-CTCH-ReconfRqstTDD		CRITICALITY reject		EXTENSION DL-Power		PRESENCE optional }|
	-- Applicable to 1.28Mcps TDD only
	{ ID id-TnlQos									CRITICALITY ignore		EXTENSION TnlQos		PRESENCE optional },
	...
}

FPACH-LCR-Parameters-CTCH-ReconfRqstTDD ::= SEQUENCE {
	commonPhysicalChannelId			CommonPhysicalChannelID,
	fPACHPower						FPACH-Power		OPTIONAL,
	iE-Extensions					ProtocolExtensionContainer  { { FPACH-LCR-Parameters-CTCH-ReconfRqstTDD-ExtIEs} }		OPTIONAL,
	...
}

FPACH-LCR-Parameters-CTCH-ReconfRqstTDD-ExtIEs NBAP-PROTOCOL-EXTENSION ::= {
	...
}

MICH-Parameters-CTCH-ReconfRqstTDD ::= SEQUENCE {
	commonPhysicalChannelID				CommonPhysicalChannelID,
	mICH-Power							PICH-Power															OPTIONAL,
	iE-Extensions						ProtocolExtensionContainer  { { MICH-Parameters-CTCH-ReconfRqstTDD-ExtIEs} }		OPTIONAL,
	...
}

MICH-Parameters-CTCH-ReconfRqstTDD-ExtIEs NBAP-PROTOCOL-EXTENSION ::= {
	...
}

PLCCH-Parameters-CTCH-ReconfRqstTDD ::= SEQUENCE {
	maxPowerPLCCH						DL-Power,
	iE-Extensions						ProtocolExtensionContainer  { { PLCCH-Parameters-CTCH-ReconfRqstTDD-ExtIEs} }		OPTIONAL,
	...
}

PLCCH-Parameters-CTCH-ReconfRqstTDD-ExtIEs NBAP-PROTOCOL-EXTENSION ::= {
	...
}

Secondary-CCPCH-768-Parameters-CTCH-ReconfRqstTDD::= SEQUENCE {
	cCTrCH-ID						CCTrCH-ID,
	secondaryCCPCH768List			Secondary-CCPCH-768-List-CTCH-ReconfRqstTDD			OPTIONAL,
	iE-Extensions					ProtocolExtensionContainer  { { Secondary-CCPCH-768-CTCH-ReconfRqstTDD-ExtIEs} }		OPTIONAL,
	...
}

Secondary-CCPCH-768-CTCH-ReconfRqstTDD-ExtIEs NBAP-PROTOCOL-EXTENSION ::= {
	...
}

Secondary-CCPCH-768-List-CTCH-ReconfRqstTDD ::= SEQUENCE (SIZE (1..maxNrOfSCCPCHs768)) OF Secondary-CCPCH-768-Item-CTCH-ReconfRqstTDD

Secondary-CCPCH-768-Item-CTCH-ReconfRqstTDD ::= SEQUENCE {
	commonPhysicalChannelID768			CommonPhysicalChannelID768,
	sCCPCH-Power						DL-Power		OPTIONAL,
	iE-Extensions						ProtocolExtensionContainer  { { Secondary-CCPCH-768-Item-CTCH-ReconfRqstTDD-ExtIEs} }		OPTIONAL,
	...
}

Secondary-CCPCH-768-Item-CTCH-ReconfRqstTDD-ExtIEs NBAP-PROTOCOL-EXTENSION ::= {
	...
}

PICH-768-Parameters-CTCH-ReconfRqstTDD	 ::= SEQUENCE {
	commonPhysicalChannelID768			CommonPhysicalChannelID768,
	pICH-Power							PICH-Power		OPTIONAL,
	iE-Extensions						ProtocolExtensionContainer  { { PICH-768-Parameters-CTCH-ReconfRqstTDD-ExtIEs} }		OPTIONAL,
	...
}

PICH-768-Parameters-CTCH-ReconfRqstTDD-ExtIEs NBAP-PROTOCOL-EXTENSION ::= {
	...
}

MICH-768-Parameters-CTCH-ReconfRqstTDD ::= SEQUENCE {
	commonPhysicalChannelID768			CommonPhysicalChannelID768,
	mICH-Power							PICH-Power																OPTIONAL,
	iE-Extensions						ProtocolExtensionContainer  { { MICH-768-Parameters-CTCH-ReconfRqstTDD-ExtIEs} }		OPTIONAL,
	...
}

MICH-768-Parameters-CTCH-ReconfRqstTDD-ExtIEs NBAP-PROTOCOL-EXTENSION ::= {
	...
}


UPPCH-LCR-Parameters-CTCH-ReconfRqstTDD ::= SEQUENCE {
	uPPCHPositionLCR				UPPCHPositionLCR		OPTIONAL,
	uARFCN							UARFCN					OPTIONAL,
	-- Mandatory for 1.28Mcps TDD when using multiple frequencies Corresponds to Nt [15]
	iE-Extensions					ProtocolExtensionContainer { { UPPCH-LCR-Parameters-CTCH-ReconfRqstTDD-ExtIEs} }	
	OPTIONAL,
	...
}

UPPCH-LCR-Parameters-CTCH-ReconfRqstTDD-ExtIEs NBAP-PROTOCOL-EXTENSION ::= {
	...
}

-- **************************************************************
--
-- COMMON TRANSPORT CHANNEL RECONFIGURATION RESPONSE
--
-- **************************************************************

CommonTransportChannelReconfigurationResponse ::= SEQUENCE {
	protocolIEs				ProtocolIE-Container		{{CommonTransportChannelReconfigurationResponse-IEs}},
	protocolExtensions		ProtocolExtensionContainer	{{CommonTransportChannelReconfigurationResponse-Extensions}}		OPTIONAL,
	...
}

CommonTransportChannelReconfigurationResponse-IEs NBAP-PROTOCOL-IES ::= {	
	{ ID	id-CriticalityDiagnostics		CRITICALITY		ignore			TYPE	CriticalityDiagnostics		PRESENCE	optional},
	...
}

CommonTransportChannelReconfigurationResponse-Extensions NBAP-PROTOCOL-EXTENSION ::= {
	...
}

-- **************************************************************
--
-- COMMON TRANSPORT CHANNEL RECONFIGURATION FAILURE
--
-- **************************************************************

CommonTransportChannelReconfigurationFailure ::= SEQUENCE {
	protocolIEs				ProtocolIE-Container		{{CommonTransportChannelReconfigurationFailure-IEs}},
	protocolExtensions		ProtocolExtensionContainer	{{CommonTransportChannelReconfigurationFailure-Extensions}}          OPTIONAL,
	...
}

CommonTransportChannelReconfigurationFailure-IEs NBAP-PROTOCOL-IES ::= {
	{ ID	id-Cause						CRITICALITY	ignore			TYPE	Cause					PRESENCE	mandatory }|
	{ ID	id-CriticalityDiagnostics		CRITICALITY	ignore			TYPE	CriticalityDiagnostics		PRESENCE	optional	},
	...
}

CommonTransportChannelReconfigurationFailure-Extensions NBAP-PROTOCOL-EXTENSION ::= {
	...
}

-- **************************************************************
--
-- COMMON TRANSPORT CHANNEL DELETION REQUEST
--
-- **************************************************************

CommonTransportChannelDeletionRequest ::= SEQUENCE {
	protocolIEs					ProtocolIE-Container		{{CommonTransportChannelDeletionRequest-IEs}},
	protocolExtensions			ProtocolExtensionContainer	{{CommonTransportChannelDeletionRequest-Extensions}}        	OPTIONAL,
	...
}

CommonTransportChannelDeletionRequest-IEs NBAP-PROTOCOL-IES ::= {
	{ ID	id-C-ID								CRITICALITY	reject		TYPE C-ID					PRESENCE mandatory }|
	{ ID	id-CommonPhysicalChannelID			CRITICALITY	reject		TYPE CommonPhysicalChannelID	PRESENCE mandatory }|
	{ ID	id-ConfigurationGenerationID		CRITICALITY	reject		TYPE ConfigurationGenerationID	PRESENCE mandatory },
	...
}

CommonTransportChannelDeletionRequest-Extensions NBAP-PROTOCOL-EXTENSION ::= {
	{ ID id-CommonPhysicalChannelID768-CommonTrChDeletionReq	CRITICALITY reject	EXTENSION CommonPhysicalChannelID768	PRESENCE optional },
	...
}

-- **************************************************************
--
-- COMMON TRANSPORT CHANNEL DELETION RESPONSE
--
-- **************************************************************

CommonTransportChannelDeletionResponse ::= SEQUENCE {
	protocolIEs				ProtocolIE-Container		{{CommonTransportChannelDeletionResponse-IEs}},
	protocolExtensions		ProtocolExtensionContainer	{{CommonTransportChannelDeletionResponse-Extensions}}     		OPTIONAL,
	...
}

CommonTransportChannelDeletionResponse-IEs NBAP-PROTOCOL-IES ::= {
	{ ID	id-CriticalityDiagnostics		CRITICALITY		ignore		TYPE	CriticalityDiagnostics		PRESENCE	optional},
	...
}

CommonTransportChannelDeletionResponse-Extensions NBAP-PROTOCOL-EXTENSION ::= {
	...
}

-- **************************************************************
--
-- BLOCK RESOURCE REQUEST
--
-- **************************************************************

BlockResourceRequest ::= SEQUENCE {
	protocolIEs				ProtocolIE-Container       	{{BlockResourceRequest-IEs}},
	protocolExtensions		ProtocolExtensionContainer	{{BlockResourceRequest-Extensions}}                   OPTIONAL,
	...
}

BlockResourceRequest-IEs NBAP-PROTOCOL-IES ::= {
	{ ID id-C-ID							CRITICALITY reject		TYPE C-ID						PRESENCE mandatory	}|
	{ ID id-BlockingPriorityIndicator		CRITICALITY reject		TYPE BlockingPriorityIndicator	PRESENCE mandatory	}|
	{ ID id-ShutdownTimer					CRITICALITY reject		TYPE ShutdownTimer				PRESENCE conditional	},
	-- The IE shall be present if the Blocking Priority Indicator IE indicates "Normal Priority"--
	...
}

BlockResourceRequest-Extensions NBAP-PROTOCOL-EXTENSION ::= {
	...
}

-- **************************************************************
--
-- BLOCK RESOURCE RESPONSE
--
-- **************************************************************

BlockResourceResponse ::= SEQUENCE {
	protocolIEs					ProtocolIE-Container       	{{BlockResourceResponse-IEs}},
	protocolExtensions			ProtocolExtensionContainer	{{BlockResourceResponse-Extensions}}		OPTIONAL,
	...
}

BlockResourceResponse-IEs NBAP-PROTOCOL-IES ::= {
	{ ID id-CriticalityDiagnostics		CRITICALITY ignore		TYPE CriticalityDiagnostics		PRESENCE optional},
	...
}

BlockResourceResponse-Extensions NBAP-PROTOCOL-EXTENSION ::= {
	...
}

-- **************************************************************
--
-- BLOCK RESOURCE FAILURE
--
-- **************************************************************

BlockResourceFailure ::= SEQUENCE {
	protocolIEs				ProtocolIE-Container       	{{BlockResourceFailure-IEs}},
	protocolExtensions		ProtocolExtensionContainer	{{BlockResourceFailure-Extensions}}		OPTIONAL,
	...
}

BlockResourceFailure-IEs NBAP-PROTOCOL-IES ::= {
	{ ID id-Cause						CRITICALITY ignore		TYPE Cause							PRESENCE mandatory	}|
	{ ID id-CriticalityDiagnostics		CRITICALITY ignore		TYPE CriticalityDiagnostics 		PRESENCE optional		},
	...
}

BlockResourceFailure-Extensions NBAP-PROTOCOL-EXTENSION ::= {
	...
}

-- **************************************************************
--
-- UNBLOCK RESOURCE INDICATION
--
-- **************************************************************

UnblockResourceIndication ::= SEQUENCE {
	protocolIEs				ProtocolIE-Container		{{UnblockResourceIndication-IEs}},
	protocolExtensions		ProtocolExtensionContainer	{{UnblockResourceIndication-Extensions}}    OPTIONAL,
	...
}

UnblockResourceIndication-IEs NBAP-PROTOCOL-IES ::= {
	{ ID id-C-ID			CRITICALITY ignore		TYPE C-ID		PRESENCE mandatory },
	...
}

UnblockResourceIndication-Extensions NBAP-PROTOCOL-EXTENSION ::= {
	...
}

-- **************************************************************
--
-- AUDIT REQUIRED INDICATION
--
-- **************************************************************

AuditRequiredIndication ::= SEQUENCE {
	protocolIEs				ProtocolIE-Container		{{AuditRequiredIndication-IEs}},
	protocolExtensions 		ProtocolExtensionContainer	{{AuditRequiredIndication-Extensions}}    	OPTIONAL,
	...
}

AuditRequiredIndication-IEs NBAP-PROTOCOL-IES ::= {
	...
}

AuditRequiredIndication-Extensions NBAP-PROTOCOL-EXTENSION ::= {
	...
}

-- **************************************************************
--
-- AUDIT REQUEST
--
-- **************************************************************

AuditRequest ::= SEQUENCE {
	protocolIEs					ProtocolIE-Container		{{AuditRequest-IEs}},
	protocolExtensions			ProtocolExtensionContainer	{{AuditRequest-Extensions}}		OPTIONAL,
	...
}

AuditRequest-IEs NBAP-PROTOCOL-IES ::= {
	{ ID id-Start-Of-Audit-Sequence-Indicator		CRITICALITY reject	TYPE Start-Of-Audit-Sequence-Indicator	 	PRESENCE mandatory },
	...
}

AuditRequest-Extensions NBAP-PROTOCOL-EXTENSION ::= {
	...
}

-- **************************************************************
--
-- AUDIT RESPONSE
--
-- **************************************************************

AuditResponse ::= SEQUENCE {
	protocolIEs					ProtocolIE-Container		{{AuditResponse-IEs}},
	protocolExtensions			ProtocolExtensionContainer	{{AuditResponse-Extensions}}		OPTIONAL,
	...
}

AuditResponse-IEs NBAP-PROTOCOL-IES ::= {
	{ ID id-End-Of-Audit-Sequence-Indicator				CRITICALITY ignore	TYPE End-Of-Audit-Sequence-Indicator				PRESENCE mandatory }|
	{ ID id-Cell-InformationList-AuditRsp				CRITICALITY ignore	TYPE Cell-InformationList-AuditRsp				PRESENCE optional }|
	{ ID id-CCP-InformationList-AuditRsp				CRITICALITY ignore	TYPE CCP-InformationList-AuditRsp				PRESENCE optional }|
	-- CCP (Communication Control Port) --
	{ ID id-Local-Cell-InformationList-AuditRsp			CRITICALITY ignore	TYPE Local-Cell-InformationList-AuditRsp			PRESENCE optional }|
	{ ID id-Local-Cell-Group-InformationList-AuditRsp	CRITICALITY ignore	TYPE Local-Cell-Group-InformationList-AuditRsp	PRESENCE optional }|
	{ ID id-CriticalityDiagnostics						CRITICALITY ignore	TYPE CriticalityDiagnostics				PRESENCE optional },
	...
}

AuditResponse-Extensions NBAP-PROTOCOL-EXTENSION ::= {
	{ ID id-Power-Local-Cell-Group-InformationList-AuditRsp	CRITICALITY ignore	EXTENSION Power-Local-Cell-Group-InformationList-AuditRsp		PRESENCE optional },
	...
}

Cell-InformationList-AuditRsp ::= SEQUENCE (SIZE (1..maxCellinNodeB)) OF ProtocolIE-Single-Container {{ Cell-InformationItemIE-AuditRsp}}

Cell-InformationItemIE-AuditRsp NBAP-PROTOCOL-IES ::= {
	{ ID	id-Cell-InformationItem-AuditRsp		CRITICALITY ignore		TYPE Cell-InformationItem-AuditRsp			PRESENCE optional	}
}

Cell-InformationItem-AuditRsp ::= SEQUENCE {
	c-ID									C-ID,
	configurationGenerationID				ConfigurationGenerationID,
	resourceOperationalState				ResourceOperationalState,
	availabilityStatus						AvailabilityStatus,
	local-Cell-ID							Local-Cell-ID,
	primary-SCH-Information					P-SCH-Information-AuditRsp					OPTIONAL,
	secondary-SCH-Information				S-SCH-Information-AuditRsp					OPTIONAL,
	primary-CPICH-Information				P-CPICH-Information-AuditRsp				OPTIONAL,
	secondary-CPICH-InformationList			S-CPICH-InformationList-AuditRsp			OPTIONAL,
	primary-CCPCH-Information				P-CCPCH-Information-AuditRsp				OPTIONAL,
	bCH-Information							BCH-Information-AuditRsp					OPTIONAL,
	secondary-CCPCH-InformationList			S-CCPCH-InformationList-AuditRsp			OPTIONAL,
	pCH-Information							PCH-Information-AuditRsp					OPTIONAL,
	pICH-Information						PICH-Information-AuditRsp					OPTIONAL,
	fACH-InformationList					FACH-InformationList-AuditRsp				OPTIONAL,
	pRACH-InformationList					PRACH-InformationList-AuditRsp				OPTIONAL,
	rACH-InformationList					RACH-InformationList-AuditRsp				OPTIONAL,
	aICH-InformationList					AICH-InformationList-AuditRsp				OPTIONAL,
	notUsed-1-pCPCH-InformationList			NULL										OPTIONAL,
	notUsed-2-cPCH-InformationList			NULL										OPTIONAL,
	notUsed-3-aP-AICH-InformationList		NULL										OPTIONAL,
	notUsed-4-cDCA-ICH-InformationList		NULL										OPTIONAL,
	sCH-Information							SCH-Information-AuditRsp					OPTIONAL,
	iE-Extensions							ProtocolExtensionContainer  { { Cell-InformationItem-AuditRsp-ExtIEs} }		OPTIONAL,
	...
}

Cell-InformationItem-AuditRsp-ExtIEs NBAP-PROTOCOL-EXTENSION ::= {
	{ ID id-FPACH-LCR-InformationList-AuditRsp		CRITICALITY ignore	EXTENSION FPACH-LCR-InformationList-AuditRsp			PRESENCE optional }|
	-- Applicable to 1.28Mcps TDD only
	{ ID id-DwPCH-LCR-InformationList-AuditRsp		CRITICALITY ignore	EXTENSION Common-PhysicalChannel-Status-Information	PRESENCE optional }|
	-- Applicable to 1.28Mcps TDD only
	{ ID id-HSDSCH-Resources-Information-AuditRsp	CRITICALITY ignore	EXTENSION HS-DSCH-Resources-Information-AuditRsp		PRESENCE optional }|
	-- For 1.28Mcps TDD, this HS-DSCH Resource Information is for the first Frequency repetition, HS-DSCH Resource Information for Frequency repetitions 2 and on, should be defined in MultipleFreq-HS-DSCH-Resources-InformationList-AuditRsp.
	{ ID id-MICH-Information-AuditRsp				CRITICALITY ignore	EXTENSION Common-PhysicalChannel-Status-Information		PRESENCE optional }|
	{ ID id-S-CCPCH-InformationListExt-AuditRsp		CRITICALITY ignore	EXTENSION S-CCPCH-InformationListExt-AuditRsp				PRESENCE optional }|
	-- Applicable to 3.84Mcps TDD only, used when there are more than maxSCCPCHCell SCCPCHs in the cell.
	{ ID id-S-CCPCH-LCR-InformationListExt-AuditRsp	CRITICALITY ignore	EXTENSION S-CCPCH-LCR-InformationListExt-AuditRsp			PRESENCE optional }|
	-- Applicable to 1.28Mcps TDD only, used when there are more than maxSCCPCHCell SCCPCHs in the cell.
	{ ID id-E-DCH-Resources-Information-AuditRsp	CRITICALITY ignore	EXTENSION E-DCH-Resources-Information-AuditRsp				PRESENCE optional }|
	-- For 1.28Mcps TDD, this E-DCH Resource Information is for the first Frequency repetition, E-DCH Resource Information for Frequency repetitions 2 and on, should be defined in MultipleFreq-E-DCH-Resources-InformationList-AuditRsp.
	{ ID id-PLCCH-InformationList-AuditRsp			CRITICALITY ignore	EXTENSION PLCCH-InformationList-AuditRsp					PRESENCE optional }|
	{ ID id-P-CCPCH-768-Information-AuditRsp		CRITICALITY ignore	EXTENSION Common-PhysicalChannel-Status-Information768	PRESENCE optional }|
	{ ID id-S-CCPCH-768-InformationList-AuditRsp	CRITICALITY ignore	EXTENSION S-CCPCH-768-InformationList-AuditRsp				PRESENCE optional }|
	{ ID id-PICH-768-Information-AuditRsp			CRITICALITY ignore	EXTENSION Common-PhysicalChannel-Status-Information768	PRESENCE optional }|
	{ ID id-PRACH-768-InformationList-AuditRsp		CRITICALITY ignore	EXTENSION PRACH-768-InformationList-AuditRsp				PRESENCE optional }|
	{ ID id-SCH-768-Information-AuditRsp			CRITICALITY ignore	EXTENSION Common-PhysicalChannel-Status-Information768	PRESENCE optional }|
	{ ID id-MICH-768-Information-AuditRsp			CRITICALITY ignore	EXTENSION Common-PhysicalChannel-Status-Information768	PRESENCE optional }|
	{ ID id-E-RUCCH-InformationList-AuditRsp		CRITICALITY ignore	EXTENSION E-RUCCH-InformationList-AuditRsp					PRESENCE optional }|
	{ ID id-E-RUCCH-768-InformationList-AuditRsp	CRITICALITY ignore	EXTENSION E-RUCCH-768-InformationList-AuditRsp				PRESENCE optional }|
	{ ID id-Cell-Frequency-List-Information-LCR-MulFreq-AuditRsp	CRITICALITY ignore	EXTENSION  Cell-Frequency-List-Information-LCR-MulFreq-AuditRsp	 PRESENCE optional }| 	-- Applicable to 1.28Mcps TDD when using multiple frequencies
	{ ID id-UPPCH-LCR-InformationList-AuditRsp		CRITICALITY ignore		EXTENSION UPPCH-LCR-InformationList-AuditRsp		PRESENCE optional	}|
	  -- Applicable to 1.28Mcps TDD only
	{ ID id-multipleFreq-HS-DSCH-Resources-InformationList-AuditRsp	CRITICALITY ignore	EXTENSION MultipleFreq-HS-DSCH-Resources-InformationList-AuditRsp	PRESENCE optional }|
-- Applicable to 1.28Mcps TDD when using multiple frequencies.This HS-DSCH Resource Information is for the 2nd and beyond frequencies.
	{ ID id-MultipleFreq-E-DCH-Resources-InformationList-AuditRsp	CRITICALITY ignore	EXTENSION MultipleFreq-E-DCH-Resources-InformationList-AuditRsp	PRESENCE optional },
	-- Applicable to 1.28Mcps TDD when using multiple frequencies. This E-DCH Resource Information is for the 2nd and beyond frequencies.
	...
}

P-SCH-Information-AuditRsp ::= ProtocolIE-Single-Container {{ P-SCH-InformationIE-AuditRsp }}

P-SCH-InformationIE-AuditRsp NBAP-PROTOCOL-IES ::= {
	{ ID id-P-SCH-Information	CRITICALITY ignore	TYPE Common-PhysicalChannel-Status-Information 	PRESENCE	mandatory }
}

S-SCH-Information-AuditRsp ::= ProtocolIE-Single-Container {{ S-SCH-InformationIE-AuditRsp }}

S-SCH-InformationIE-AuditRsp NBAP-PROTOCOL-IES ::= {
	{ ID id-S-SCH-Information	CRITICALITY ignore	TYPE Common-PhysicalChannel-Status-Information 	PRESENCE	mandatory }
}

P-CPICH-Information-AuditRsp ::= ProtocolIE-Single-Container {{ P-CPICH-InformationIE-AuditRsp }}

P-CPICH-InformationIE-AuditRsp NBAP-PROTOCOL-IES ::= {
	{ ID id-P-CPICH-Information	CRITICALITY ignore	TYPE Common-PhysicalChannel-Status-Information 	PRESENCE	mandatory }
}

S-CPICH-InformationList-AuditRsp ::= SEQUENCE (SIZE (1..maxSCPICHCell)) OF ProtocolIE-Single-Container {{ S-CPICH-InformationItemIE-AuditRsp }}

S-CPICH-InformationItemIE-AuditRsp NBAP-PROTOCOL-IES ::= {
	{ ID id-S-CPICH-Information   CRITICALITY ignore	TYPE Common-PhysicalChannel-Status-Information		PRESENCE mandatory }
}

P-CCPCH-Information-AuditRsp ::= ProtocolIE-Single-Container {{ P-CCPCH-InformationIE-AuditRsp }}

P-CCPCH-InformationIE-AuditRsp NBAP-PROTOCOL-IES ::= {
	{ ID id-P-CCPCH-Information   CRITICALITY ignore	TYPE Common-PhysicalChannel-Status-Information		PRESENCE mandatory }
}

BCH-Information-AuditRsp ::= ProtocolIE-Single-Container {{ BCH-InformationIE-AuditRsp }}

BCH-InformationIE-AuditRsp NBAP-PROTOCOL-IES ::= {
	{ ID id-BCH-Information   CRITICALITY ignore	TYPE Common-TransportChannel-Status-Information		PRESENCE mandatory }
}

S-CCPCH-InformationList-AuditRsp ::= SEQUENCE (SIZE (1..maxSCCPCHCell)) OF ProtocolIE-Single-Container {{ S-CCPCH-InformationItemIE-AuditRsp }}

S-CCPCH-InformationItemIE-AuditRsp NBAP-PROTOCOL-IES ::= {
	{ ID id-S-CCPCH-Information   CRITICALITY ignore	TYPE Common-PhysicalChannel-Status-Information		PRESENCE mandatory }
}

PCH-Information-AuditRsp ::= ProtocolIE-Single-Container {{ PCH-InformationIE-AuditRsp }}

PCH-InformationIE-AuditRsp NBAP-PROTOCOL-IES ::= {
	{ ID id-PCH-Information   CRITICALITY ignore	TYPE Common-TransportChannel-Status-Information		PRESENCE mandatory }
}

PICH-Information-AuditRsp ::= ProtocolIE-Single-Container {{ PICH-InformationIE-AuditRsp }}

PICH-InformationIE-AuditRsp NBAP-PROTOCOL-IES ::= {
	{ ID id-PICH-Information   CRITICALITY ignore	TYPE Common-PhysicalChannel-Status-Information		PRESENCE mandatory }
}

FACH-InformationList-AuditRsp ::= SEQUENCE (SIZE (1..maxFACHCell)) OF ProtocolIE-Single-Container {{ FACH-InformationItemIE-AuditRsp }}

FACH-InformationItemIE-AuditRsp NBAP-PROTOCOL-IES ::= {
	{ ID id-FACH-Information   CRITICALITY ignore	TYPE Common-TransportChannel-Status-Information		PRESENCE mandatory }
}

PRACH-InformationList-AuditRsp ::= SEQUENCE (SIZE (1..maxPRACHCell)) OF ProtocolIE-Single-Container {{ PRACH-InformationItemIE-AuditRsp }}

PRACH-InformationItemIE-AuditRsp NBAP-PROTOCOL-IES ::= {
	{ ID id-PRACH-Information   CRITICALITY ignore	TYPE Common-PhysicalChannel-Status-Information		PRESENCE mandatory }
}

RACH-InformationList-AuditRsp ::= SEQUENCE (SIZE (1..maxRACHCell)) OF ProtocolIE-Single-Container {{ RACH-InformationItemIE-AuditRsp }}

RACH-InformationItemIE-AuditRsp NBAP-PROTOCOL-IES ::= {
	{ ID id-RACH-Information   CRITICALITY ignore	TYPE Common-TransportChannel-Status-Information		PRESENCE mandatory }
}

AICH-InformationList-AuditRsp ::= SEQUENCE (SIZE (1..maxPRACHCell)) OF ProtocolIE-Single-Container {{ AICH-InformationItemIE-AuditRsp }}

AICH-InformationItemIE-AuditRsp NBAP-PROTOCOL-IES ::= {
	{ ID id-AICH-Information   CRITICALITY ignore	TYPE Common-PhysicalChannel-Status-Information		PRESENCE mandatory }
}

SCH-Information-AuditRsp ::= ProtocolIE-Single-Container {{ SCH-InformationIE-AuditRsp }}

SCH-InformationIE-AuditRsp NBAP-PROTOCOL-IES ::= {
	{ ID id-SCH-Information   CRITICALITY ignore	TYPE Common-PhysicalChannel-Status-Information		PRESENCE mandatory }
}

FPACH-LCR-InformationList-AuditRsp ::= SEQUENCE (SIZE (1..maxFPACHCell)) OF ProtocolIE-Single-Container {{ FPACH-LCR-InformationItemIE-AuditRsp }}

FPACH-LCR-InformationItemIE-AuditRsp NBAP-PROTOCOL-IES ::= {
	{ ID id-FPACH-LCR-Information-AuditRsp   CRITICALITY ignore	TYPE Common-PhysicalChannel-Status-Information		PRESENCE mandatory }
}

HS-DSCH-Resources-Information-AuditRsp ::= SEQUENCE {
	resourceOperationalState			ResourceOperationalState,
	availabilityStatus					AvailabilityStatus,
	iE-Extensions						ProtocolExtensionContainer  {{ HS-DSCH-Resources-Information-AuditRsp-ExtIEs }}		OPTIONAL,
	...
}

HS-DSCH-Resources-Information-AuditRsp-ExtIEs NBAP-PROTOCOL-EXTENSION ::= {
	{ ID id-UARFCNforNt		CRITICALITY ignore		EXTENSION UARFCN		PRESENCE	optional },
	--  Applicable to 1.28Mcps TDD when using multiple frequencies.
	...
}

S-CCPCH-InformationListExt-AuditRsp ::= SEQUENCE (SIZE (1..maxSCCPCHCellinExt)) OF ProtocolIE-Single-Container {{ S-CCPCH-InformationItemIE-AuditRsp }}

S-CCPCH-LCR-InformationListExt-AuditRsp ::= SEQUENCE (SIZE (1..maxSCCPCHCellinExtLCR)) OF ProtocolIE-Single-Container {{ S-CCPCH-InformationItemIE-AuditRsp }}

E-DCH-Resources-Information-AuditRsp ::= SEQUENCE {
	resourceOperationalState			ResourceOperationalState,
	availabilityStatus					AvailabilityStatus,
	iE-Extensions						ProtocolExtensionContainer  {{ E-DCH-Resources-Information-AuditRsp-ExtIEs }}		OPTIONAL,
	...
}

E-DCH-Resources-Information-AuditRsp-ExtIEs NBAP-PROTOCOL-EXTENSION ::= {
	{ ID id-UARFCNforNt		CRITICALITY ignore		EXTENSION UARFCN		PRESENCE	optional },
	-- Applicable to 1.28Mcps TDD when using multiple frequencies.
	...
}

PLCCH-InformationList-AuditRsp ::= SEQUENCE (SIZE (1..maxPLCCHCell)) OF ProtocolIE-Single-Container {{ PLCCH-InformationItemIE-AuditRsp }}

PLCCH-InformationItemIE-AuditRsp NBAP-PROTOCOL-IES ::= {
	{ ID id-PLCCH-Information-AuditRsp   CRITICALITY ignore	TYPE Common-PhysicalChannel-Status-Information		PRESENCE mandatory }
}

S-CCPCH-768-InformationList-AuditRsp ::= SEQUENCE (SIZE (1..maxSCCPCHCell768)) OF ProtocolIE-Single-Container {{ S-CCPCH-768-InformationItemIE-AuditRsp }}

S-CCPCH-768-InformationItemIE-AuditRsp NBAP-PROTOCOL-IES ::= {
	{ ID id-S-CCPCH-768-Information-AuditRsp   CRITICALITY ignore	TYPE Common-PhysicalChannel-Status-Information768		PRESENCE mandatory }
}

PRACH-768-InformationList-AuditRsp ::= SEQUENCE (SIZE (1..maxPRACHCell)) OF ProtocolIE-Single-Container {{ PRACH-768-InformationItemIE-AuditRsp }}

PRACH-768-InformationItemIE-AuditRsp NBAP-PROTOCOL-IES ::= {
	{ ID id-PRACH-768-Information   CRITICALITY ignore	TYPE Common-PhysicalChannel-Status-Information768		PRESENCE mandatory }
}

E-RUCCH-InformationList-AuditRsp ::= SEQUENCE (SIZE (1..maxE-RUCCHCell)) OF ProtocolIE-Single-Container {{ E-RUCCH-InformationItemIE-AuditRsp }}

E-RUCCH-InformationItemIE-AuditRsp NBAP-PROTOCOL-IES ::= {
	{ ID id-E-RUCCH-Information   CRITICALITY ignore	TYPE Common-PhysicalChannel-Status-Information		PRESENCE mandatory }
}

E-RUCCH-768-InformationList-AuditRsp ::= SEQUENCE (SIZE (1..maxE-RUCCHCell)) OF ProtocolIE-Single-Container {{ E-RUCCH-768-InformationItemIE-AuditRsp }}

E-RUCCH-768-InformationItemIE-AuditRsp NBAP-PROTOCOL-IES ::= {
	{ ID id-E-RUCCH-768-Information   CRITICALITY ignore	TYPE Common-PhysicalChannel-Status-Information768		PRESENCE mandatory }
}

Cell-Frequency-List-Information-LCR-MulFreq-AuditRsp ::= SEQUENCE (SIZE (1..maxFrequencyinCell)) OF ProtocolIE-Single-Container {{ Cell-Frequency-List-InformationIE-LCR-MulFreq-AuditRsp }}

Cell-Frequency-List-InformationIE-LCR-MulFreq-AuditRsp NBAP-PROTOCOL-IES ::= {
	{ ID id-Cell-Frequency-List-InformationItem-LCR-MulFreq-AuditRsp	CRITICALITY ignore	TYPE Cell-Frequency-List-InformationItem-LCR-MulFreq-AuditRsp		PRESENCE mandatory }
}

Cell-Frequency-List-InformationItem-LCR-MulFreq-AuditRsp ::= SEQUENCE {
	uARFCN								UARFCN,
	resourceOperationalState			ResourceOperationalState,
	availabilityStatus					AvailabilityStatus,
	iE-Extensions						ProtocolExtensionContainer  {{ Cell-Frequency-List-InformationItem-LCR-MulFreq-AuditRsp-ExtIEs }}		OPTIONAL,
	...
}

Cell-Frequency-List-InformationItem-LCR-MulFreq-AuditRsp-ExtIEs NBAP-PROTOCOL-EXTENSION ::= {
	...
}

UPPCH-LCR-InformationList-AuditRsp ::= SEQUENCE (SIZE (1..maxFrequencyinCell)) OF ProtocolIE-Single-Container {{ UPPCH-LCR-InformationIE-AuditRsp }}

UPPCH-LCR-InformationIE-AuditRsp NBAP-PROTOCOL-IES ::= {
	{ ID id-UPPCH-LCR-InformationItem-AuditRsp   CRITICALITY ignore	TYPE UPPCH-LCR-InformationItem-AuditRsp		PRESENCE mandatory }
}

UPPCH-LCR-InformationItem-AuditRsp ::= SEQUENCE {
	uARFCN								UARFCN				OPTIONAL,
	uPPCHPositionLCR					UPPCHPositionLCR, 
	resourceOperationalState			ResourceOperationalState,
	availabilityStatus					AvailabilityStatus,
	iE-Extensions						ProtocolExtensionContainer {{ UPPCH-LCR-InformationItem-AuditRsp-ExtIEs }}		OPTIONAL,
	...
}

UPPCH-LCR-InformationItem-AuditRsp-ExtIEs NBAP-PROTOCOL-EXTENSION ::= {
	...
}

MultipleFreq-HS-DSCH-Resources-InformationList-AuditRsp ::= SEQUENCE (SIZE (1..maxFrequencyinCell-1)) OF ProtocolIE-Single-Container {{ MultipleFreq-HS-DSCH-Resources-InformationItem-AuditRsp}} 
--Includes the 2nd through the max number of frequencies information repetitions.

MultipleFreq-HS-DSCH-Resources-InformationItem-AuditRsp NBAP-PROTOCOL-IES ::= {
	{ ID id-HSDSCH-Resources-Information-AuditRsp	CRITICALITY ignore	TYPE HS-DSCH-Resources-Information-AuditRsp		PRESENCE mandatory }
}


MultipleFreq-E-DCH-Resources-InformationList-AuditRsp ::= SEQUENCE (SIZE (1..maxFrequencyinCell-1)) OF ProtocolIE-Single-Container {{ MultipleFreq-E-DCH-Resources-InformationItem-AuditRsp}} 
	-- Includes the 2nd through the max number of frequencies information repetitions.

MultipleFreq-E-DCH-Resources-InformationItem-AuditRsp NBAP-PROTOCOL-IES ::= {
	{ ID id-E-DCH-Resources-Information-AuditRsp	CRITICALITY ignore	TYPE E-DCH-Resources-Information-AuditRsp		PRESENCE mandatory }
}

CCP-InformationList-AuditRsp ::= SEQUENCE (SIZE (1..maxCCPinNodeB)) OF ProtocolIE-Single-Container {{ CCP-InformationItemIE-AuditRsp }}

CCP-InformationItemIE-AuditRsp NBAP-PROTOCOL-IES ::= {
	{ ID id-CCP-InformationItem-AuditRsp			CRITICALITY ignore			TYPE CCP-InformationItem-AuditRsp			PRESENCE mandatory }
}

CCP-InformationItem-AuditRsp ::= SEQUENCE {
	communicationControlPortID			CommunicationControlPortID,
	resourceOperationalState			ResourceOperationalState,
	availabilityStatus					AvailabilityStatus,
	iE-Extensions						ProtocolExtensionContainer  {{ CCP-InformationItem-AuditRsp-ExtIEs }}		OPTIONAL,
	...
}

CCP-InformationItem-AuditRsp-ExtIEs NBAP-PROTOCOL-EXTENSION ::= {
	...
}

Local-Cell-InformationList-AuditRsp	 ::=SEQUENCE (SIZE (1..maxLocalCellinNodeB)) OF ProtocolIE-Single-Container {{ Local-Cell-InformationItemIE-AuditRsp }}

Local-Cell-InformationItemIE-AuditRsp NBAP-PROTOCOL-IES ::= {
	{ ID id-Local-Cell-InformationItem-AuditRsp		CRITICALITY ignore	TYPE Local-Cell-InformationItem-AuditRsp	PRESENCE	mandatory}
}

Local-Cell-InformationItem-AuditRsp ::= SEQUENCE {
	local-Cell-ID								Local-Cell-ID,
	dl-or-global-capacityCredit					DL-or-Global-CapacityCredit,
	ul-capacityCredit							UL-CapacityCredit													OPTIONAL,
	commonChannelsCapacityConsumptionLaw 		CommonChannelsCapacityConsumptionLaw,
	dedicatedChannelsCapacityConsumptionLaw 	DedicatedChannelsCapacityConsumptionLaw,
	maximumDL-PowerCapability					MaximumDL-PowerCapability											OPTIONAL,
	minSpreadingFactor							MinSpreadingFactor													OPTIONAL,
	minimumDL-PowerCapability					MinimumDL-PowerCapability											OPTIONAL,
	local-Cell-Group-ID							Local-Cell-ID														OPTIONAL,
	iE-Extensions								ProtocolExtensionContainer  {{ Local-Cell-InformationItem-AuditRsp-ExtIEs}}		OPTIONAL,
	...
}

Local-Cell-InformationItem-AuditRsp-ExtIEs NBAP-PROTOCOL-EXTENSION ::= {
	{ ID id-ReferenceClockAvailability			CRITICALITY ignore			EXTENSION ReferenceClockAvailability			PRESENCE	optional }|
	{ ID id-Power-Local-Cell-Group-ID			CRITICALITY ignore			EXTENSION Local-Cell-ID			PRESENCE	optional }|
	{ ID id-HSDPA-Capability					CRITICALITY ignore			EXTENSION HSDPA-Capability			PRESENCE	optional }|
	{ ID id-E-DCH-Capability					CRITICALITY ignore			EXTENSION E-DCH-Capability			PRESENCE	optional }|
	{ ID id-E-DCH-TTI2ms-Capability				CRITICALITY ignore			EXTENSION E-DCH-TTI2ms-Capability			PRESENCE	conditional }|
	-- The IE shall be present if E-DCH Capability IE is set to ”E-DCH Capable”.
	{ ID id-E-DCH-SF-Capability					CRITICALITY ignore			EXTENSION E-DCH-SF-Capability			PRESENCE	conditional }|
	-- The IE shall be present if E-DCH Capability IE is set to ”E-DCH Capable”.
	{ ID id-E-DCH-HARQ-Combining-Capability		CRITICALITY ignore			EXTENSION E-DCH-HARQ-Combining-Capability		PRESENCE	conditional }|
	-- The IE shall be present if E-DCH Capability IE is set to ”E-DCH Capable”.
	{ ID id-E-DCH-CapacityConsumptionLaw		CRITICALITY ignore			EXTENSION E-DCHCapacityConsumptionLaw			PRESENCE	optional }|
	{ ID id-F-DPCH-Capability					CRITICALITY ignore			EXTENSION F-DPCH-Capability			PRESENCE	optional }|
	{ ID id-E-DCH-TDD-CapacityConsumptionLaw	CRITICALITY ignore			EXTENSION E-DCH-TDD-CapacityConsumptionLaw		PRESENCE	optional }|
	{ ID id-ContinuousPacketConnectivityDTX-DRX-Capability			CRITICALITY ignore			EXTENSION ContinuousPacketConnectivityDTX-DRX-Capability			PRESENCE	optional }|
	{ ID id-Max-UE-DTX-Cycle					CRITICALITY ignore			EXTENSION Max-UE-DTX-Cycle			PRESENCE	conditional }|
	-- The IE shall be present if Continuous Packet Connectivity DTX-DRX Capability IE is present and set to ”Continuous Packet Connectivity DTX-DRX Capable”.
	{ ID id-ContinuousPacketConnectivityHS-SCCH-less-Capability		CRITICALITY ignore			EXTENSION ContinuousPacketConnectivityHS-SCCH-less-Capability			PRESENCE	optional }|
	{ ID id-MIMO-Capability						CRITICALITY ignore			EXTENSION MIMO-Capability			PRESENCE	optional }|
	{ ID id-SixtyfourQAM-DL-Capability			CRITICALITY ignore			EXTENSION SixtyfourQAM-DL-Capability			PRESENCE	optional }|
	{ ID id-MBMS-Capability						CRITICALITY ignore			EXTENSION MBMS-Capability			PRESENCE	optional }|
	{ ID id-Enhanced-FACH-Capability			CRITICALITY ignore			EXTENSION Enhanced-FACH-Capability			PRESENCE	optional }|
	{ ID id-Enhanced-PCH-Capability				CRITICALITY ignore			EXTENSION Enhanced-PCH-Capability			PRESENCE	conditional }|
	-- The IE shall be present if Enhanced FACH Capability IE is set to ”Enhanced FACH Capable”.
	{ ID id-SixteenQAM-UL-Capability			CRITICALITY ignore			EXTENSION SixteenQAM-UL-Capability			PRESENCE	optional }|
	{ ID id-HSDSCH-MACdPDU-SizeCapability		CRITICALITY ignore			EXTENSION HSDSCH-MACdPDU-SizeCapability			PRESENCE	optional }|
	{ ID id-MBSFN-Only-Mode-Capability			CRITICALITY ignore			EXTENSION MBSFN-Only-Mode-Capability			PRESENCE	optional }|
	{ ID id-F-DPCH-SlotFormatCapability			CRITICALITY ignore			EXTENSION F-DPCH-SlotFormatCapability			PRESENCE	optional }|
	{ ID id-E-DCH-MACdPDU-SizeCapability		CRITICALITY ignore			EXTENSION E-DCH-MACdPDU-SizeCapability			PRESENCE	optional }|
	{ ID id-Common-EDCH-Capability				CRITICALITY ignore			EXTENSION Common-EDCH-Capability			PRESENCE	optional }|
	{ ID id-E-AI-Capability					CRITICALITY ignore			EXTENSION E-AI-Capability			PRESENCE	optional }|
	-- The IE shall be present if Common E-DCH Capability IE is present and set to ”Common E-DCH Capable”.
	{ ID id-Enhanced-UE-DRX-Capability				CRITICALITY ignore			EXTENSION Enhanced-UE-DRX-Capability			PRESENCE	optional }|
	-- The IE shall be present if Common E-DCH Capability IE is present and set to ”Common E-DCH Capable”.
	{ ID id-Enhanced-UE-DRX-CapabilityLCR		CRITICALITY ignore			EXTENSION Enhanced-UE-DRX-Capability			PRESENCE	optional }|
	{ ID id-E-DPCCH-Power-Boosting-Capability	CRITICALITY ignore			EXTENSION E-DPCCH-Power-Boosting-Capability	PRESENCE	optional }|
	{ ID id-SixtyfourQAM-DL-MIMO-Combined-Capability	CRITICALITY ignore	EXTENSION SixtyfourQAM-DL-MIMO-Combined-Capability						PRESENCE	conditional }|
	{ ID id-Multi-Cell-Capability-Info			CRITICALITY ignore			EXTENSION Multi-Cell-Capability-Info			PRESENCE	optional },
	...
}

Local-Cell-Group-InformationList-AuditRsp	 ::= SEQUENCE (SIZE (1..maxLocalCellinNodeB)) OF ProtocolIE-Single-Container {{ Local-Cell-Group-InformationItemIE-AuditRsp }}

Local-Cell-Group-InformationItemIE-AuditRsp NBAP-PROTOCOL-IES ::= {
	{ ID id-Local-Cell-Group-InformationItem-AuditRsp	CRITICALITY ignore	TYPE Local-Cell-Group-InformationItem-AuditRsp	PRESENCE mandatory}
}

Local-Cell-Group-InformationItem-AuditRsp ::= SEQUENCE {
	local-Cell-Group-ID							Local-Cell-ID,
	dl-or-global-capacityCredit					DL-or-Global-CapacityCredit,
	ul-capacityCredit							UL-CapacityCredit						OPTIONAL,
	commonChannelsCapacityConsumptionLaw 		CommonChannelsCapacityConsumptionLaw,
	dedicatedChannelsCapacityConsumptionLaw 	DedicatedChannelsCapacityConsumptionLaw,
	iE-Extensions								ProtocolExtensionContainer  {{ Local-Cell-Group-InformationItem-AuditRsp-ExtIEs}}		OPTIONAL,
	...
}

Local-Cell-Group-InformationItem-AuditRsp-ExtIEs NBAP-PROTOCOL-EXTENSION ::= {
	{ ID id-E-DCH-CapacityConsumptionLaw		CRITICALITY ignore			EXTENSION E-DCHCapacityConsumptionLaw			PRESENCE	optional }|
	{ ID id-E-DCH-TDD-CapacityConsumptionLaw	CRITICALITY ignore			EXTENSION E-DCH-TDD-CapacityConsumptionLaw		PRESENCE	optional },
	...
}

Power-Local-Cell-Group-InformationList-AuditRsp	 ::= SEQUENCE (SIZE (1..maxLocalCellinNodeB)) OF ProtocolIE-Single-Container {{ Power-Local-Cell-Group-InformationItemIE-AuditRsp }}

Power-Local-Cell-Group-InformationItemIE-AuditRsp NBAP-PROTOCOL-IES ::= {
	{ ID	id-Power-Local-Cell-Group-InformationItem-AuditRsp			CRITICALITY		ignore			TYPE	Power-Local-Cell-Group-InformationItem-AuditRsp		PRESENCE	mandatory}
}

Power-Local-Cell-Group-InformationItem-AuditRsp ::= SEQUENCE {
	power-Local-Cell-Group-ID					Local-Cell-ID,
	maximumDL-PowerCapability					MaximumDL-PowerCapability,
	iE-Extensions								ProtocolExtensionContainer  {{ Power-Local-Cell-Group-InformationItem-AuditRsp-ExtIEs}}		OPTIONAL,
	...
}

Power-Local-Cell-Group-InformationItem-AuditRsp-ExtIEs NBAP-PROTOCOL-EXTENSION ::= {
	...
}


-- **************************************************************
--
-- AUDIT FAILURE
--
-- **************************************************************

AuditFailure ::= SEQUENCE {
	protocolIEs				ProtocolIE-Container		{{AuditFailure-IEs}},
	protocolExtensions		ProtocolExtensionContainer	{{AuditFailure-Extensions}}			OPTIONAL,
	...
}

AuditFailure-IEs NBAP-PROTOCOL-IES ::= {
	{ ID id-Cause							CRITICALITY ignore			TYPE Cause						PRESENCE mandatory	}|
	{ ID id-CriticalityDiagnostics			CRITICALITY ignore			TYPE CriticalityDiagnostics		PRESENCE optional		},
	...
}

AuditFailure-Extensions NBAP-PROTOCOL-EXTENSION ::= {
	...
}

-- **************************************************************
--
-- COMMON MEASUREMENT INITIATION REQUEST
--
-- **************************************************************

CommonMeasurementInitiationRequest ::= SEQUENCE {
	protocolIEs				ProtocolIE-Container		{{CommonMeasurementInitiationRequest-IEs}},
	protocolExtensions		ProtocolExtensionContainer	{{CommonMeasurementInitiationRequest-Extensions}}		OPTIONAL,
	...
}

CommonMeasurementInitiationRequest-IEs NBAP-PROTOCOL-IES ::= {
	{ ID id-MeasurementID							CRITICALITY reject	TYPE MeasurementID				PRESENCE mandatory }|
	{ ID id-CommonMeasurementObjectType-CM-Rqst		CRITICALITY reject	TYPE CommonMeasurementObjectType-CM-Rqst		PRESENCE mandatory }|
	{ ID id-CommonMeasurementType					CRITICALITY reject	TYPE CommonMeasurementType		PRESENCE mandatory }|
	{ ID id-MeasurementFilterCoefficient			CRITICALITY reject	TYPE MeasurementFilterCoefficient		PRESENCE optional }|
	{ ID id-ReportCharacteristics					CRITICALITY reject	TYPE ReportCharacteristics		PRESENCE mandatory }|
	{ ID id-SFNReportingIndicator					CRITICALITY reject	TYPE FNReportingIndicator		PRESENCE mandatory }|
	{ ID id-SFN										CRITICALITY reject	TYPE SFN						PRESENCE optional },
	...
}

CommonMeasurementInitiationRequest-Extensions NBAP-PROTOCOL-EXTENSION ::= {
	{ ID id-CommonMeasurementAccuracy						CRITICALITY reject		EXTENSION CommonMeasurementAccuracy		PRESENCE optional}|
	{ ID id-MeasurementRecoveryBehavior						CRITICALITY ignore		EXTENSION MeasurementRecoveryBehavior		PRESENCE optional	}|
	{ ID id-RTWP-ReportingIndicator							CRITICALITY reject		EXTENSION RTWP-ReportingIndicator										PRESENCE optional}|
	{ ID id-RTWP-CellPortion-ReportingIndicator				CRITICALITY reject		EXTENSION RTWP-CellPortion-ReportingIndicator							PRESENCE optional}|
	{ ID id-Reference-ReceivedTotalWideBandPowerReporting	CRITICALITY ignore		EXTENSION Reference-ReceivedTotalWideBandPowerReporting			PRESENCE optional}|
	{ ID id-GANSS-Time-ID									CRITICALITY ignore		EXTENSION GANSS-Time-ID						PRESENCE optional},
	...
}

CommonMeasurementObjectType-CM-Rqst ::= CHOICE {
	cell							Cell-CM-Rqst,
	rACH							RACH-CM-Rqst,
	notUsed-cPCH					NULL,
	...,
	extension-CommonMeasurementObjectType-CM-Rqst		Extension-CommonMeasurementObjectType-CM-Rqst
}

Extension-CommonMeasurementObjectType-CM-Rqst	::= ProtocolIE-Single-Container {{ Extension-CommonMeasurementObjectType-CM-RqstIE }}

Extension-CommonMeasurementObjectType-CM-RqstIE NBAP-PROTOCOL-IES ::= {
	{ ID id-Power-Local-Cell-Group-choice-CM-Rqst	CRITICALITY reject	TYPE PowerLocalCellGroup-CM-Rqst	PRESENCE mandatory }|
	{ ID id-ERACH-CM-Rqst							CRITICALITY ignore	TYPE ERACH-CM-Rqst			PRESENCE mandatory}
		-- FDD only
}

ERACH-CM-Rqst ::= SEQUENCE {
	c-ID							C-ID,
	iE-Extensions					ProtocolExtensionContainer  { { ERACHItem-CM-Rqst-ExtIEs} } OPTIONAL,
	...
}


ERACHItem-CM-Rqst-ExtIEs NBAP-PROTOCOL-EXTENSION ::= {
	...
}

Cell-CM-Rqst ::= SEQUENCE {
	c-ID							C-ID,
	timeSlot						TimeSlot	OPTIONAL, 	-- Applicable to 3.84Mcps TDD and 7.68Mcps TDD only
	iE-Extensions					ProtocolExtensionContainer  { { CellItem-CM-Rqst-ExtIEs} }		OPTIONAL,
	...
}

CellItem-CM-Rqst-ExtIEs NBAP-PROTOCOL-EXTENSION ::= {
	{ ID id-TimeSlotLCR-CM-Rqst						CRITICALITY reject	EXTENSION TimeSlotLCR				PRESENCE optional }|
	-- Applicable to 1.28Mcps TDD only
	{ID id-NeighbouringCellMeasurementInformation	CRITICALITY ignore	EXTENSION NeighbouringCellMeasurementInformation	PRESENCE optional }|
	{ID id-UARFCNforNt								CRITICALITY reject	EXTENSION UARFCN					PRESENCE optional }|
	-- Mandatory for 1.28Mcps TDD when using multiple frequencies and the requested common measurementype is the one except for "HS-DSCH Required Power" or "HS-DSCH Provided Bit Rate"
	{ID id-UPPCHPositionLCR							CRITICALITY reject	EXTENSION UPPCHPositionLCR			PRESENCE optional }|
	-- Applicable to 1.28Mcps TDD only
	{ID id-AdditionalTimeSlotListLCR				CRITICALITY ignore	EXTENSION AdditionalTimeSlotListLCR			PRESENCE optional },
	-- Applicable to 1.28Mcps TDD only
	...
}

RACH-CM-Rqst ::= SEQUENCE {
	c-ID							C-ID,
	commonTransportChannelID		CommonTransportChannelID,
	iE-Extensions					ProtocolExtensionContainer  { { RACHItem-CM-Rqst-ExtIEs} }		OPTIONAL,
	...
}

RACHItem-CM-Rqst-ExtIEs NBAP-PROTOCOL-EXTENSION ::= {
	...
}

PowerLocalCellGroup-CM-Rqst ::= SEQUENCE {
	powerLocalCellGroupID			Local-Cell-ID,
	iE-Extensions					ProtocolExtensionContainer {{ PowerLocalCellGroup-CM-Rqst-ExtIEs }}	OPTIONAL,
	...
}

PowerLocalCellGroup-CM-Rqst-ExtIEs NBAP-PROTOCOL-EXTENSION ::= {
	...
}

-- **************************************************************
--
-- COMMON MEASUREMENT INITIATION RESPONSE
--
-- **************************************************************

CommonMeasurementInitiationResponse ::= SEQUENCE {
	protocolIEs				ProtocolIE-Container		{{CommonMeasurementInitiationResponse-IEs}},
	protocolExtensions		ProtocolExtensionContainer	{{CommonMeasurementInitiationResponse-Extensions}}		OPTIONAL,
	...
}

CommonMeasurementInitiationResponse-IEs NBAP-PROTOCOL-IES ::= {
	{ ID id-MeasurementID							CRITICALITY ignore		TYPE MeasurementID			PRESENCE	mandatory	}|
	{ ID id-CommonMeasurementObjectType-CM-Rsp		CRITICALITY ignore		TYPE CommonMeasurementObjectType-CM-Rsp		PRESENCE	optional	}|
	{ ID id-SFN										CRITICALITY ignore		TYPE SFN					PRESENCE	optional	}|
	{ ID id-CriticalityDiagnostics					CRITICALITY ignore		TYPE CriticalityDiagnostics		PRESENCE	optional	},
	...
}

CommonMeasurementInitiationResponse-Extensions NBAP-PROTOCOL-EXTENSION ::= {
	{ ID id-CommonMeasurementAccuracy				CRITICALITY ignore		EXTENSION CommonMeasurementAccuracy				PRESENCE optional }|
	{ ID id-MeasurementRecoverySupportIndicator		CRITICALITY ignore		EXTENSION MeasurementRecoverySupportIndicator		PRESENCE optional }|
	{ ID id-Reference-ReceivedTotalWideBandPowerSupportIndicator				CRITICALITY ignore							EXTENSION	Reference-ReceivedTotalWideBandPowerSupportIndicator		PRESENCE optional }|
	{ ID id-Reference-ReceivedTotalWideBandPower								CRITICALITY ignore		EXTENSION	Reference-ReceivedTotalWideBandPower						PRESENCE optional },
	...
}

CommonMeasurementObjectType-CM-Rsp ::= CHOICE {
	cell												Cell-CM-Rsp,
	rACH												RACH-CM-Rsp,
	notUsed-cPCH										NULL,
	...,
	extension-CommonMeasurementObjectType-CM-Rsp		Extension-CommonMeasurementObjectType-CM-Rsp
}

Extension-CommonMeasurementObjectType-CM-Rsp ::= ProtocolIE-Single-Container {{ Extension-CommonMeasurementObjectType-CM-RspIE }}

Extension-CommonMeasurementObjectType-CM-RspIE NBAP-PROTOCOL-IES ::= {
	{ ID id-Power-Local-Cell-Group-choice-CM-Rsp	CRITICALITY ignore		TYPE PowerLocalCellGroup-CM-Rsp	PRESENCE mandatory }|
	{ ID id-ERACH-CM-Rsp							CRITICALITY	ignore		TYPE ERACH-CM-Rsp		PRESENCE mandatory }
		-- FDD only
}

ERACH-CM-Rsp ::= SEQUENCE {
	commonMeasurementValue			CommonMeasurementValue,
	iE-Extensions					ProtocolExtensionContainer  { { ERACHItem-CM-Rsp-ExtIEs} } OPTIONAL,
	...
}


ERACHItem-CM-Rsp-ExtIEs NBAP-PROTOCOL-EXTENSION ::= {
	...
}

Cell-CM-Rsp ::= SEQUENCE {
	commonMeasurementValue			CommonMeasurementValue,
	iE-Extensions					ProtocolExtensionContainer  { { CellItem-CM-Rsp-ExtIEs} }		OPTIONAL,
	...
}

CellItem-CM-Rsp-ExtIEs NBAP-PROTOCOL-EXTENSION ::= {
	{ID id-AdditionalMeasurementValueList 		CRITICALITY ignore	EXTENSION AdditionalMeasurementValueList 	PRESENCE optional },
	...
}

RACH-CM-Rsp ::= SEQUENCE {
	commonMeasurementValue			CommonMeasurementValue,
	iE-Extensions					ProtocolExtensionContainer  { { RACHItem-CM-Rsp-ExtIEs} }		OPTIONAL,
	...
}

RACHItem-CM-Rsp-ExtIEs NBAP-PROTOCOL-EXTENSION ::= {
	...
}

PowerLocalCellGroup-CM-Rsp ::= SEQUENCE {
	commonMeasurementValue			CommonMeasurementValue,
	iE-Extensions					ProtocolExtensionContainer {{ PowerLocalCellGroup-CM-Rsp-ExtIEs}}		OPTIONAL,
	...
}

PowerLocalCellGroup-CM-Rsp-ExtIEs NBAP-PROTOCOL-EXTENSION ::= {
	...
}

-- **************************************************************
--
-- COMMON MEASUREMENT INITIATION FAILURE
--
-- **************************************************************

CommonMeasurementInitiationFailure ::= SEQUENCE {
	protocolIEs				ProtocolIE-Container		{{CommonMeasurementInitiationFailure-IEs}},
	protocolExtensions		ProtocolExtensionContainer	{{CommonMeasurementInitiationFailure-Extensions}}		OPTIONAL,
	...
}

CommonMeasurementInitiationFailure-IEs NBAP-PROTOCOL-IES ::= {
	{ ID id-MeasurementID				CRITICALITY ignore			TYPE MeasurementID				PRESENCE	mandatory	}|
	{ ID id-Cause						CRITICALITY ignore			TYPE Cause						PRESENCE	mandatory	}|
	{ ID id-CriticalityDiagnostics		CRITICALITY ignore			TYPE CriticalityDiagnostics		PRESENCE	optional	},
	...
}

CommonMeasurementInitiationFailure-Extensions NBAP-PROTOCOL-EXTENSION ::= {
	...
}

-- **************************************************************
--
-- COMMON MEASUREMENT REPORT
--
-- **************************************************************

CommonMeasurementReport ::= SEQUENCE {
	protocolIEs				ProtocolIE-Container		{{CommonMeasurementReport-IEs}},
	protocolExtensions		ProtocolExtensionContainer	{{CommonMeasurementReport-Extensions}}		OPTIONAL,
	...
}

CommonMeasurementReport-IEs NBAP-PROTOCOL-IES ::= {
	{ ID id-MeasurementID							CRITICALITY ignore		TYPE MeasurementID				PRESENCE	mandatory	}|
	{ ID id-CommonMeasurementObjectType-CM-Rprt		CRITICALITY ignore		TYPE CommonMeasurementObjectType-CM-Rprt		PRESENCE	mandatory	}|
	{ ID id-SFN										CRITICALITY ignore		TYPE SFN						PRESENCE	optional	},
	...
}

CommonMeasurementReport-Extensions NBAP-PROTOCOL-EXTENSION ::= {
	{ ID id-MeasurementRecoveryReportingIndicator	CRITICALITY ignore		EXTENSION MeasurementRecoveryReportingIndicator		PRESENCE optional }|
	{ ID id-Reference-ReceivedTotalWideBandPower	CRITICALITY ignore		EXTENSION Reference-ReceivedTotalWideBandPower		PRESENCE optional },
	...
}

CommonMeasurementObjectType-CM-Rprt ::= CHOICE {
	cell												Cell-CM-Rprt,
	rACH												RACH-CM-Rprt,
	notUsed-cPCH										NULL,
	...,
	extension-CommonMeasurementObjectType-CM-Rprt		Extension-CommonMeasurementObjectType-CM-Rprt
}

Extension-CommonMeasurementObjectType-CM-Rprt ::= ProtocolIE-Single-Container {{ Extension-CommonMeasurementObjectType-CM-RprtIE }}

Extension-CommonMeasurementObjectType-CM-RprtIE NBAP-PROTOCOL-IES ::= {
	{ ID id-Power-Local-Cell-Group-choice-CM-Rprt	CRITICALITY ignore		TYPE PowerLocalCellGroup-CM-Rprt	PRESENCE mandatory }|
	{ ID id-ERACH-CM-Rprt							CRITICALITY ignore		TYPE ERACH-CM-Rprt		PRESENCE mandatory },
	...
}

ERACH-CM-Rprt ::= SEQUENCE {
	commonMeasurementValueInformation	CommonMeasurementValueInformation,
	iE-Extensions						ProtocolExtensionContainer {{ ERACHItem-CM-Rprt-ExtIEs }} OPTIONAL,
	...
}

ERACHItem-CM-Rprt-ExtIEs NBAP-PROTOCOL-EXTENSION ::= {
	...
}

Cell-CM-Rprt ::= SEQUENCE {
	commonMeasurementValueInformation	CommonMeasurementValueInformation,
	iE-Extensions						ProtocolExtensionContainer  {{ CellItem-CM-Rprt-ExtIEs }}		OPTIONAL,
	...
}

CellItem-CM-Rprt-ExtIEs NBAP-PROTOCOL-EXTENSION ::= {
	{ID id-C-ID								CRITICALITY ignore		EXTENSION C-ID				PRESENCE optional}|
	{ID id-AdditionalMeasurementValueList 	CRITICALITY ignore		EXTENSION AdditionalMeasurementValueList	PRESENCE optional },
	...
}


RACH-CM-Rprt ::= SEQUENCE {
	commonMeasurementValueInformation	CommonMeasurementValueInformation,
	iE-Extensions						ProtocolExtensionContainer {{ RACHItem-CM-Rprt-ExtIEs }}			OPTIONAL,
	...
}

RACHItem-CM-Rprt-ExtIEs NBAP-PROTOCOL-EXTENSION ::= {
	{ID id-C-ID			CRITICALITY ignore			EXTENSION C-ID				PRESENCE optional},
	...
}

PowerLocalCellGroup-CM-Rprt ::= SEQUENCE {
	commonMeasurementValueInformation	CommonMeasurementValueInformation,
	iE-Extensions						ProtocolExtensionContainer {{ PowerLocalCellGroup-CM-Rprt-ExtIEs}}	OPTIONAL,
	...
}

PowerLocalCellGroup-CM-Rprt-ExtIEs NBAP-PROTOCOL-EXTENSION ::= {
	...
}

-- **************************************************************
--
-- COMMON MEASUREMENT TERMINATION REQUEST
--
-- **************************************************************

CommonMeasurementTerminationRequest ::= SEQUENCE {
	protocolIEs				ProtocolIE-Container		{{CommonMeasurementTerminationRequest-IEs}},
	protocolExtensions		ProtocolExtensionContainer	{{CommonMeasurementTerminationRequest-Extensions}}		OPTIONAL,
	...
}

CommonMeasurementTerminationRequest-IEs NBAP-PROTOCOL-IES ::= {
	{ ID id-MeasurementID			CRITICALITY ignore				TYPE MeasurementID			PRESENCE mandatory },
	...
}

CommonMeasurementTerminationRequest-Extensions NBAP-PROTOCOL-EXTENSION ::= {
	...
}

-- **************************************************************
--
-- COMMON MEASUREMENT FAILURE INDICATION
--
-- **************************************************************

CommonMeasurementFailureIndication ::= SEQUENCE {
	protocolIEs					ProtocolIE-Container		{{CommonMeasurementFailureIndication-IEs}},
	protocolExtensions			ProtocolExtensionContainer	{{CommonMeasurementFailureIndication-Extensions}}				OPTIONAL,
	...
}

CommonMeasurementFailureIndication-IEs NBAP-PROTOCOL-IES ::= {
	{ ID id-MeasurementID			CRITICALITY ignore			TYPE MeasurementID			PRESENCE mandatory }|
	{ ID id-Cause					CRITICALITY ignore			TYPE Cause					PRESENCE mandatory },
	...
}

CommonMeasurementFailureIndication-Extensions NBAP-PROTOCOL-EXTENSION ::= {
	...
}

-- **************************************************************
--
-- CELL SETUP REQUEST FDD
--
-- **************************************************************

CellSetupRequestFDD ::= SEQUENCE {
	protocolIEs				ProtocolIE-Container		{{CellSetupRequestFDD-IEs}},
	protocolExtensions		ProtocolExtensionContainer	{{CellSetupRequestFDD-Extensions}}		OPTIONAL,
	...
}

CellSetupRequestFDD-IEs NBAP-PROTOCOL-IES ::= {
	{ ID id-Local-Cell-ID										CRITICALITY reject	TYPE Local-Cell-ID					PRESENCE mandatory }|
	{ ID id-C-ID												CRITICALITY reject	TYPE C-ID						PRESENCE mandatory }|
	{ ID id-ConfigurationGenerationID							CRITICALITY reject	TYPE ConfigurationGenerationID					PRESENCE mandatory }|
	{ ID id-T-Cell												CRITICALITY reject	TYPE T-Cell						PRESENCE mandatory }|
	{ ID id-UARFCNforNu											CRITICALITY reject	TYPE UARFCN						PRESENCE mandatory }|
	{ ID id-UARFCNforNd											CRITICALITY reject	TYPE UARFCN						PRESENCE mandatory }|
	{ ID id-MaximumTransmissionPower							CRITICALITY reject	TYPE MaximumTransmissionPower					PRESENCE mandatory }|
	{ ID id-Closed-Loop-Timing-Adjustment-Mode					CRITICALITY reject	TYPE Closedlooptimingadjustmentmode			PRESENCE optional }|
	{ ID id-PrimaryScramblingCode								CRITICALITY reject	TYPE PrimaryScramblingCode					PRESENCE mandatory }|
	{ ID id-Synchronisation-Configuration-Cell-SetupRqst		CRITICALITY reject	TYPE Synchronisation-Configuration-Cell-SetupRqst			PRESENCE	mandatory }|
	{ ID id-DL-TPC-Pattern01Count								CRITICALITY reject	TYPE DL-TPC-Pattern01Count					PRESENCE mandatory }|
	{ ID id-PrimarySCH-Information-Cell-SetupRqstFDD			CRITICALITY reject	TYPE PrimarySCH-Information-Cell-SetupRqstFDD				PRESENCE	mandatory }|
	{ ID id-SecondarySCH-Information-Cell-SetupRqstFDD			CRITICALITY reject	TYPE SecondarySCH-Information-Cell-SetupRqstFDD			PRESENCE mandatory }|
	{ ID id-PrimaryCPICH-Information-Cell-SetupRqstFDD			CRITICALITY reject	TYPE PrimaryCPICH-Information-Cell-SetupRqstFDD			PRESENCE	mandatory }|
	{ ID id-SecondaryCPICH-InformationList-Cell-SetupRqstFDD	CRITICALITY reject	TYPE SecondaryCPICH-InformationList-Cell-SetupRqstFDD	PRESENCE	optional }|
	{ ID id-PrimaryCCPCH-Information-Cell-SetupRqstFDD			CRITICALITY reject	TYPE PrimaryCCPCH-Information-Cell-SetupRqstFDD			PRESENCE	mandatory }|
	{ ID id-Limited-power-increase-information-Cell-SetupRqstFDD	CRITICALITY reject	TYPE Limited-power-increase-information-Cell-SetupRqstFDD		PRESENCE mandatory },
	...
}

CellSetupRequestFDD-Extensions NBAP-PROTOCOL-EXTENSION ::= {
	{ ID id-IPDLParameter-Information-Cell-SetupRqstFDD		CRITICALITY reject	EXTENSION IPDLParameter-Information-Cell-SetupRqstFDD				PRESENCE optional }|
	{ ID id-CellPortion-InformationList-Cell-SetupRqstFDD	CRITICALITY reject	EXTENSION CellPortion-InformationList-Cell-SetupRqstFDD			PRESENCE optional }|
	{ ID id-MIMO-PilotConfiguration							CRITICALITY reject	EXTENSION MIMO-PilotConfiguration			PRESENCE optional },
	...
}

Synchronisation-Configuration-Cell-SetupRqst ::= SEQUENCE {
	n-INSYNC-IND			N-INSYNC-IND,
 	n-OUTSYNC-IND			N-OUTSYNC-IND,
 	t-RLFAILURE				T-RLFAILURE,
	iE-Extensions			ProtocolExtensionContainer { { Synchronisation-Configuration-Cell-SetupRqst-ExtIEs} }		OPTIONAL,
	...
}

Synchronisation-Configuration-Cell-SetupRqst-ExtIEs NBAP-PROTOCOL-EXTENSION ::= {
	...
}

PrimarySCH-Information-Cell-SetupRqstFDD ::= SEQUENCE {
	commonPhysicalChannelID					CommonPhysicalChannelID,
	primarySCH-Power						DL-Power,
	tSTD-Indicator							TSTD-Indicator,
	iE-Extensions							ProtocolExtensionContainer { { PrimarySCH-Information-Cell-SetupRqstFDD-ExtIEs} }		OPTIONAL,
	...
}

PrimarySCH-Information-Cell-SetupRqstFDD-ExtIEs NBAP-PROTOCOL-EXTENSION ::= {
	...
}

SecondarySCH-Information-Cell-SetupRqstFDD ::= SEQUENCE {
	commonPhysicalChannelID					CommonPhysicalChannelID,
	secondarySCH-Power						DL-Power,
	tSTD-Indicator							TSTD-Indicator,
	iE-Extensions							ProtocolExtensionContainer { { SecondarySCH-Information-Cell-SetupRqstFDD-ExtIEs} }		OPTIONAL,
	...
}

SecondarySCH-Information-Cell-SetupRqstFDD-ExtIEs NBAP-PROTOCOL-EXTENSION ::= {
	...
}

PrimaryCPICH-Information-Cell-SetupRqstFDD ::= SEQUENCE {
	commonPhysicalChannelID					CommonPhysicalChannelID,
	primaryCPICH-Power						PrimaryCPICH-Power,
	transmitDiversityIndicator				TransmitDiversityIndicator,
	iE-Extensions							ProtocolExtensionContainer { { PrimaryCPICH-Information-Cell-SetupRqstFDD-ExtIEs} }		OPTIONAL,
	...
}

PrimaryCPICH-Information-Cell-SetupRqstFDD-ExtIEs NBAP-PROTOCOL-EXTENSION ::= {
	...
}

SecondaryCPICH-InformationList-Cell-SetupRqstFDD ::= SEQUENCE (SIZE (1..maxSCPICHCell)) OF ProtocolIE-Single-Container{{ SecondaryCPICH-InformationItemIE-Cell-SetupRqstFDD }}

SecondaryCPICH-InformationItemIE-Cell-SetupRqstFDD NBAP-PROTOCOL-IES ::= {
	{ ID id-SecondaryCPICH-InformationItem-Cell-SetupRqstFDD		CRITICALITY reject	TYPE SecondaryCPICH-InformationItem-Cell-SetupRqstFDD		PRESENCE mandatory}
}

SecondaryCPICH-InformationItem-Cell-SetupRqstFDD ::= SEQUENCE {
	commonPhysicalChannelID					CommonPhysicalChannelID,
	dl-ScramblingCode						DL-ScramblingCode,
	fDD-DL-ChannelisationCodeNumber			FDD-DL-ChannelisationCodeNumber,
	secondaryCPICH-Power					DL-Power,
	transmitDiversityIndicator				TransmitDiversityIndicator,
	iE-Extensions							ProtocolExtensionContainer { { SecondaryCPICH-InformationItem-Cell-SetupRqstFDD-ExtIEs} }		OPTIONAL,
	...
}

SecondaryCPICH-InformationItem-Cell-SetupRqstFDD-ExtIEs NBAP-PROTOCOL-EXTENSION ::= {
	...
}

PrimaryCCPCH-Information-Cell-SetupRqstFDD ::= SEQUENCE {
	commonPhysicalChannelID					CommonPhysicalChannelID,
	bCH-information							BCH-Information-Cell-SetupRqstFDD,
	sTTD-Indicator							STTD-Indicator,
	iE-Extensions							ProtocolExtensionContainer { { PrimaryCCPCH-Information-Cell-SetupRqstFDD-ExtIEs} }		OPTIONAL,
	...
}

PrimaryCCPCH-Information-Cell-SetupRqstFDD-ExtIEs NBAP-PROTOCOL-EXTENSION ::= {
	...
}

BCH-Information-Cell-SetupRqstFDD ::= SEQUENCE {
 	commonTransportChannelID				CommonTransportChannelID,
 	bCH-Power								DL-Power,
	iE-Extensions							ProtocolExtensionContainer { { BCH-Information-Cell-SetupRqstFDD-ExtIEs} }		OPTIONAL,
	...
 }

BCH-Information-Cell-SetupRqstFDD-ExtIEs NBAP-PROTOCOL-EXTENSION ::= {
	...
}

Limited-power-increase-information-Cell-SetupRqstFDD ::= SEQUENCE {
	powerRaiseLimit							PowerRaiseLimit,
	dLPowerAveragingWindowSize				DLPowerAveragingWindowSize,
	iE-Extensions							ProtocolExtensionContainer { { Limited-power-increase-information-Cell-SetupRqstFDD-ExtIEs} }		OPTIONAL,
	...
}

Limited-power-increase-information-Cell-SetupRqstFDD-ExtIEs NBAP-PROTOCOL-EXTENSION ::= {
	...
}

IPDLParameter-Information-Cell-SetupRqstFDD::= SEQUENCE {
	iPDL-FDD-Parameters						IPDL-FDD-Parameters,
	iPDL-Indicator							IPDL-Indicator,	
	iE-Extensions							ProtocolExtensionContainer { { IPDLParameter-Information-Cell-SetupRqstFDD-ExtIEs} }		OPTIONAL,
	...
}

IPDLParameter-Information-Cell-SetupRqstFDD-ExtIEs NBAP-PROTOCOL-EXTENSION ::= {
	...
}

CellPortion-InformationList-Cell-SetupRqstFDD ::= SEQUENCE (SIZE (1..maxNrOfCellPortionsPerCell)) OF ProtocolIE-Single-Container{{ CellPortion-InformationItemIE-Cell-SetupRqstFDD }}

CellPortion-InformationItemIE-Cell-SetupRqstFDD NBAP-PROTOCOL-IES ::= {
	{ ID id-CellPortion-InformationItem-Cell-SetupRqstFDD	CRITICALITY reject	TYPE CellPortion-InformationItem-Cell-SetupRqstFDD					PRESENCE mandatory }
}

CellPortion-InformationItem-Cell-SetupRqstFDD::= SEQUENCE {
	cellPortionID							CellPortionID,
	associatedSecondaryCPICH				CommonPhysicalChannelID,
	maximumTransmissionPowerforCellPortion	MaximumTransmissionPower,
	iE-Extensions							ProtocolExtensionContainer { { CellPortion-InformationItem-Cell-SetupRqstFDD-ExtIEs} }		OPTIONAL,
	...
}

CellPortion-InformationItem-Cell-SetupRqstFDD-ExtIEs NBAP-PROTOCOL-EXTENSION ::= {
...
}

-- **************************************************************
--
-- CELL SETUP REQUEST TDD
--
-- **************************************************************

CellSetupRequestTDD ::= SEQUENCE {
	protocolIEs				ProtocolIE-Container		{{CellSetupRequestTDD-IEs}},
	protocolExtensions		ProtocolExtensionContainer	{{CellSetupRequestTDD-Extensions}}		OPTIONAL,
	...
}

CellSetupRequestTDD-IEs NBAP-PROTOCOL-IES ::= {
	{ ID id-Local-Cell-ID									CRITICALITY reject	TYPE Local-Cell-ID					PRESENCE mandatory }|
	{ ID id-C-ID											CRITICALITY reject	TYPE C-ID							PRESENCE mandatory }|
	{ ID id-ConfigurationGenerationID						CRITICALITY reject	TYPE ConfigurationGenerationID					PRESENCE mandatory }|
	{ ID id-UARFCNforNt										CRITICALITY reject	TYPE UARFCN							PRESENCE mandatory }|	-- For 1.28Mcps TDD, if multiple frequencies exist within the cell indicated by C-ID, this IE indicates the frequency of Primary frequency
	{ ID id-CellParameterID									CRITICALITY reject	TYPE CellParameterID					PRESENCE mandatory }|
	-- For 1.28 Mcps TDD, if the cell is operating in MBSFN only mode, this IE indicate the Preamble code used in the Speial Time Slot [19]
	{ ID id-MaximumTransmissionPower						CRITICALITY reject	TYPE MaximumTransmissionPower					PRESENCE mandatory }|
	{ ID id-TransmissionDiversityApplied					CRITICALITY reject	TYPE TransmissionDiversityApplied					PRESENCE mandatory }|
	{ ID id-SyncCase										CRITICALITY reject	TYPE SyncCase						PRESENCE mandatory }|
	{ ID id-Synchronisation-Configuration-Cell-SetupRqst	CRITICALITY reject	TYPE Synchronisation-Configuration-Cell-SetupRqst	PRESENCE mandatory }|
	{ ID id-DPCHConstant									CRITICALITY reject	TYPE ConstantValue					PRESENCE mandatory }|	-- This IE shall be ignored by the Node B.
	{ ID id-PUSCHConstant									CRITICALITY reject	TYPE ConstantValue					PRESENCE mandatory }|	-- This IE shall be ignored by the Node B.
	{ ID id-PRACHConstant									CRITICALITY reject	TYPE ConstantValue					PRESENCE mandatory }|	-- This IE shall be ignored by the Node B.
	{ ID id-TimingAdvanceApplied							CRITICALITY reject	TYPE TimingAdvanceApplied					PRESENCE mandatory }|
	{ ID id-SCH-Information-Cell-SetupRqstTDD				CRITICALITY reject	TYPE SCH-Information-Cell-SetupRqstTDD				PRESENCE optional }|	-- Mandatory for 3.84Mcps TDD and 7.68Mcps TDD, Not Applicable to 1.28Mcps TDD
	{ ID id-PCCPCH-Information-Cell-SetupRqstTDD			CRITICALITY reject	TYPE PCCPCH-Information-Cell-SetupRqstTDD			PRESENCE optional }|	-- Mandatory for 3.84Mcps TDD, Not Applicable to 1.28Mcps TDD or 7.68Mcps TDD
	{ ID id-TimeSlotConfigurationList-Cell-SetupRqstTDD		CRITICALITY reject	TYPE TimeSlotConfigurationList-Cell-SetupRqstTDD	PRESENCE optional },	-- Mandatory for 3.84Mcps TDD and 7.68Mcps TDD, Not Applicable to 1.28Mcps TDD
	...
}

CellSetupRequestTDD-Extensions NBAP-PROTOCOL-EXTENSION ::= {
	{ ID id-TimeSlotConfigurationList-LCR-Cell-SetupRqstTDD		CRITICALITY reject	EXTENSION TimeSlotConfigurationList-LCR-Cell-SetupRqstTDD		PRESENCE optional }|	-- Mandatory for 1.28Mcps TDD, Not Applicable to 3.84Mcps TDD or 7.68Mcps TDD. If multiple frequencies exist within the cell indicated by C-ID, this IE indicates the Time Slot configuration of Primary frequency.
	{ ID id-PCCPCH-LCR-Information-Cell-SetupRqstTDD			CRITICALITY reject	EXTENSION PCCPCH-LCR-Information-Cell-SetupRqstTDD				PRESENCE optional }|	-- Mandatory for 1.28Mcps TDD, Not Applicable to 3.84Mcps TDD or 7.68Mcps TDD, For 1.28 Mcps TDD, if the cell is operating in MBSFN only mode, PCCPCH is deployed on the MBSFN Special Time Slot [19].
	{ ID id-DwPCH-LCR-Information-Cell-SetupRqstTDD				CRITICALITY reject	EXTENSION DwPCH-LCR-Information-Cell-SetupRqstTDD				PRESENCE optional }|	-- Mandatory for 1.28Mcps TDD, Not Applicable to 3.84Mcps TDD or 7.68Mcps TDD
	{ ID id-ReferenceSFNoffset									CRITICALITY ignore	EXTENSION ReferenceSFNoffset										PRESENCE optional }|
	{ ID id-IPDLParameter-Information-Cell-SetupRqstTDD			CRITICALITY reject	EXTENSION IPDLParameter-Information-Cell-SetupRqstTDD			PRESENCE optional }|	-- Applicable to 3.84Mcps TDD and 7.68Mcps TDD only
	{ ID id-IPDLParameter-Information-LCR-Cell-SetupRqstTDD		CRITICALITY reject	EXTENSION IPDLParameter-Information-LCR-Cell-SetupRqstTDD	PRESENCE optional }|	-- Applicable to 1.28Mcps TDD only
	{ ID id-PCCPCH-768-Information-Cell-SetupRqstTDD			CRITICALITY reject	EXTENSION PCCPCH-768-Information-Cell-SetupRqstTDD				PRESENCE optional }|	-- Mandatory for 7.68Mcps TDD, Not Applicable to 3.84Mcps TDD or 1.28Mcps TDD
	{ ID id-SCH-768-Information-Cell-SetupRqstTDD				CRITICALITY reject	EXTENSION SCH-768-Information-Cell-SetupRqstTDD				PRESENCE optional }|	-- Mandatory for 7.68Mcps TDD, Not Applicable to 3.84Mcps TDD or 1.28Mcps TDD
	{ ID id-MBSFN-Only-Mode-Indicator-Cell-SetupRqstTDD-LCR		CRITICALITY reject	EXTENSION MBSFN-Only-Mode-Indicator									PRESENCE optional }|
	{ ID id-Cell-Frequency-List-LCR-MulFreq-Cell-SetupRqstTDD	CRITICALITY reject	EXTENSION Cell-Frequency-List-LCR-MulFreq-Cell-SetupRqstTDD		PRESENCE optional },  -- Mandatory for 1.28Mcps TDD when using multiple frequencies
	...
}

SCH-Information-Cell-SetupRqstTDD ::= SEQUENCE {
	commonPhysicalChannelID					CommonPhysicalChannelID,
	syncCaseIndicator						SyncCaseIndicator-Cell-SetupRqstTDD-PSCH,
	sCH-Power								DL-Power,
	tSTD-Indicator							TSTD-Indicator,
	iE-Extensions							ProtocolExtensionContainer { { SCH-Information-Cell-SetupRqstTDD-ExtIEs} }		OPTIONAL,
	...
}

SCH-Information-Cell-SetupRqstTDD-ExtIEs NBAP-PROTOCOL-EXTENSION ::= {
	...
}

SyncCaseIndicator-Cell-SetupRqstTDD-PSCH ::= ProtocolIE-Single-Container {{ SyncCaseIndicatorIE-Cell-SetupRqstTDD-PSCH }}

SyncCaseIndicatorIE-Cell-SetupRqstTDD-PSCH NBAP-PROTOCOL-IES ::= {
	{ ID id-SyncCaseIndicatorItem-Cell-SetupRqstTDD-PSCH   CRITICALITY reject	TYPE SyncCaseIndicatorItem-Cell-SetupRqstTDD-PSCH		PRESENCE mandatory }
}

SyncCaseIndicatorItem-Cell-SetupRqstTDD-PSCH ::= CHOICE {
	case1								Case1-Cell-SetupRqstTDD,
	case2								Case2-Cell-SetupRqstTDD,
	...
}

Case1-Cell-SetupRqstTDD ::= SEQUENCE {
	timeSlot							TimeSlot,
	iE-Extensions						ProtocolExtensionContainer { { Case1Item-Cell-SetupRqstTDD-ExtIEs} }		OPTIONAL,
	...
}

Case1Item-Cell-SetupRqstTDD-ExtIEs NBAP-PROTOCOL-EXTENSION ::= {
	...
}

Case2-Cell-SetupRqstTDD ::= SEQUENCE {
	sCH-TimeSlot						SCH-TimeSlot,
	iE-Extensions						ProtocolExtensionContainer { { Case2Item-Cell-SetupRqstTDD-ExtIEs} }		OPTIONAL,
	...
}

Case2Item-Cell-SetupRqstTDD-ExtIEs NBAP-PROTOCOL-EXTENSION ::= {
	...
}

PCCPCH-Information-Cell-SetupRqstTDD ::= SEQUENCE {
	commonPhysicalChannelID					CommonPhysicalChannelID,
	tdd-PhysicalChannelOffset				TDD-PhysicalChannelOffset,
	repetitionPeriod						RepetitionPeriod,
	repetitionLength						RepetitionLength,
	pCCPCH-Power							PCCPCH-Power,
	sCTD-Indicator							SCTD-Indicator,
	iE-Extensions							ProtocolExtensionContainer { { PCCPCH-Information-Cell-SetupRqstTDD-ExtIEs} }		OPTIONAL,
	...
}

PCCPCH-Information-Cell-SetupRqstTDD-ExtIEs NBAP-PROTOCOL-EXTENSION ::= {
	...
}

TimeSlotConfigurationList-Cell-SetupRqstTDD ::= SEQUENCE (SIZE (1..15)) OF TimeSlotConfigurationItem-Cell-SetupRqstTDD

TimeSlotConfigurationItem-Cell-SetupRqstTDD ::= SEQUENCE {
	timeSlot								TimeSlot,
	timeSlotStatus							TimeSlotStatus,
	timeSlotDirection						TimeSlotDirection,
	iE-Extensions							ProtocolExtensionContainer { { TimeSlotConfigurationItem-Cell-SetupRqstTDD-ExtIEs} }		OPTIONAL,
	...
}

TimeSlotConfigurationItem-Cell-SetupRqstTDD-ExtIEs NBAP-PROTOCOL-EXTENSION ::= {
	{ ID id-MBSFN-Cell-ParameterID-Cell-SetupRqstTDD			CRITICALITY reject	EXTENSION CellParameterID		PRESENCE optional },-- Applicable only to for MBSFN only mode
	...
}

TimeSlotConfigurationList-LCR-Cell-SetupRqstTDD ::= SEQUENCE (SIZE (1..7)) OF TimeSlotConfigurationItem-LCR-Cell-SetupRqstTDD

TimeSlotConfigurationItem-LCR-Cell-SetupRqstTDD ::= SEQUENCE {
	timeSlotLCR								TimeSlotLCR,
	timeSlotStatus							TimeSlotStatus,
	timeSlotDirection						TimeSlotDirection,
	iE-Extensions							ProtocolExtensionContainer { { TimeSlotConfigurationItem-LCR-Cell-SetupRqstTDD-ExtIEs} }		OPTIONAL,
	...
}

TimeSlotConfigurationItem-LCR-Cell-SetupRqstTDD-ExtIEs NBAP-PROTOCOL-EXTENSION ::= {
	{ ID id-Time-Slot-Parameter-ID							CRITICALITY reject			EXTENSION CellParameterID				PRESENCE optional },
	...
}

PCCPCH-LCR-Information-Cell-SetupRqstTDD ::= SEQUENCE {
	commonPhysicalChannelID					CommonPhysicalChannelID,
	tdd-PhysicalChannelOffset				TDD-PhysicalChannelOffset,
	repetitionPeriod						RepetitionPeriod,
	repetitionLength						RepetitionLength,
	pCCPCH-Power							PCCPCH-Power,
	sCTD-Indicator							SCTD-Indicator,
	tSTD-Indicator							TSTD-Indicator,
	iE-Extensions							ProtocolExtensionContainer { { PCCPCH-LCR-Information-Cell-SetupRqstTDD-ExtIEs} }		OPTIONAL,
	...
}

PCCPCH-LCR-Information-Cell-SetupRqstTDD-ExtIEs NBAP-PROTOCOL-EXTENSION ::= {
	...
}

DwPCH-LCR-Information-Cell-SetupRqstTDD ::= SEQUENCE {
	commonPhysicalChannelId			CommonPhysicalChannelID,
	tSTD-Indicator					TSTD-Indicator,
	dwPCH-Power						DwPCH-Power,
	iE-Extensions					ProtocolExtensionContainer { { DwPCH-LCR-Information-Cell-SetupRqstTDD-ExtIEs} }		OPTIONAL,
	...
}

DwPCH-LCR-Information-Cell-SetupRqstTDD-ExtIEs NBAP-PROTOCOL-EXTENSION ::= {
	...
}

IPDLParameter-Information-Cell-SetupRqstTDD ::= SEQUENCE {
	iPDL-TDD-Parameters						IPDL-TDD-Parameters,
	iPDL-Indicator							IPDL-Indicator,
	iE-Extensions							ProtocolExtensionContainer { { IPDLParameter-Information-Cell-SetupRqstTDD-ExtIEs} }		OPTIONAL,
	...
}

IPDLParameter-Information-Cell-SetupRqstTDD-ExtIEs NBAP-PROTOCOL-EXTENSION ::= {
	...
}

IPDLParameter-Information-LCR-Cell-SetupRqstTDD ::= SEQUENCE {
	iPDL-TDD-Parameters-LCR					IPDL-TDD-Parameters-LCR,
	iPDL-Indicator							IPDL-Indicator,
	iE-Extensions							ProtocolExtensionContainer { { IPDLParameter-Information-LCR-Cell-SetupRqstTDD-ExtIEs} }		OPTIONAL,
	...
}

IPDLParameter-Information-LCR-Cell-SetupRqstTDD-ExtIEs NBAP-PROTOCOL-EXTENSION ::= {
	...
}

PCCPCH-768-Information-Cell-SetupRqstTDD ::= SEQUENCE {
	commonPhysicalChannelID768				CommonPhysicalChannelID768,
	tdd-PhysicalChannelOffset				TDD-PhysicalChannelOffset,
	repetitionPeriod						RepetitionPeriod,
	repetitionLength						RepetitionLength,
	pCCPCH-Power							PCCPCH-Power,
	sCTD-Indicator							SCTD-Indicator,
	iE-Extensions							ProtocolExtensionContainer { { PCCPCH-768-Information-Cell-SetupRqstTDD-ExtIEs} }		OPTIONAL,
	...
}

PCCPCH-768-Information-Cell-SetupRqstTDD-ExtIEs NBAP-PROTOCOL-EXTENSION ::= {
	...
}

SCH-768-Information-Cell-SetupRqstTDD ::= SEQUENCE {
	commonPhysicalChannelID768				CommonPhysicalChannelID768,
	syncCaseIndicator						SyncCaseIndicator-Cell-SetupRqstTDD-PSCH,
	sCH-Power								DL-Power,
	tSTD-Indicator							TSTD-Indicator,
	iE-Extensions							ProtocolExtensionContainer { { SCH-768-Information-Cell-SetupRqstTDD-ExtIEs} }		OPTIONAL,
	...
}

SCH-768-Information-Cell-SetupRqstTDD-ExtIEs NBAP-PROTOCOL-EXTENSION ::= {
	...
}

Cell-Frequency-List-LCR-MulFreq-Cell-SetupRqstTDD ::= SEQUENCE (SIZE (1..maxFrequencyinCell-1)) OF Cell-Frequency-Item-LCR-MulFreq-Cell-SetupRqstTDD

Cell-Frequency-Item-LCR-MulFreq-Cell-SetupRqstTDD ::= SEQUENCE {
	uARFCN													UARFCN,
	-- This IE indicates the frequency of  Secondary frequency 
	timeSlotConfigurationList-LCR-Cell-SetupRqstTDD			TimeSlotConfigurationList-LCR-Cell-SetupRqstTDD,
	-- This IE indicates the Time Slot configuration of Secondary frequency 
	iE-Extensions							ProtocolExtensionContainer { { Cell-Frequency-Item-LCR-MulFreq-Cell-SetupRqstTDD-ExtIEs} }		OPTIONAL,
	...
}

Cell-Frequency-Item-LCR-MulFreq-Cell-SetupRqstTDD-ExtIEs NBAP-PROTOCOL-EXTENSION ::= {
	...
}

-- **************************************************************
--
-- CELL SETUP RESPONSE
--
-- **************************************************************

CellSetupResponse ::= SEQUENCE {
	protocolIEs					ProtocolIE-Container		{{CellSetupResponse-IEs}},
	protocolExtensions			ProtocolExtensionContainer	{{CellSetupResponse-Extensions}}		OPTIONAL,
	...
}

CellSetupResponse-IEs NBAP-PROTOCOL-IES ::= {
	{ ID id-CriticalityDiagnostics		CRITICALITY ignore			TYPE CriticalityDiagnostics		PRESENCE optional },
	...
}

CellSetupResponse-Extensions NBAP-PROTOCOL-EXTENSION ::= {
	...
}

-- **************************************************************
--
-- CELL SETUP FAILURE
--
-- **************************************************************

CellSetupFailure ::= SEQUENCE {
	protocolIEs				ProtocolIE-Container		{{CellSetupFailure-IEs}},
	protocolExtensions		ProtocolExtensionContainer	{{CellSetupFailure-Extensions}}			OPTIONAL,
	...
}

CellSetupFailure-IEs NBAP-PROTOCOL-IES ::= {
	{ ID id-Cause							CRITICALITY ignore			TYPE Cause						PRESENCE mandatory	}|
	{ ID id-CriticalityDiagnostics			CRITICALITY ignore			TYPE CriticalityDiagnostics		PRESENCE optional	},
	...
}

CellSetupFailure-Extensions NBAP-PROTOCOL-EXTENSION ::= {
	...
}

-- **************************************************************
--
-- CELL RECONFIGURATION REQUEST FDD
--
-- **************************************************************

CellReconfigurationRequestFDD ::= SEQUENCE {
	protocolIEs				ProtocolIE-Container		{{CellReconfigurationRequestFDD-IEs}},
	protocolExtensions		ProtocolExtensionContainer	{{CellReconfigurationRequestFDD-Extensions}} 		OPTIONAL,
	...
}

CellReconfigurationRequestFDD-IEs NBAP-PROTOCOL-IES ::= {
	{ ID	id-C-ID													CRITICALITY reject	TYPE C-ID												PRESENCE mandatory }|
	{ ID	id-ConfigurationGenerationID							CRITICALITY reject	TYPE ConfigurationGenerationID									PRESENCE mandatory }|
	{ ID	id-MaximumTransmissionPower								CRITICALITY reject	TYPE MaximumTransmissionPower									PRESENCE optional }|
	{ ID	id-Synchronisation-Configuration-Cell-ReconfRqst		CRITICALITY reject	TYPE Synchronisation-Configuration-Cell-ReconfRqst		PRESENCE optional }|
	{ ID	id-PrimarySCH-Information-Cell-ReconfRqstFDD			CRITICALITY reject	TYPE PrimarySCH-Information-Cell-ReconfRqstFDD			PRESENCE optional }|
	{ ID	id-SecondarySCH-Information-Cell-ReconfRqstFDD			CRITICALITY reject	TYPE SecondarySCH-Information-Cell-ReconfRqstFDD			PRESENCE optional }|
	{ ID	id-PrimaryCPICH-Information-Cell-ReconfRqstFDD			CRITICALITY reject	TYPE PrimaryCPICH-Information-Cell-ReconfRqstFDD			PRESENCE optional }|
	{ ID	id-SecondaryCPICH-InformationList-Cell-ReconfRqstFDD	CRITICALITY reject	TYPE SecondaryCPICH-InformationList-Cell-ReconfRqstFDD		PRESENCE optional }|
	{ ID	id-PrimaryCCPCH-Information-Cell-ReconfRqstFDD			CRITICALITY reject	TYPE PrimaryCCPCH-Information-Cell-ReconfRqstFDD			PRESENCE optional },
	...
}

CellReconfigurationRequestFDD-Extensions NBAP-PROTOCOL-EXTENSION ::= {
	{ ID	id-IPDLParameter-Information-Cell-ReconfRqstFDD	CRITICALITY reject	EXTENSION IPDLParameter-Information-Cell-ReconfRqstFDD					PRESENCE optional }|
	{ ID id-CellPortion-InformationList-Cell-ReconfRqstFDD	CRITICALITY reject	EXTENSION CellPortion-InformationList-Cell-ReconfRqstFDD			PRESENCE optional }|
	{ ID id-MIMO-PilotConfiguration							CRITICALITY reject	EXTENSION MIMO-PilotConfiguration										PRESENCE optional },
	...
}

Synchronisation-Configuration-Cell-ReconfRqst ::= SEQUENCE {
	n-INSYNC-IND			N-INSYNC-IND,
 	n-OUTSYNC-IND			N-OUTSYNC-IND,
 	t-RLFAILURE				T-RLFAILURE,
	iE-Extensions			ProtocolExtensionContainer { { Synchronisation-Configuration-Cell-ReconfRqst-ExtIEs} }		OPTIONAL,
	...
}

Synchronisation-Configuration-Cell-ReconfRqst-ExtIEs NBAP-PROTOCOL-EXTENSION ::= {
	...
}

PrimarySCH-Information-Cell-ReconfRqstFDD ::= SEQUENCE {
 	commonPhysicalChannelID					CommonPhysicalChannelID,
 	primarySCH-Power						DL-Power,
	iE-Extensions							ProtocolExtensionContainer { { PrimarySCH-Information-Cell-ReconfRqstFDD-ExtIEs} }		OPTIONAL,
	...
 }

PrimarySCH-Information-Cell-ReconfRqstFDD-ExtIEs NBAP-PROTOCOL-EXTENSION ::= {
	...
}

SecondarySCH-Information-Cell-ReconfRqstFDD ::= SEQUENCE {
 	commonPhysicalChannelID					CommonPhysicalChannelID,
 	secondarySCH-Power						DL-Power,
	iE-Extensions							ProtocolExtensionContainer { { SecondarySCH-Information-Cell-ReconfRqstFDD-ExtIEs} }		OPTIONAL,
	...
 }

SecondarySCH-Information-Cell-ReconfRqstFDD-ExtIEs NBAP-PROTOCOL-EXTENSION ::= {
	...
}

PrimaryCPICH-Information-Cell-ReconfRqstFDD ::= SEQUENCE {
 	commonPhysicalChannelID					CommonPhysicalChannelID,
	primaryCPICH-Power						PrimaryCPICH-Power,
	iE-Extensions							ProtocolExtensionContainer { { PrimaryCPICH-Information-Cell-ReconfRqstFDD-ExtIEs} }		OPTIONAL,
	...
 }

PrimaryCPICH-Information-Cell-ReconfRqstFDD-ExtIEs NBAP-PROTOCOL-EXTENSION ::= {
	...
}

SecondaryCPICH-InformationList-Cell-ReconfRqstFDD ::= SEQUENCE (SIZE (1..maxSCPICHCell)) OF ProtocolIE-Single-Container{{ SecondaryCPICH-InformationItemIE-Cell-ReconfRqstFDD }}

SecondaryCPICH-InformationItemIE-Cell-ReconfRqstFDD NBAP-PROTOCOL-IES ::= {
	{ ID	id-SecondaryCPICH-InformationItem-Cell-ReconfRqstFDD	CRITICALITY reject	TYPE	SecondaryCPICH-InformationItem-Cell-ReconfRqstFDD		PRESENCE mandatory }
}

SecondaryCPICH-InformationItem-Cell-ReconfRqstFDD ::= SEQUENCE {
 	commonPhysicalChannelID					CommonPhysicalChannelID,
 	secondaryCPICH-Power					DL-Power,
	iE-Extensions							ProtocolExtensionContainer { { SecondaryCPICH-InformationItem-Cell-ReconfRqstFDD-ExtIEs} }		OPTIONAL,
	...
 }

SecondaryCPICH-InformationItem-Cell-ReconfRqstFDD-ExtIEs NBAP-PROTOCOL-EXTENSION ::= {
	...
}
 
PrimaryCCPCH-Information-Cell-ReconfRqstFDD ::= SEQUENCE {
 	bCH-information							BCH-information-Cell-ReconfRqstFDD,
	iE-Extensions							ProtocolExtensionContainer { { PrimaryCCPCH-Information-Cell-ReconfRqstFDD-ExtIEs} }		OPTIONAL,
	...
 }

PrimaryCCPCH-Information-Cell-ReconfRqstFDD-ExtIEs NBAP-PROTOCOL-EXTENSION ::= {
	...
}

BCH-information-Cell-ReconfRqstFDD ::= SEQUENCE {
 	commonTransportChannelID				CommonTransportChannelID,
 	bCH-Power								DL-Power,
	iE-Extensions							ProtocolExtensionContainer { { BCH-information-Cell-ReconfRqstFDD-ExtIEs} }		OPTIONAL,
	...
 }

BCH-information-Cell-ReconfRqstFDD-ExtIEs NBAP-PROTOCOL-EXTENSION ::= {
	...
}

IPDLParameter-Information-Cell-ReconfRqstFDD::= SEQUENCE {
	iPDL-FDD-Parameters							IPDL-FDD-Parameters		OPTIONAL,
	iPDL-Indicator								IPDL-Indicator,
	iE-Extensions							ProtocolExtensionContainer { { IPDLParameter-Information-Cell-ReconfRqstFDD-ExtIEs} }		OPTIONAL,
	...
}

IPDLParameter-Information-Cell-ReconfRqstFDD-ExtIEs NBAP-PROTOCOL-EXTENSION ::= {
	...
}

CellPortion-InformationList-Cell-ReconfRqstFDD ::= SEQUENCE (SIZE (1..maxNrOfCellPortionsPerCell)) OF ProtocolIE-Single-Container{{ CellPortion-InformationItemIE-Cell-ReconfRqstFDD }}

CellPortion-InformationItemIE-Cell-ReconfRqstFDD NBAP-PROTOCOL-IES ::= {
	{ ID id-CellPortion-InformationItem-Cell-ReconfRqstFDD	CRITICALITY reject	TYPE CellPortion-InformationItem-Cell-ReconfRqstFDD					PRESENCE	mandatory}
}

CellPortion-InformationItem-Cell-ReconfRqstFDD::= SEQUENCE {
	cellPortionID							CellPortionID,
	maximumTransmissionPowerforCellPortion	MaximumTransmissionPower,
	iE-Extensions							ProtocolExtensionContainer { { CellPortion-InformationItem-Cell-ReconfRqstFDD-ExtIEs} }		OPTIONAL,
	...
}

CellPortion-InformationItem-Cell-ReconfRqstFDD-ExtIEs NBAP-PROTOCOL-EXTENSION ::= {
...
}

-- **************************************************************
--
-- CELL RECONFIGURATION REQUEST TDD
--
-- **************************************************************

CellReconfigurationRequestTDD ::= SEQUENCE {
	protocolIEs				ProtocolIE-Container		{{CellReconfigurationRequestTDD-IEs}},
	protocolExtensions		ProtocolExtensionContainer	{{CellReconfigurationRequestTDD-Extensions}}		OPTIONAL,
	...
}

CellReconfigurationRequestTDD-IEs NBAP-PROTOCOL-IES ::= {
	{ ID id-C-ID											CRITICALITY reject	TYPE C-ID						PRESENCE mandatory }|
	{ ID id-ConfigurationGenerationID						CRITICALITY reject	TYPE ConfigurationGenerationID				PRESENCE mandatory }|
	{ ID id-Synchronisation-Configuration-Cell-ReconfRqst	CRITICALITY reject	TYPE Synchronisation-Configuration-Cell-ReconfRqst		PRESENCE optional }|
	{ ID id-TimingAdvanceApplied							CRITICALITY reject	TYPE TimingAdvanceApplied				PRESENCE optional }|
	{ ID id-SCH-Information-Cell-ReconfRqstTDD				CRITICALITY reject	TYPE SCH-Information-Cell-ReconfRqstTDD		PRESENCE optional }|
	-- Applicable to 3.84Mcps TDD only
	{ ID id-PCCPCH-Information-Cell-ReconfRqstTDD			CRITICALITY reject	TYPE PCCPCH-Information-Cell-ReconfRqstTDD	PRESENCE optional }|
	-- Not applicable to 7.68Mcps TDD only. For 1.28 Mcps TDD, if the cell is operating in MBSFN only mode, PCCPCH is deployed on the MBSFN Special Time Slot [19].
	{ ID id-MaximumTransmissionPower						CRITICALITY reject	TYPE MaximumTransmissionPower				PRESENCE optional }|
	{ ID id-DPCHConstant									CRITICALITY reject	TYPE ConstantValue				PRESENCE optional }|
	-- This IE shall be ignored by the Node B.
	{ ID id-PUSCHConstant									CRITICALITY reject	TYPE ConstantValue				PRESENCE optional }|
	-- This IE shall be ignored by the Node B.
	{ ID id-PRACHConstant									CRITICALITY reject	TYPE ConstantValue				PRESENCE optional }|
	-- This IE shall be ignored by the Node B.
	{ ID id-TimeSlotConfigurationList-Cell-ReconfRqstTDD	CRITICALITY reject	TYPE TimeSlotConfigurationList-Cell-ReconfRqstTDD		PRESENCE optional },
	-- Mandatory for 3.84Mcps TDD and 7.68Mcps TDD only. Not Applicable to 1.28Mcps TDD.
	...
}

CellReconfigurationRequestTDD-Extensions NBAP-PROTOCOL-EXTENSION ::= {
	{ ID	id-TimeSlotConfigurationList-LCR-Cell-ReconfRqstTDD	CRITICALITY reject	EXTENSION TimeSlotConfigurationList-LCR-Cell-ReconfRqstTDD	PRESENCE optional }|	-- Applicable to 1.28Mcps TDD only, If multiple frequencies exist within the cell indicated by C-ID, this IE indicates the Time Slot reconfiguration of Primary frequency 
	{ ID	id-DwPCH-LCR-Information-Cell-ReconfRqstTDD			CRITICALITY reject	EXTENSION DwPCH-LCR-Information-Cell-ReconfRqstTDD			PRESENCE optional }|	-- Applicable to 1.28Mcps TDD only
	{ ID	id-IPDLParameter-Information-Cell-ReconfRqstTDD		CRITICALITY reject	EXTENSION IPDLParameter-Information-Cell-ReconfRqstTDD		PRESENCE optional }|	-- Applicable to 3.84Mcps TDD and 7.68Mcps TDD only
	{ ID	id-IPDLParameter-Information-LCR-Cell-ReconfRqstTDD	CRITICALITY reject	EXTENSION IPDLParameter-Information-LCR-Cell-ReconfRqstTDD	PRESENCE optional }|	-- Applicable to 1.28Mcps TDD only
	{ ID id-SCH-768-Information-Cell-ReconfRqstTDD				CRITICALITY reject	EXTENSION SCH-768-Information-Cell-ReconfRqstTDD				PRESENCE optional }|	-- Applicable to 7.68Mcps TDD only
	{ ID id-PCCPCH-768-Information-Cell-ReconfRqstTDD			CRITICALITY reject	EXTENSION PCCPCH-768-Information-Cell-ReconfRqstTDD			PRESENCE optional }|	-- Applicable to 7.68Mcps TDD only
	{ ID id-UARFCN-Adjustment									CRITICALITY reject	EXTENSION UARFCN-Adjustment										PRESENCE optional },	-- Applicable to 1.28Mcps TDD when using multiple frequencies
	...
}

SCH-Information-Cell-ReconfRqstTDD ::= SEQUENCE {
	commonPhysicalChannelID					CommonPhysicalChannelID,
	sCH-Power								DL-Power,
	iE-Extensions							ProtocolExtensionContainer { { PSCH-Information-Cell-ReconfRqstTDD-ExtIEs} }		OPTIONAL,
	...
}

PSCH-Information-Cell-ReconfRqstTDD-ExtIEs NBAP-PROTOCOL-EXTENSION ::= {
	...
}

PCCPCH-Information-Cell-ReconfRqstTDD ::= SEQUENCE {
	commonPhysicalChannelID					CommonPhysicalChannelID,
	pCCPCH-Power							PCCPCH-Power,
	iE-Extensions							ProtocolExtensionContainer { { PCCPCH-Information-Cell-ReconfRqstTDD-ExtIEs} }		OPTIONAL,
	...
}

PCCPCH-Information-Cell-ReconfRqstTDD-ExtIEs NBAP-PROTOCOL-EXTENSION ::= {
	...
}

TimeSlotConfigurationList-Cell-ReconfRqstTDD ::= SEQUENCE (SIZE (1..15)) OF TimeSlotConfigurationItem-Cell-ReconfRqstTDD

TimeSlotConfigurationItem-Cell-ReconfRqstTDD ::= SEQUENCE {
	timeSlot								TimeSlot,
 	timeSlotStatus							TimeSlotStatus,
 	timeSlotDirection						TimeSlotDirection,
	iE-Extensions							ProtocolExtensionContainer { { TimeSlotConfigurationItem-Cell-ReconfRqstTDD-ExtIEs} }		OPTIONAL,
	...
 }

TimeSlotConfigurationItem-Cell-ReconfRqstTDD-ExtIEs NBAP-PROTOCOL-EXTENSION ::= {
	{ ID id-MBSFN-Cell-ParameterID-Cell-ReconfRqstTDD			CRITICALITY reject	EXTENSION 	CellParameterID		PRESENCE optional },
	...
}

TimeSlotConfigurationList-LCR-Cell-ReconfRqstTDD ::= SEQUENCE (SIZE (1..7)) OF TimeSlotConfigurationItem-LCR-Cell-ReconfRqstTDD

TimeSlotConfigurationItem-LCR-Cell-ReconfRqstTDD ::= SEQUENCE {
	timeSlotLCR								TimeSlotLCR,
 	timeSlotStatus							TimeSlotStatus,
 	timeSlotDirection						TimeSlotDirection,
	iE-Extensions							ProtocolExtensionContainer { { TimeSlotConfigurationItem-LCR-Cell-ReconfRqstTDD-ExtIEs} }		OPTIONAL,
	...
 }

TimeSlotConfigurationItem-LCR-Cell-ReconfRqstTDD-ExtIEs NBAP-PROTOCOL-EXTENSION ::= {
	...
}

DwPCH-LCR-Information-Cell-ReconfRqstTDD ::= SEQUENCE {
	commonPhysicalChannelId					CommonPhysicalChannelID,
 	dwPCH-Power								DwPCH-Power,
	iE-Extensions							ProtocolExtensionContainer { { DwPCH-LCR-Information-Cell-ReconfRqstTDD-ExtIEs} }		OPTIONAL,
	...
 }

DwPCH-LCR-Information-Cell-ReconfRqstTDD-ExtIEs NBAP-PROTOCOL-EXTENSION ::= {
	...
}

IPDLParameter-Information-Cell-ReconfRqstTDD ::= SEQUENCE {
	iPDL-TDD-Parameters						IPDL-TDD-Parameters		OPTIONAL,
	iPDL-Indicator							IPDL-Indicator,
	iE-Extensions							ProtocolExtensionContainer { { IPDLParameter-Information-Cell-ReconfRqstTDD-ExtIEs} }		OPTIONAL,
	...
}

IPDLParameter-Information-Cell-ReconfRqstTDD-ExtIEs NBAP-PROTOCOL-EXTENSION ::= {
	...
}

IPDLParameter-Information-LCR-Cell-ReconfRqstTDD ::= SEQUENCE {
	iPDL-TDD-Parameters-LCR					IPDL-TDD-Parameters-LCR		OPTIONAL,
	iPDL-Indicator							IPDL-Indicator,
	iE-Extensions							ProtocolExtensionContainer { { IPDLParameter-Information-LCR-Cell-ReconfRqstTDD-ExtIEs} }		OPTIONAL,
	...
}

IPDLParameter-Information-LCR-Cell-ReconfRqstTDD-ExtIEs NBAP-PROTOCOL-EXTENSION ::= {
	...
}

SCH-768-Information-Cell-ReconfRqstTDD ::= SEQUENCE {
	commonPhysicalChannelID768				CommonPhysicalChannelID768,
	sCH-Power								DL-Power,
	iE-Extensions							ProtocolExtensionContainer { { PSCH-768-Information-Cell-ReconfRqstTDD-ExtIEs} }		OPTIONAL,
	...
}

PSCH-768-Information-Cell-ReconfRqstTDD-ExtIEs NBAP-PROTOCOL-EXTENSION ::= {
	...
}

PCCPCH-768-Information-Cell-ReconfRqstTDD ::= SEQUENCE {
	commonPhysicalChannelID768				CommonPhysicalChannelID768,
	pCCPCH-Power							PCCPCH-Power,
	iE-Extensions							ProtocolExtensionContainer { { PCCPCH-768-Information-Cell-ReconfRqstTDD-ExtIEs} }		OPTIONAL,
	...
}

PCCPCH-768-Information-Cell-ReconfRqstTDD-ExtIEs NBAP-PROTOCOL-EXTENSION ::= {
	...
}

UARFCN-Adjustment::= CHOICE {
	cell-Frequency-Add-LCR-MulFreq-Cell-ReconfRqstTDD				Cell-Frequency-Add-LCR-MulFreq-Cell-ReconfRqstTDD,
	cell-Frequency-ModifyList-LCR-MulFreq-Cell-ReconfRqstTDD		Cell-Frequency-ModifyList-LCR-MulFreq-Cell-ReconfRqstTDD,
	cell-Frequency-Delete-LCR-MulFreq-Cell-ReconfRqstTDD			Cell-Frequency-Delete-LCR-MulFreq-Cell-ReconfRqstTDD,
	...
}

Cell-Frequency-Add-LCR-MulFreq-Cell-ReconfRqstTDD ::= SEQUENCE {
	uARFCN													UARFCN,
	-- This IE indicates the frequency of  Secondary frequency to add
	timeSlotConfigurationList-LCR-Cell-ReconfRqstTDD		TimeSlotConfigurationList-LCR-Cell-ReconfRqstTDD,
	-- This IE indicates the Time Slot configuration of Secondary frequency to add
	iE-Extensions							ProtocolExtensionContainer { { Cell-Frequency-Add-LCR-MulFreq-Cell-ReconfRqstTDD-ExtIEs} }		OPTIONAL,
	...
}

Cell-Frequency-Add-LCR-MulFreq-Cell-ReconfRqstTDD-ExtIEs NBAP-PROTOCOL-EXTENSION ::= {
	...
}

Cell-Frequency-ModifyList-LCR-MulFreq-Cell-ReconfRqstTDD ::= SEQUENCE (SIZE (1..maxFrequencyinCell-1)) OF Cell-Frequency-ModifyItem-LCR-MulFreq-Cell-ReconfRqstTDD

Cell-Frequency-ModifyItem-LCR-MulFreq-Cell-ReconfRqstTDD ::= SEQUENCE {
	uARFCN													UARFCN,
	-- This IE indicates the frequency of  Secondary frequency to modify
	timeSlotConfigurationList-LCR-Cell-ReconfRqstTDD		TimeSlotConfigurationList-LCR-Cell-ReconfRqstTDD,
	-- This IE indicates the Time Slot reconfiguration of Secondary frequency 
	iE-Extensions							ProtocolExtensionContainer { { Cell-Frequency-ModifyItem-LCR-MulFreq-Cell-ReconfRqstTDD-ExtIEs} }		OPTIONAL,
	...
}

Cell-Frequency-ModifyItem-LCR-MulFreq-Cell-ReconfRqstTDD-ExtIEs NBAP-PROTOCOL-EXTENSION ::= {
	...
}

Cell-Frequency-Delete-LCR-MulFreq-Cell-ReconfRqstTDD ::= SEQUENCE {
	uARFCN													UARFCN,
	-- This IE indicates the frequency of  Secondary  Frequency to delete
	iE-Extensions							ProtocolExtensionContainer { { Cell-Frequency-Delete-LCR-MulFreq-Cell-ReconfRqstTDD-ExtIEs} }		OPTIONAL,
	...
}

Cell-Frequency-Delete-LCR-MulFreq-Cell-ReconfRqstTDD-ExtIEs NBAP-PROTOCOL-EXTENSION ::= {
	...
}

-- **************************************************************
--
-- CELL RECONFIGURATION RESPONSE
--
-- **************************************************************

CellReconfigurationResponse ::= SEQUENCE {
	protocolIEs					ProtocolIE-Container		{{CellReconfigurationResponse-IEs}},
	protocolExtensions			ProtocolExtensionContainer	{{CellReconfigurationResponse-Extensions}}		OPTIONAL,
	...
}

CellReconfigurationResponse-IEs NBAP-PROTOCOL-IES ::= {
	{ ID id-CriticalityDiagnostics		CRITICALITY ignore			TYPE CriticalityDiagnostics		PRESENCE optional },
	...
}

CellReconfigurationResponse-Extensions NBAP-PROTOCOL-EXTENSION ::= {
	...
}

-- **************************************************************
--
-- CELL RECONFIGURATION FAILURE
--
-- **************************************************************

CellReconfigurationFailure ::= SEQUENCE {
	protocolIEs				ProtocolIE-Container		{{CellReconfigurationFailure-IEs}},
	protocolExtensions		ProtocolExtensionContainer	{{CellReconfigurationFailure-Extensions}}		OPTIONAL,
	...
}

CellReconfigurationFailure-IEs NBAP-PROTOCOL-IES ::= {
	{ ID id-Cause						CRITICALITY ignore			TYPE Cause							PRESENCE mandatory	}|
	{ ID id-CriticalityDiagnostics		CRITICALITY ignore			TYPE CriticalityDiagnostics			PRESENCE optional	},
	...
}

CellReconfigurationFailure-Extensions NBAP-PROTOCOL-EXTENSION ::= {
	...
}

-- **************************************************************
--
-- CELL DELETION REQUEST
--
-- **************************************************************

CellDeletionRequest ::= SEQUENCE {
	protocolIEs				ProtocolIE-Container		{{CellDeletionRequest-IEs}},
	protocolExtensions		ProtocolExtensionContainer	{{CellDeletionRequest-Extensions}}		OPTIONAL,
	...
}

CellDeletionRequest-IEs NBAP-PROTOCOL-IES ::= {
	{ ID id-C-ID			CRITICALITY reject			TYPE C-ID		PRESENCE mandatory },
	...
}

CellDeletionRequest-Extensions NBAP-PROTOCOL-EXTENSION ::= {
	...
}

-- **************************************************************
--
-- CELL DELETION RESPONSE
--
-- **************************************************************

CellDeletionResponse ::= SEQUENCE {
	protocolIEs				ProtocolIE-Container		{{CellDeletionResponse-IEs}},
	protocolExtensions		ProtocolExtensionContainer	{{CellDeletionResponse-Extensions}}		OPTIONAL,
	...
}

CellDeletionResponse-IEs NBAP-PROTOCOL-IES ::= {
	{ ID id-CriticalityDiagnostics		CRITICALITY ignore			TYPE CriticalityDiagnostics		PRESENCE optional },
	...
}

CellDeletionResponse-Extensions NBAP-PROTOCOL-EXTENSION ::= {
	...
}

-- **************************************************************
--
-- RESOURCE STATUS INDICATION
--
-- **************************************************************

ResourceStatusIndication ::= SEQUENCE {
	protocolIEs				ProtocolIE-Container		{{ResourceStatusIndication-IEs}},
	protocolExtensions		ProtocolExtensionContainer	{{ResourceStatusIndication-Extensions}}		OPTIONAL,
	...
}

ResourceStatusIndication-IEs NBAP-PROTOCOL-IES ::= {
	{ ID id-IndicationType-ResourceStatusInd	CRITICALITY ignore	TYPE IndicationType-ResourceStatusInd		PRESENCE mandatory }|
	{ ID id-Cause								CRITICALITY ignore	TYPE Cause							PRESENCE optional },
	...
}

ResourceStatusIndication-Extensions NBAP-PROTOCOL-EXTENSION ::= {
	...
}

IndicationType-ResourceStatusInd ::= CHOICE {
	no-Failure								No-Failure-ResourceStatusInd,
	serviceImpacting						ServiceImpacting-ResourceStatusInd,
	...
}

No-Failure-ResourceStatusInd ::= SEQUENCE {
	local-Cell-InformationList				Local-Cell-InformationList-ResourceStatusInd,
	local-Cell-Group-InformationList		Local-Cell-Group-InformationList-ResourceStatusInd	OPTIONAL,
	iE-Extensions							ProtocolExtensionContainer { { No-FailureItem-ResourceStatusInd-ExtIEs} }	OPTIONAL,
	...
}

No-FailureItem-ResourceStatusInd-ExtIEs NBAP-PROTOCOL-EXTENSION ::= {
	{ ID	id-Power-Local-Cell-Group-InformationList-ResourceStatusInd		CRITICALITY		ignore			EXTENSION	Power-Local-Cell-Group-InformationList-ResourceStatusInd		PRESENCE	optional	},
	...
}

Local-Cell-InformationList-ResourceStatusInd ::= SEQUENCE(SIZE (1..maxLocalCellinNodeB)) OF ProtocolIE-Single-Container {{ Local-Cell-InformationItemIE-ResourceStatusInd }}

Local-Cell-InformationItemIE-ResourceStatusInd NBAP-PROTOCOL-IES ::= {
	{ ID id-Local-Cell-InformationItem-ResourceStatusInd   CRITICALITY ignore	TYPE Local-Cell-InformationItem-ResourceStatusInd		PRESENCE mandatory }
}

Local-Cell-InformationItem-ResourceStatusInd ::= SEQUENCE {
	local-CellID								Local-Cell-ID,
	addorDeleteIndicator						AddorDeleteIndicator,
	dl-or-global-capacityCredit					DL-or-Global-CapacityCredit					OPTIONAL,
	-- This IE shall be present if AddorDeleteIndicator IE is set to “add”
	ul-capacityCredit							UL-CapacityCredit							OPTIONAL,
	commonChannelsCapacityConsumptionLaw 		CommonChannelsCapacityConsumptionLaw		OPTIONAL,
	-- This IE shall be present if AddorDeleteIndicator IE is set to “add”
	dedicatedChannelsCapacityConsumptionLaw 	DedicatedChannelsCapacityConsumptionLaw		OPTIONAL,
	-- This IE shall be present if AddorDeleteIndicator IE is set to “add”
	maximumDL-PowerCapability					MaximumDL-PowerCapability					OPTIONAL,
	-- This IE shall be present if AddorDeleteIndicator IE is set to “add”
	minSpreadingFactor							MinSpreadingFactor							OPTIONAL,
	-- This IE shall be present if AddorDeleteIndicator IE is set to “add”
	minimumDL-PowerCapability					MinimumDL-PowerCapability					OPTIONAL,
	-- This IE shall be present if AddorDeleteIndicator IE is set to “add”
	local-Cell-Group-ID							Local-Cell-ID								OPTIONAL,
	iE-Extensions								ProtocolExtensionContainer { { Local-Cell-InformationItem-ResourceStatusInd-ExtIEs} }	OPTIONAL,
	...
}

Local-Cell-InformationItem-ResourceStatusInd-ExtIEs NBAP-PROTOCOL-EXTENSION ::= {
	{ ID	id-ReferenceClockAvailability		CRITICALITY ignore		EXTENSION ReferenceClockAvailability			PRESENCE	optional }|
	-- This IE shall be present if AddorDeleteIndicator IE is set to “add“ and the Local Cell is related to a TDD cell
	{ ID	id-Power-Local-Cell-Group-ID		CRITICALITY ignore		EXTENSION Local-Cell-ID				PRESENCE	optional }|
	{ ID	id-HSDPA-Capability					CRITICALITY ignore		EXTENSION HSDPA-Capability			PRESENCE	optional }|
	{ ID	id-E-DCH-Capability					CRITICALITY ignore		EXTENSION E-DCH-Capability			PRESENCE	optional }|
	{ ID	id-E-DCH-TTI2ms-Capability			CRITICALITY ignore		EXTENSION E-DCH-TTI2ms-Capability			PRESENCE	conditional }|
	-- The IE shall be present if E-DCH Capability IE is set to ”E-DCH Capable”.
	{ ID	id-E-DCH-SF-Capability				CRITICALITY ignore		EXTENSION E-DCH-SF-Capability			PRESENCE	conditional }|
	-- The IE shall be present if E-DCH Capability IE is set to ”E-DCH Capable”.
	{ ID	id-E-DCH-HARQ-Combining-Capability				CRITICALITY ignore			EXTENSION E-DCH-HARQ-Combining-Capability			PRESENCE	conditional }|
	-- The IE shall be present if E-DCH Capability IE is set to ”E-DCH Capable”.
	{ ID	id-E-DCH-CapacityConsumptionLaw		CRITICALITY ignore		EXTENSION E-DCHCapacityConsumptionLaw		PRESENCE	optional }|
	{ ID	id-F-DPCH-Capability				CRITICALITY ignore		EXTENSION F-DPCH-Capability		PRESENCE	optional }|
	{ ID	id-E-DCH-TDD-CapacityConsumptionLaw		CRITICALITY ignore		EXTENSION E-DCH-TDD-CapacityConsumptionLaw		PRESENCE	optional }|
	{ ID	id-ContinuousPacketConnectivityDTX-DRX-Capability			CRITICALITY ignore			EXTENSION ContinuousPacketConnectivityDTX-DRX-Capability			PRESENCE	optional }|
	{ ID	id-Max-UE-DTX-Cycle					CRITICALITY ignore		EXTENSION Max-UE-DTX-Cycle		PRESENCE	conditional }|
	-- The IE shall be present if Continuous Packet Connectivity DTX-DRX Capability IE is present and set to ”Continuous Packet Connectivity DTX-DRX Capable”.
	{ ID	id-ContinuousPacketConnectivityHS-SCCH-less-Capability		CRITICALITY ignore			EXTENSION ContinuousPacketConnectivityHS-SCCH-less-Capability			PRESENCE	optional }|
	{ ID	id-MIMO-Capability					CRITICALITY ignore		EXTENSION MIMO-Capability		PRESENCE	optional }|
	{ ID	id-SixtyfourQAM-DL-Capability		CRITICALITY ignore		EXTENSION SixtyfourQAM-DL-Capability		PRESENCE	optional }|
	{ ID	id-MBMS-Capability					CRITICALITY ignore		EXTENSION MBMS-Capability		PRESENCE	optional }|
	{ ID	id-Enhanced-FACH-Capability			CRITICALITY ignore		EXTENSION Enhanced-FACH-Capability		PRESENCE	optional }|
	{ ID	id-Enhanced-PCH-Capability			CRITICALITY ignore		EXTENSION Enhanced-PCH-Capability		PRESENCE	conditional }|
	-- The IE shall be present if Enhanced FACH Capability IE is set to ”Enhanced FACH Capable”.
	{ ID	id-SixteenQAM-UL-Capability			CRITICALITY ignore		EXTENSION SixteenQAM-UL-Capability		PRESENCE	optional }|
	{ ID	id-HSDSCH-MACdPDU-SizeCapability	CRITICALITY ignore		EXTENSION HSDSCH-MACdPDU-SizeCapability		PRESENCE	optional }|
	{ ID	id-MBSFN-Only-Mode-Capability		CRITICALITY ignore		EXTENSION MBSFN-Only-Mode-Capability		PRESENCE	optional }|
	{ ID	id-F-DPCH-SlotFormatCapability		CRITICALITY ignore		EXTENSION F-DPCH-SlotFormatCapability		PRESENCE	optional }|
	{ ID	id-E-DCH-MACdPDU-SizeCapability		CRITICALITY ignore		EXTENSION E-DCH-MACdPDU-SizeCapability		PRESENCE	optional }|
	{ ID 	id-Common-EDCH-Capability			CRITICALITY ignore		EXTENSION Common-EDCH-Capability		PRESENCE	optional }|
	{ ID 	id-E-AI-Capability				CRITICALITY ignore		EXTENSION E-AI-Capability		PRESENCE	optional }|
	-- The IE shall be present if Common E-DCH Capability IE is present and set to ”Common E-DCH Capable”.
	{ ID id-Enhanced-UE-DRX-Capability				CRITICALITY ignore		EXTENSION Enhanced-UE-DRX-Capability		PRESENCE	optional }|
	-- The IE shall be present if Common E-DCH Capability IE is present and set to ”Common E-DCH”.
	{ ID id-Enhanced-UE-DRX-CapabilityLCR			CRITICALITY ignore		EXTENSION Enhanced-UE-DRX-Capability		PRESENCE	optional }|
	{ ID id-E-DPCCH-Power-Boosting-Capability		CRITICALITY ignore		EXTENSION E-DPCCH-Power-Boosting-Capability		PRESENCE	optional }|
	{ ID	id-SixtyfourQAM-DL-MIMO-Combined-Capability		CRITICALITY ignore		EXTENSION SixtyfourQAM-DL-MIMO-Combined-Capability			PRESENCE	conditional }|
	{ ID id-Multi-Cell-Capability-Info				CRITICALITY ignore		EXTENSION Multi-Cell-Capability-Info		PRESENCE	optional },
	...

}

Local-Cell-Group-InformationList-ResourceStatusInd ::= SEQUENCE(SIZE (1..maxLocalCellinNodeB)) OF ProtocolIE-Single-Container {{ Local-Cell-Group-InformationItemIE-ResourceStatusInd }}

Local-Cell-Group-InformationItemIE-ResourceStatusInd NBAP-PROTOCOL-IES ::= {
	{ ID id-Local-Cell-Group-InformationItem-ResourceStatusInd   CRITICALITY ignore	TYPE Local-Cell-Group-InformationItem-ResourceStatusInd		PRESENCE mandatory }
}

Local-Cell-Group-InformationItem-ResourceStatusInd::= SEQUENCE {
	local-Cell-Group-ID							Local-Cell-ID,
	dl-or-global-capacityCredit					DL-or-Global-CapacityCredit,
	ul-capacityCredit							UL-CapacityCredit		OPTIONAL,
	commonChannelsCapacityConsumptionLaw 		CommonChannelsCapacityConsumptionLaw,
	dedicatedChannelsCapacityConsumptionLaw 	DedicatedChannelsCapacityConsumptionLaw,
	iE-Extensions								ProtocolExtensionContainer { { Local-Cell-Group-InformationItem-ResourceStatusInd-ExtIEs} }	OPTIONAL,
	...
}

Local-Cell-Group-InformationItem-ResourceStatusInd-ExtIEs NBAP-PROTOCOL-EXTENSION ::= {
	{ ID id-E-DCH-CapacityConsumptionLaw		CRITICALITY ignore		EXTENSION E-DCHCapacityConsumptionLaw		PRESENCE optional }|
	{ ID id-E-DCH-TDD-CapacityConsumptionLaw	CRITICALITY ignore		EXTENSION E-DCH-TDD-CapacityConsumptionLaw		PRESENCE optional },
	...
}

Power-Local-Cell-Group-InformationList-ResourceStatusInd ::= SEQUENCE(SIZE (1..maxLocalCellinNodeB)) OF ProtocolIE-Single-Container {{ Power-Local-Cell-Group-InformationItemIE-ResourceStatusInd }}

Power-Local-Cell-Group-InformationItemIE-ResourceStatusInd NBAP-PROTOCOL-IES ::= {
	{ ID id-Power-Local-Cell-Group-InformationItem-ResourceStatusInd	CRITICALITY ignore	TYPE Power-Local-Cell-Group-InformationItem-ResourceStatusInd		PRESENCE mandatory	}
}

Power-Local-Cell-Group-InformationItem-ResourceStatusInd::= SEQUENCE {
	power-Local-Cell-Group-ID					Local-Cell-ID,
	maximumDL-PowerCapability					MaximumDL-PowerCapability,
	iE-Extensions								ProtocolExtensionContainer { { Power-Local-Cell-Group-InformationItem-ResourceStatusInd-ExtIEs} }	OPTIONAL,
	...
}

Power-Local-Cell-Group-InformationItem-ResourceStatusInd-ExtIEs NBAP-PROTOCOL-EXTENSION ::= {
	...
}

ServiceImpacting-ResourceStatusInd ::= SEQUENCE {
	local-Cell-InformationList				Local-Cell-InformationList2-ResourceStatusInd	OPTIONAL,
	local-Cell-Group-InformationList		Local-Cell-Group-InformationList2-ResourceStatusInd	OPTIONAL,
	cCP-InformationList						CCP-InformationList-ResourceStatusInd 			OPTIONAL,
	cell-InformationList					Cell-InformationList-ResourceStatusInd 			OPTIONAL,
	iE-Extensions							ProtocolExtensionContainer { { ServiceImpactingItem-ResourceStatusInd-ExtIEs} }		OPTIONAL,
	...
}

ServiceImpactingItem-ResourceStatusInd-ExtIEs NBAP-PROTOCOL-EXTENSION ::= {
	{ ID id-Power-Local-Cell-Group-InformationList2-ResourceStatusInd		CRITICALITY ignore	EXTENSION Power-Local-Cell-Group-InformationList2-ResourceStatusInd		PRESENCE optional	},
	...
}

Local-Cell-InformationList2-ResourceStatusInd ::= SEQUENCE(SIZE (1..maxLocalCellinNodeB)) OF ProtocolIE-Single-Container {{ Local-Cell-InformationItemIE2-ResourceStatusInd }}

Local-Cell-InformationItemIE2-ResourceStatusInd NBAP-PROTOCOL-IES ::= {
	{ ID id-Local-Cell-InformationItem2-ResourceStatusInd   CRITICALITY ignore	TYPE Local-Cell-InformationItem2-ResourceStatusInd		PRESENCE mandatory }
}

Local-Cell-InformationItem2-ResourceStatusInd ::= SEQUENCE {
	local-Cell-ID								Local-Cell-ID,
	dl-or-global-capacityCredit					DL-or-Global-CapacityCredit				OPTIONAL,
	ul-capacityCredit							UL-CapacityCredit						OPTIONAL,
	commonChannelsCapacityConsumptionLaw		CommonChannelsCapacityConsumptionLaw	OPTIONAL,
	dedicatedChannelsCapacityConsumptionLaw		DedicatedChannelsCapacityConsumptionLaw	OPTIONAL,
	maximum-DL-PowerCapability					MaximumDL-PowerCapability				OPTIONAL,
	minSpreadingFactor							MinSpreadingFactor						OPTIONAL,
	minimumDL-PowerCapability					MinimumDL-PowerCapability				OPTIONAL,
	iE-Extensions							ProtocolExtensionContainer { { Local-Cell-InformationItem2-ResourceStatusInd-ExtIEs} }		OPTIONAL,
	...
}

Local-Cell-InformationItem2-ResourceStatusInd-ExtIEs NBAP-PROTOCOL-EXTENSION ::= {
	{ ID	id-ReferenceClockAvailability		CRITICALITY ignore			EXTENSION ReferenceClockAvailability			PRESENCE	optional }|
	{ ID	id-HSDPA-Capability					CRITICALITY ignore			EXTENSION HSDPA-Capability			PRESENCE	optional }|
	{ ID	id-E-DCH-Capability					CRITICALITY ignore			EXTENSION E-DCH-Capability			PRESENCE	optional }|
	{ ID	id-E-DCH-TTI2ms-Capability			CRITICALITY ignore			EXTENSION E-DCH-TTI2ms-Capability			PRESENCE	conditional }|
	-- The IE shall be present if E-DCH Capability IE is set to ”E-DCH Capable”.
	{ ID	id-E-DCH-SF-Capability				CRITICALITY ignore			EXTENSION E-DCH-SF-Capability			PRESENCE	conditional }|
	-- The IE shall be present if E-DCH Capability IE is set to ”E-DCH Capable”.
	{ ID	id-E-DCH-HARQ-Combining-Capability				CRITICALITY ignore			EXTENSION E-DCH-HARQ-Combining-Capability			PRESENCE	conditional }|
	-- The IE shall be present if E-DCH Capability IE is set to ”E-DCH Capable”.
	{ ID	id-E-DCH-CapacityConsumptionLaw		CRITICALITY ignore			EXTENSION E-DCHCapacityConsumptionLaw			PRESENCE	optional }|
	{ ID	id-F-DPCH-Capability				CRITICALITY ignore			EXTENSION F-DPCH-Capability			PRESENCE	optional }|
	{ ID	id-E-DCH-TDD-CapacityConsumptionLaw		CRITICALITY ignore		EXTENSION E-DCH-TDD-CapacityConsumptionLaw		PRESENCE	optional }|
	{ ID	id-ContinuousPacketConnectivityDTX-DRX-Capability			CRITICALITY ignore			EXTENSION ContinuousPacketConnectivityDTX-DRX-Capability			PRESENCE	optional }|
	{ ID	id-Max-UE-DTX-Cycle					CRITICALITY ignore			EXTENSION Max-UE-DTX-Cycle			PRESENCE	conditional }|
	-- The IE shall be present if Continuous Packet Connectivity DTX-DRX Capability IE is present and set to ”Continuous Packet Connectivity DTX-DRX Capable”.
	{ ID	id-ContinuousPacketConnectivityHS-SCCH-less-Capability		CRITICALITY ignore			EXTENSION ContinuousPacketConnectivityHS-SCCH-less-Capability			PRESENCE	optional }|
	{ ID	id-MIMO-Capability					CRITICALITY ignore		EXTENSION MIMO-Capability			PRESENCE	optional }|
	{ ID	id-SixtyfourQAM-DL-Capability		CRITICALITY ignore		EXTENSION SixtyfourQAM-DL-Capability			PRESENCE	optional }|
	{ ID	id-MBMS-Capability					CRITICALITY ignore		EXTENSION MBMS-Capability			PRESENCE	optional }|
	{ ID	id-Enhanced-FACH-Capability			CRITICALITY ignore		EXTENSION Enhanced-FACH-Capability			PRESENCE	optional }|
	{ ID	id-Enhanced-PCH-Capability			CRITICALITY ignore		EXTENSION Enhanced-PCH-Capability			PRESENCE	conditional }|
	-- The IE shall be present if Enhanced FACH Capability IE is set to ”Enhanced FACH Capable”.
	{ ID	id-SixteenQAM-UL-Capability			CRITICALITY ignore		EXTENSION SixteenQAM-UL-Capability			PRESENCE	optional }|
	{ ID	id-HSDSCH-MACdPDU-SizeCapability	CRITICALITY ignore		EXTENSION HSDSCH-MACdPDU-SizeCapability			PRESENCE	optional }|
	{ ID	id-MBSFN-Only-Mode-Capability		CRITICALITY ignore		EXTENSION MBSFN-Only-Mode-Capability			PRESENCE	optional }|
	{ ID	id-F-DPCH-SlotFormatCapability		CRITICALITY ignore		EXTENSION F-DPCH-SlotFormatCapability			PRESENCE	optional }|
	{ ID id-E-DCH-MACdPDU-SizeCapability		CRITICALITY ignore		EXTENSION E-DCH-MACdPDU-SizeCapability			PRESENCE	optional }|
	{ ID 	id-Common-EDCH-Capability			CRITICALITY ignore		EXTENSION Common-EDCH-Capability			PRESENCE	optional }|
	{ ID 	id-E-AI-Capability				CRITICALITY ignore		EXTENSION E-AI-Capability			PRESENCE	optional }|
	-- The IE shall be present if Common E-DCH Capability IE is present and set to ”Common E-DCH Capable”.
	{ ID 	id-Enhanced-UE-DRX-Capability			CRITICALITY ignore		EXTENSION Enhanced-UE-DRX-Capability			PRESENCE	optional }|
	-- The IE shall be present if Common E-DCH Capability IE is present and set to ”Common E-DCH Capable”.
	{ ID 	id-Enhanced-UE-DRX-CapabilityLCR	CRITICALITY ignore		EXTENSION Enhanced-UE-DRX-Capability			PRESENCE	optional }|
	{ ID 	id-E-DPCCH-Power-Boosting-Capability		CRITICALITY ignore	EXTENSION E-DPCCH-Power-Boosting-Capability							PRESENCE	optional }|
	{ ID	id-SixtyfourQAM-DL-MIMO-Combined-Capability		CRITICALITY ignore		EXTENSION SixtyfourQAM-DL-MIMO-Combined-Capability			PRESENCE	conditional }|
	{ ID 	id-Multi-Cell-Capability-Info			CRITICALITY ignore		EXTENSION Multi-Cell-Capability-Info			PRESENCE	optional },
	...
}

Local-Cell-Group-InformationList2-ResourceStatusInd ::= SEQUENCE(SIZE (1..maxLocalCellinNodeB)) OF ProtocolIE-Single-Container {{ Local-Cell-Group-InformationItemIE2-ResourceStatusInd }}

Local-Cell-Group-InformationItemIE2-ResourceStatusInd NBAP-PROTOCOL-IES ::= {
	{ ID id-Local-Cell-Group-InformationItem2-ResourceStatusInd   CRITICALITY ignore	TYPE Local-Cell-Group-InformationItem2-ResourceStatusInd		PRESENCE mandatory }
}

Local-Cell-Group-InformationItem2-ResourceStatusInd ::= SEQUENCE {
	local-Cell-Group-ID							Local-Cell-ID,
	dl-or-global-capacityCredit					DL-or-Global-CapacityCredit					OPTIONAL,
	ul-capacityCredit							UL-CapacityCredit							OPTIONAL,
	commonChannelsCapacityConsumptionLaw		CommonChannelsCapacityConsumptionLaw		OPTIONAL,
	dedicatedChannelsCapacityConsumptionLaw		DedicatedChannelsCapacityConsumptionLaw		OPTIONAL,
	iE-Extensions							ProtocolExtensionContainer { { Local-Cell-Group-InformationItem2-ResourceStatusInd-ExtIEs} }		OPTIONAL,
	...
}

Local-Cell-Group-InformationItem2-ResourceStatusInd-ExtIEs NBAP-PROTOCOL-EXTENSION ::= {
	{ ID id-E-DCH-CapacityConsumptionLaw		CRITICALITY ignore		EXTENSION E-DCHCapacityConsumptionLaw		PRESENCE optional }|
	{ ID id-E-DCH-TDD-CapacityConsumptionLaw	CRITICALITY ignore		EXTENSION E-DCH-TDD-CapacityConsumptionLaw	 PRESENCE	optional },
	...
}

CCP-InformationList-ResourceStatusInd ::= SEQUENCE (SIZE (1..maxCCPinNodeB)) OF ProtocolIE-Single-Container {{ CCP-InformationItemIE-ResourceStatusInd }}

CCP-InformationItemIE-ResourceStatusInd NBAP-PROTOCOL-IES ::= {
	{ ID id-CCP-InformationItem-ResourceStatusInd   CRITICALITY ignore	TYPE CCP-InformationItem-ResourceStatusInd		PRESENCE mandatory }
}

CCP-InformationItem-ResourceStatusInd ::= SEQUENCE {
	communicationControlPortID				CommunicationControlPortID,
	resourceOperationalState				ResourceOperationalState,
	availabilityStatus						AvailabilityStatus,
	iE-Extensions							ProtocolExtensionContainer { { CCP-InformationItem-ResourceStatusInd-ExtIEs} }		OPTIONAL,
	...
}

CCP-InformationItem-ResourceStatusInd-ExtIEs NBAP-PROTOCOL-EXTENSION ::= {
	...
}

Cell-InformationList-ResourceStatusInd ::= SEQUENCE (SIZE (1..maxCellinNodeB)) OF ProtocolIE-Single-Container {{ Cell-InformationItemIE-ResourceStatusInd }}

Cell-InformationItemIE-ResourceStatusInd NBAP-PROTOCOL-IES ::= {
	{ ID id-Cell-InformationItem-ResourceStatusInd   CRITICALITY ignore	TYPE Cell-InformationItem-ResourceStatusInd		PRESENCE mandatory }
}

Cell-InformationItem-ResourceStatusInd  ::= SEQUENCE {
	c-ID									C-ID,
	resourceOperationalState 				ResourceOperationalState						OPTIONAL,
	availabilityStatus						AvailabilityStatus								OPTIONAL,
	primary-SCH-Information					P-SCH-Information-ResourceStatusInd				OPTIONAL, -- FDD only
	secondary-SCH-Information				S-SCH-Information-ResourceStatusInd				OPTIONAL, -- FDD only
	primary-CPICH-Information				P-CPICH-Information-ResourceStatusInd			OPTIONAL, -- FDD only
	secondary-CPICH-Information				S-CPICH-InformationList-ResourceStatusInd		OPTIONAL, -- FDD only
	primary-CCPCH-Information				P-CCPCH-Information-ResourceStatusInd			OPTIONAL,
	bCH-Information							BCH-Information-ResourceStatusInd 				OPTIONAL,
	secondary-CCPCH-InformationList			S-CCPCH-InformationList-ResourceStatusInd		OPTIONAL,
	pCH-Information							PCH-Information-ResourceStatusInd 				OPTIONAL,
	pICH-Information						PICH-Information-ResourceStatusInd				OPTIONAL,
	fACH-InformationList					FACH-InformationList-ResourceStatusInd 			OPTIONAL,
	pRACH-InformationList					PRACH-InformationList-ResourceStatusInd			OPTIONAL,
	rACH-InformationList					RACH-InformationList-ResourceStatusInd 			OPTIONAL,
	aICH-InformationList					AICH-InformationList-ResourceStatusInd 			OPTIONAL, -- FDD only
	notUsed-1-pCPCH-InformationList			NULL											OPTIONAL,
	notUsed-2-cPCH-InformationList			NULL											OPTIONAL,
	notUsed-3-aP-AICH-InformationList		NULL											OPTIONAL,
	notUsed-4-cDCA-ICH-InformationList		NULL											OPTIONAL,
	sCH-Information							SCH-Information-ResourceStatusInd 				OPTIONAL, -- Applicable to 3.84Mcps TDD only
	iE-Extensions							ProtocolExtensionContainer { { Cell-InformationItem-ResourceStatusInd-ExtIEs} }	OPTIONAL,
	...
}

Cell-InformationItem-ResourceStatusInd-ExtIEs NBAP-PROTOCOL-EXTENSION ::= {
	{ ID id-FPACH-LCR-InformationList-ResourceStatusInd			CRITICALITY ignore	EXTENSION FPACH-LCR-InformationList-ResourceStatusInd			PRESENCE optional }|	-- Applicable to 1.28Mcps TDD only
	{ ID id-DwPCH-LCR-Information-ResourceStatusInd				CRITICALITY ignore	EXTENSION DwPCH-LCR-Information-ResourceStatusInd					PRESENCE optional }|	-- Applicable to 1.28Mcps TDD only
	{ ID id-HSDSCH-Resources-Information-ResourceStatusInd		CRITICALITY ignore	EXTENSION HS-DSCH-Resources-Information-ResourceStatusInd			PRESENCE optional }|	-- For 1.28Mcps TDD, this HS-DSCH Resource Information is for the first Frequency repetition, HS-DSCH Resource Information for Frequency repetitions 2 and on, should be defined in MultipleFreq-HS-DSCH-Resources-InformationList-ResourceStatusInd.
	{ ID id-MICH-Information-ResourceStatusInd					CRITICALITY ignore	EXTENSION Common-PhysicalChannel-Status-Information				PRESENCE optional }|
	{ ID id-S-CCPCH-InformationListExt-ResourceStatusInd		CRITICALITY ignore	EXTENSION S-CCPCH-InformationListExt-ResourceStatusInd			PRESENCE optional }|
	-- Applicable to 3.84Mcps TDD only, used when there are more than maxSCCPCHCell SCCPCHs in the message.
	{ ID id-S-CCPCH-LCR-InformationListExt-ResourceStatusInd	CRITICALITY ignore	EXTENSION S-CCPCH-LCR-InformationListExt-ResourceStatusInd		PRESENCE optional }|
	-- Applicable to 1.28Mcps TDD only, used when there are more than maxSCCPCHCell SCCPCHs in the message.
	{ ID id-E-DCH-Resources-Information-ResourceStatusInd		CRITICALITY ignore	EXTENSION E-DCH-Resources-Information-ResourceStatusInd			PRESENCE optional }|
	-- For 1.28Mcps TDD, this E-DCH Resource Information is for the first Frequency repetition, E-DCH Resource Information for Frequency repetitions 2 and on, should be defined in MultipleFreq-E-DCH-Resources-InformationList-ResourceStatusInd.
	{ ID id-PLCCH-InformationList-ResourceStatusInd				CRITICALITY ignore	EXTENSION PLCCH-InformationList-ResourceStatusInd			
	PRESENCE optional }|
	{ ID id-P-CCPCH-768-Information-ResourceStatusInd			CRITICALITY ignore	EXTENSION Common-PhysicalChannel-Status-Information768			PRESENCE optional }|
	{ ID id-S-CCPCH-768-InformationList-ResourceStatusInd		CRITICALITY ignore	EXTENSION S-CCPCH-768-InformationList-ResourceStatusInd			PRESENCE optional }|
	{ ID id-PICH-768-Information-ResourceStatusInd				CRITICALITY ignore	EXTENSION Common-PhysicalChannel-Status-Information768		PRESENCE optional }|
	{ ID id-PRACH-768-InformationList-ResourceStatusInd			CRITICALITY ignore	EXTENSION PRACH-768-InformationList-ResourceStatusInd			PRESENCE optional }|
	{ ID id-SCH-768-Information-ResourceStatusInd				CRITICALITY ignore	EXTENSION Common-PhysicalChannel-Status-Information768		PRESENCE optional }|
	{ ID id-MICH-768-Information-ResourceStatusInd				CRITICALITY ignore	EXTENSION Common-PhysicalChannel-Status-Information768		PRESENCE optional }|
	{ ID id-E-RUCCH-InformationList-ResourceStatusInd			CRITICALITY ignore	EXTENSION E-RUCCH-InformationList-ResourceStatusInd			PRESENCE optional }|
	{ ID id-E-RUCCH-768-InformationList-ResourceStatusInd			CRITICALITY ignore	EXTENSION E-RUCCH-768-InformationList-ResourceStatusInd			PRESENCE optional }|
	{ ID id-Cell-Frequency-List-Information-LCR-MulFreq-ResourceStatusInd		CRITICALITY ignore		EXTENSION Cell-Frequency-List-Information-LCR-MulFreq-ResourceStatusInd			PRESENCE optional }|	-- Applicable to 1.28Mcps TDD when using multiple frequencies
	{ ID id-UPPCH-LCR-InformationList-ResourceStatusInd							CRITICALITY ignore		EXTENSION UPPCH-LCR-InformationList-ResourceStatusInd					PRESENCE optional }|	-- Applicable to 1.28Mcps TDD only
	{ ID id-multipleFreq-HS-DSCH-Resources-InformationList-ResourceStatusInd	CRITICALITY ignore		EXTENSION MultipleFreq-HS-DSCH-Resources-InformationList-ResourceStatusInd	PRESENCE optional }|
	-- Applicable to 1.28Mcps TDD when using multiple frequencies, This HS-DSCH Resource Information is for the 2nd and beyond frequencies.
	{ ID id-MultipleFreq-E-DCH-Resources-InformationList-ResourceStatusInd		CRITICALITY ignore		EXTENSION MultipleFreq-E-DCH-Resources-InformationList-ResourceStatusInd	PRESENCE optional },
	-- Applicable to 1.28Mcps TDD when using multiple frequencies. This E-DCH Resource Information is for the 2nd and beyond frequencies.
	...
}

P-SCH-Information-ResourceStatusInd ::= ProtocolIE-Single-Container {{ P-SCH-InformationIE-ResourceStatusInd }}

P-SCH-InformationIE-ResourceStatusInd NBAP-PROTOCOL-IES ::= {
	{ ID id-P-SCH-Information   CRITICALITY ignore	TYPE Common-PhysicalChannel-Status-Information		PRESENCE mandatory }
}

S-SCH-Information-ResourceStatusInd ::= ProtocolIE-Single-Container {{ S-SCH-InformationIE-ResourceStatusInd }}

S-SCH-InformationIE-ResourceStatusInd NBAP-PROTOCOL-IES ::= {
	{ ID id-S-SCH-Information   CRITICALITY ignore	TYPE Common-PhysicalChannel-Status-Information		PRESENCE mandatory }
}

P-CPICH-Information-ResourceStatusInd ::= ProtocolIE-Single-Container {{ P-CPICH-InformationIE-ResourceStatusInd }}

P-CPICH-InformationIE-ResourceStatusInd NBAP-PROTOCOL-IES ::= {
	{ ID id-P-CPICH-Information   CRITICALITY ignore	TYPE Common-PhysicalChannel-Status-Information		PRESENCE mandatory }
}

S-CPICH-InformationList-ResourceStatusInd ::= SEQUENCE (SIZE (1..maxSCPICHCell)) OF ProtocolIE-Single-Container {{ S-CPICH-InformationItemIE-ResourceStatusInd }}

S-CPICH-InformationItemIE-ResourceStatusInd NBAP-PROTOCOL-IES ::= {
	{ ID id-S-CPICH-Information   CRITICALITY ignore	TYPE Common-PhysicalChannel-Status-Information		PRESENCE mandatory }
}

P-CCPCH-Information-ResourceStatusInd ::= ProtocolIE-Single-Container {{ P-CCPCH-InformationIE-ResourceStatusInd }}

P-CCPCH-InformationIE-ResourceStatusInd NBAP-PROTOCOL-IES ::= {
	{ ID id-P-CCPCH-Information   CRITICALITY ignore	TYPE Common-PhysicalChannel-Status-Information		PRESENCE mandatory }
}

BCH-Information-ResourceStatusInd ::= ProtocolIE-Single-Container {{ BCH-InformationIE-ResourceStatusInd }}

BCH-InformationIE-ResourceStatusInd NBAP-PROTOCOL-IES ::= {
	{ ID id-BCH-Information   CRITICALITY ignore	TYPE Common-TransportChannel-Status-Information		PRESENCE mandatory }
}

S-CCPCH-InformationList-ResourceStatusInd ::= SEQUENCE (SIZE (1..maxSCCPCHCell)) OF ProtocolIE-Single-Container {{ S-CCPCH-InformationItemIE-ResourceStatusInd }}

S-CCPCH-InformationItemIE-ResourceStatusInd NBAP-PROTOCOL-IES ::= {
	{ ID id-S-CCPCH-Information   CRITICALITY ignore	TYPE Common-PhysicalChannel-Status-Information		PRESENCE mandatory }
}

PCH-Information-ResourceStatusInd ::= ProtocolIE-Single-Container {{ PCH-InformationIE-ResourceStatusInd }}

PCH-InformationIE-ResourceStatusInd NBAP-PROTOCOL-IES ::= {
	{ ID id-PCH-Information   CRITICALITY ignore	TYPE Common-TransportChannel-Status-Information		PRESENCE mandatory }
}

PICH-Information-ResourceStatusInd ::= ProtocolIE-Single-Container {{ PICH-InformationIE-ResourceStatusInd }}

PICH-InformationIE-ResourceStatusInd NBAP-PROTOCOL-IES ::= {
	{ ID id-PICH-Information   CRITICALITY ignore	TYPE Common-PhysicalChannel-Status-Information		PRESENCE mandatory }
}

FACH-InformationList-ResourceStatusInd ::= SEQUENCE (SIZE (1..maxFACHCell)) OF ProtocolIE-Single-Container {{ FACH-InformationItemIE-ResourceStatusInd }}

FACH-InformationItemIE-ResourceStatusInd NBAP-PROTOCOL-IES ::= {
	{ ID id-FACH-Information   CRITICALITY ignore	TYPE Common-TransportChannel-Status-Information		PRESENCE mandatory }
}

PRACH-InformationList-ResourceStatusInd ::= SEQUENCE (SIZE (1..maxPRACHCell)) OF ProtocolIE-Single-Container {{ PRACH-InformationItemIE-ResourceStatusInd }}

PRACH-InformationItemIE-ResourceStatusInd NBAP-PROTOCOL-IES ::= {
	{ ID id-PRACH-Information   CRITICALITY ignore	TYPE Common-PhysicalChannel-Status-Information		PRESENCE mandatory }
}

RACH-InformationList-ResourceStatusInd ::= SEQUENCE (SIZE (1..maxPRACHCell)) OF ProtocolIE-Single-Container {{ RACH-InformationItemIE-ResourceStatusInd }}

RACH-InformationItemIE-ResourceStatusInd NBAP-PROTOCOL-IES ::= {
	{ ID id-RACH-Information   CRITICALITY ignore	TYPE Common-TransportChannel-Status-Information		PRESENCE mandatory }
}

AICH-InformationList-ResourceStatusInd ::= SEQUENCE (SIZE (1..maxPRACHCell)) OF ProtocolIE-Single-Container {{ AICH-InformationItemIE-ResourceStatusInd }}

AICH-InformationItemIE-ResourceStatusInd NBAP-PROTOCOL-IES ::= {
	{ ID id-AICH-Information   CRITICALITY ignore	TYPE Common-PhysicalChannel-Status-Information		PRESENCE mandatory }
}

SCH-Information-ResourceStatusInd ::= ProtocolIE-Single-Container {{ SCH-InformationIE-ResourceStatusInd }}

SCH-InformationIE-ResourceStatusInd NBAP-PROTOCOL-IES ::= {
	{ ID id-SCH-Information   CRITICALITY ignore	TYPE Common-PhysicalChannel-Status-Information		PRESENCE mandatory }
}

FPACH-LCR-InformationList-ResourceStatusInd ::= SEQUENCE (SIZE (1..maxFPACHCell)) OF ProtocolIE-Single-Container {{ FPACH-LCR-InformationItemIE-ResourceStatusInd }}

FPACH-LCR-InformationItemIE-ResourceStatusInd NBAP-PROTOCOL-IES ::= {
	{ ID id-FPACH-LCR-Information  CRITICALITY ignore	TYPE Common-PhysicalChannel-Status-Information		PRESENCE mandatory }
}

DwPCH-LCR-Information-ResourceStatusInd ::= ProtocolIE-Single-Container {{ DwPCH-LCR-InformationIE-ResourceStatusInd }}

DwPCH-LCR-InformationIE-ResourceStatusInd NBAP-PROTOCOL-IES ::= {
	{ ID id-DwPCH-LCR-Information   CRITICALITY ignore	TYPE Common-PhysicalChannel-Status-Information		PRESENCE mandatory }
}

HS-DSCH-Resources-Information-ResourceStatusInd ::= SEQUENCE {
	resourceOperationalState			ResourceOperationalState,
	availabilityStatus					AvailabilityStatus,
	iE-Extensions						ProtocolExtensionContainer  {{ HS-DSCH-Resources-Information-ResourceStatusInd-ExtIEs }}		OPTIONAL,
	...
}

HS-DSCH-Resources-Information-ResourceStatusInd-ExtIEs NBAP-PROTOCOL-EXTENSION ::= {
	{ID id-UARFCNforNt		CRITICALITY ignore		EXTENSION UARFCN		PRESENCE optional},
	--  Applicable to 1.28Mcps TDD when using multiple frequencies.
	...
}

S-CCPCH-InformationListExt-ResourceStatusInd ::= SEQUENCE (SIZE (1..maxSCCPCHCellinExt)) OF ProtocolIE-Single-Container {{ S-CCPCH-InformationItemIE-ResourceStatusInd }}

S-CCPCH-LCR-InformationListExt-ResourceStatusInd ::= SEQUENCE (SIZE (1..maxSCCPCHCellinExtLCR)) OF ProtocolIE-Single-Container {{ S-CCPCH-InformationItemIE-ResourceStatusInd }}

E-DCH-Resources-Information-ResourceStatusInd ::= SEQUENCE {
	resourceOperationalState			ResourceOperationalState,
	availabilityStatus					AvailabilityStatus,
	iE-Extensions						ProtocolExtensionContainer  {{ E-DCH-Resources-Information-ResourceStatusInd-ExtIEs }}		OPTIONAL,
	...
}

E-DCH-Resources-Information-ResourceStatusInd-ExtIEs NBAP-PROTOCOL-EXTENSION ::= {
	{ID id-UARFCNforNt		CRITICALITY ignore		EXTENSION UARFCN		PRESENCE optional},
	--  Applicable to 1.28Mcps TDD when using multiple frequencies.
	...
}

PLCCH-InformationList-ResourceStatusInd ::= SEQUENCE (SIZE (1..maxPLCCHCell)) OF ProtocolIE-Single-Container {{ PLCCH-InformationItemIE-ResourceStatusInd }}

PLCCH-InformationItemIE-ResourceStatusInd NBAP-PROTOCOL-IES ::= {
	{ ID id-PLCCH-Information-ResourceStatusInd  CRITICALITY ignore	TYPE Common-PhysicalChannel-Status-Information		PRESENCE mandatory }
}

S-CCPCH-768-InformationList-ResourceStatusInd ::= SEQUENCE (SIZE (1..maxSCCPCHCell768)) OF ProtocolIE-Single-Container {{ S-CCPCH-768-InformationItemIE-ResourceStatusInd }}

S-CCPCH-768-InformationItemIE-ResourceStatusInd NBAP-PROTOCOL-IES ::= {
	{ ID id-S-CCPCH-768-Information-ResourceStatusInd   CRITICALITY ignore	TYPE Common-PhysicalChannel-Status-Information768		PRESENCE mandatory }
}

PRACH-768-InformationList-ResourceStatusInd ::= SEQUENCE (SIZE (1..maxPRACHCell)) OF ProtocolIE-Single-Container {{ PRACH-768-InformationItemIE-ResourceStatusInd }}

PRACH-768-InformationItemIE-ResourceStatusInd NBAP-PROTOCOL-IES ::= {
	{ ID id-PRACH-768-Information   CRITICALITY ignore	TYPE Common-PhysicalChannel-Status-Information768		PRESENCE mandatory }
}

E-RUCCH-InformationList-ResourceStatusInd ::= SEQUENCE (SIZE (1..maxE-RUCCHCell)) OF ProtocolIE-Single-Container {{ E-RUCCH-InformationItemIE-ResourceStatusInd }}

E-RUCCH-InformationItemIE-ResourceStatusInd NBAP-PROTOCOL-IES ::= {
	{ ID id-E-RUCCH-Information		CRITICALITY ignore	TYPE Common-PhysicalChannel-Status-Information		PRESENCE mandatory }
}

E-RUCCH-768-InformationList-ResourceStatusInd ::= SEQUENCE (SIZE (1..maxE-RUCCHCell)) OF ProtocolIE-Single-Container {{ E-RUCCH-768-InformationItemIE-ResourceStatusInd }}

E-RUCCH-768-InformationItemIE-ResourceStatusInd NBAP-PROTOCOL-IES ::= {
	{ ID id-E-RUCCH-768-Information		CRITICALITY ignore	TYPE Common-PhysicalChannel-Status-Information768		PRESENCE mandatory }
}

Cell-Frequency-List-Information-LCR-MulFreq-ResourceStatusInd ::= SEQUENCE (SIZE (1..maxFrequencyinCell)) OF ProtocolIE-Single-Container {{ Cell-Frequency-List-InformationIE-LCR-MulFreq-ResourceStatusInd }}

Cell-Frequency-List-InformationIE-LCR-MulFreq-ResourceStatusInd NBAP-PROTOCOL-IES ::= {
	{ ID id-Cell-Frequency-List-InformationItem-LCR-MulFreq-ResourceStatusInd   CRITICALITY ignore	TYPE Cell-Frequency-List-InformationItem-LCR-MulFreq-ResourceStatusInd		PRESENCE mandatory }
}

Cell-Frequency-List-InformationItem-LCR-MulFreq-ResourceStatusInd ::= SEQUENCE {
	uARFCN								UARFCN,
	resourceOperationalState			ResourceOperationalState,
	availabilityStatus					AvailabilityStatus,
	cause								Cause				OPTIONAL,
	iE-Extensions						ProtocolExtensionContainer {{ Cell-Frequency-List-InformationItem-LCR-MulFreq-ResourceStatusInd-ExtIEs }}		OPTIONAL,
	...
}

Cell-Frequency-List-InformationItem-LCR-MulFreq-ResourceStatusInd-ExtIEs NBAP-PROTOCOL-EXTENSION ::= {
	...
}

UPPCH-LCR-InformationList-ResourceStatusInd ::= SEQUENCE (SIZE (1..maxFrequencyinCell)) OF ProtocolIE-Single-Container {{ UPPCH-LCR-InformationIE-ResourceStatusInd }}

UPPCH-LCR-InformationIE-ResourceStatusInd NBAP-PROTOCOL-IES ::= {
	{ ID id-UPPCH-LCR-InformationItem-ResourceStatusInd		CRITICALITY ignore	TYPE UPPCH-LCR-InformationItem-ResourceStatusInd		PRESENCE mandatory }
}

UPPCH-LCR-InformationItem-ResourceStatusInd ::= SEQUENCE {
	uARFCN								UARFCN				OPTIONAL,
	uPPCHPositionLCR					UPPCHPositionLCR, 
	resourceOperationalState			ResourceOperationalState,
	availabilityStatus					AvailabilityStatus,
	iE-Extensions						ProtocolExtensionContainer  {{ UPPCH-LCR-InformationItem-ResourceStatusInd-ExtIEs }}		OPTIONAL,
	...
}

UPPCH-LCR-InformationItem-ResourceStatusInd-ExtIEs NBAP-PROTOCOL-EXTENSION ::= {
	...
}

MultipleFreq-HS-DSCH-Resources-InformationList-ResourceStatusInd ::= SEQUENCE (SIZE (1..maxFrequencyinCell-1)) OF ProtocolIE-Single-Container{{ MultipleFreq-HS-DSCH-Resources-InformationItem-ResourceStatusInd }} 
--Includes the 2nd through the max number of frequencies information repetitions.

MultipleFreq-HS-DSCH-Resources-InformationItem-ResourceStatusInd  NBAP-PROTOCOL-IES ::= {
	{ ID id-HSDSCH-Resources-Information-ResourceStatusInd	CRITICALITY ignore	TYPE HS-DSCH-Resources-Information-ResourceStatusInd		PRESENCE mandatory }
}

Power-Local-Cell-Group-InformationList2-ResourceStatusInd ::= SEQUENCE(SIZE (1..maxLocalCellinNodeB)) OF ProtocolIE-Single-Container {{ Power-Local-Cell-Group-InformationItemIE2-ResourceStatusInd }}

Power-Local-Cell-Group-InformationItemIE2-ResourceStatusInd NBAP-PROTOCOL-IES ::= {
	{ ID id-Power-Local-Cell-Group-InformationItem2-ResourceStatusInd	CRITICALITY ignore	TYPE Power-Local-Cell-Group-InformationItem2-ResourceStatusInd		PRESENCE mandatory	}
}

Power-Local-Cell-Group-InformationItem2-ResourceStatusInd::= SEQUENCE {
	power-Local-Cell-Group-ID			Local-Cell-ID,
	maximumDL-PowerCapability			MaximumDL-PowerCapability,
	iE-Extensions						ProtocolExtensionContainer { { Power-Local-Cell-Group-InformationItem2-ResourceStatusInd-ExtIEs} }	OPTIONAL,
	...
}

Power-Local-Cell-Group-InformationItem2-ResourceStatusInd-ExtIEs NBAP-PROTOCOL-EXTENSION ::= {
	...
}

MultipleFreq-E-DCH-Resources-InformationList-ResourceStatusInd ::= SEQUENCE (SIZE (1..maxFrequencyinCell-1)) OF ProtocolIE-Single-Container{{ MultipleFreq-E-DCH-Resources-InformationItem-ResourceStatusInd }} 
	--Includes the 2nd through the max number of frequencies information repetitions.

MultipleFreq-E-DCH-Resources-InformationItem-ResourceStatusInd  NBAP-PROTOCOL-IES ::= {
	{ ID id-E-DCH-Resources-Information-ResourceStatusInd	CRITICALITY ignore	TYPE E-DCH-Resources-Information-ResourceStatusInd		PRESENCE mandatory }
}

-- **************************************************************
--
-- SYSTEM INFORMATION UPDATE REQUEST
--
-- **************************************************************

SystemInformationUpdateRequest ::= SEQUENCE {
	protocolIEs				ProtocolIE-Container		{{SystemInformationUpdateRequest-IEs}},
	protocolExtensions		ProtocolExtensionContainer	{{SystemInformationUpdateRequest-Extensions}}		OPTIONAL,
	...
}

SystemInformationUpdateRequest-IEs NBAP-PROTOCOL-IES ::= {
	{ ID id-C-ID												CRITICALITY reject	TYPE C-ID					PRESENCE mandatory }|
	{ ID id-BCCH-ModificationTime								CRITICALITY reject	TYPE BCCH-ModificationTime				PRESENCE optional }|
	{ ID id-MIB-SB-SIB-InformationList-SystemInfoUpdateRqst		CRITICALITY reject	TYPE MIB-SB-SIB-InformationList-SystemInfoUpdateRqst				PRESENCE mandatory },
	...
}

SystemInformationUpdateRequest-Extensions NBAP-PROTOCOL-EXTENSION ::= {
	...
}

MIB-SB-SIB-InformationList-SystemInfoUpdateRqst ::= SEQUENCE (SIZE (1..maxIB)) OF MIB-SB-SIB-InformationItem-SystemInfoUpdateRqst

MIB-SB-SIB-InformationItem-SystemInfoUpdateRqst ::= SEQUENCE {
	iB-Type								IB-Type,	
	iB-OC-ID							IB-OC-ID,
	deletionIndicator					DeletionIndicator-SystemInfoUpdate,
	iE-Extensions						ProtocolExtensionContainer { { MIB-SB-SIB-InformationItem-SystemInfoUpdateRqst-ExtIEs} }		OPTIONAL,
	...
}

MIB-SB-SIB-InformationItem-SystemInfoUpdateRqst-ExtIEs NBAP-PROTOCOL-EXTENSION ::= {
	...
}

DeletionIndicator-SystemInfoUpdate ::= CHOICE {
	no-Deletion							No-Deletion-SystemInfoUpdate,
	yes-Deletion						NULL

}

No-Deletion-SystemInfoUpdate ::= SEQUENCE {
	sIB-Originator							SIB-Originator				OPTIONAL,
	-- This IE shall be present if the IB-Type IE is set to "SIB"
	iB-SG-REP								IB-SG-REP					OPTIONAL,
	segmentInformationList					SegmentInformationList-SystemInfoUpdate,
	iE-Extensions							ProtocolExtensionContainer { { No-DeletionItem-SystemInfoUpdate-ExtIEs} }		OPTIONAL,
	...
}

No-DeletionItem-SystemInfoUpdate-ExtIEs NBAP-PROTOCOL-EXTENSION ::= {
	...
}

SegmentInformationList-SystemInfoUpdate ::= ProtocolIE-Single-Container {{ SegmentInformationListIEs-SystemInfoUpdate }}

SegmentInformationListIEs-SystemInfoUpdate NBAP-PROTOCOL-IES ::= {
	{ ID id-SegmentInformationListIE-SystemInfoUpdate   CRITICALITY reject	TYPE SegmentInformationListIE-SystemInfoUpdate		PRESENCE mandatory }
}

SegmentInformationListIE-SystemInfoUpdate ::= SEQUENCE (SIZE (1..maxIBSEG)) OF SegmentInformationItem-SystemInfoUpdate

SegmentInformationItem-SystemInfoUpdate ::= SEQUENCE {
	iB-SG-POS								IB-SG-POS			OPTIONAL,
	segment-Type							Segment-Type		OPTIONAL,
	-- This IE shall be present if the SIB Originator IE is set to "CRNC" or the IB-Type IE is set to "MIB", "SB1" or "SB2"
	iB-SG-DATA								IB-SG-DATA			OPTIONAL,
	-- This IE shall be present if the SIB Originator IE is set to "CRNC" or the IB-Type IE is set to "MIB", "SB1" or "SB2"
	iE-Extensions							ProtocolExtensionContainer { { SegmentInformationItem-SystemInfoUpdate-ExtIEs} }	OPTIONAL,
	...
}

SegmentInformationItem-SystemInfoUpdate-ExtIEs NBAP-PROTOCOL-EXTENSION ::= {
	...
}

-- **************************************************************
--
-- SYSTEM INFORMATION UPDATE RESPONSE
--
-- **************************************************************

SystemInformationUpdateResponse ::= SEQUENCE {
	protocolIEs				ProtocolIE-Container    	{{SystemInformationUpdateResponse-IEs}},
	protocolExtensions		ProtocolExtensionContainer	{{SystemInformationUpdateResponse-Extensions}}		OPTIONAL,
	...
}

SystemInformationUpdateResponse-IEs NBAP-PROTOCOL-IES ::= {
	{ ID id-CriticalityDiagnostics		CRITICALITY ignore			TYPE CriticalityDiagnostics		PRESENCE optional },
	...
}

SystemInformationUpdateResponse-Extensions NBAP-PROTOCOL-EXTENSION ::= {
	...
}

-- **************************************************************
--
-- SYSTEM INFORMATION UPDATE FAILURE
--
-- **************************************************************

SystemInformationUpdateFailure ::= SEQUENCE {
	protocolIEs				ProtocolIE-Container		{{SystemInformationUpdateFailure-IEs}},
	protocolExtensions		ProtocolExtensionContainer	{{SystemInformationUpdateFailure-Extensions}}		OPTIONAL,
	...
}

SystemInformationUpdateFailure-IEs NBAP-PROTOCOL-IES ::= {
	{ ID id-Cause							CRITICALITY ignore			TYPE Cause						PRESENCE	mandatory	}|
	{ ID id-CriticalityDiagnostics			CRITICALITY ignore			TYPE CriticalityDiagnostics		PRESENCE	optional	},
	...
}

SystemInformationUpdateFailure-Extensions NBAP-PROTOCOL-EXTENSION ::= {
	...
}

-- **************************************************************
--
-- RADIO LINK SETUP REQUEST FDD
--
-- **************************************************************

RadioLinkSetupRequestFDD ::= SEQUENCE {
	protocolIEs				ProtocolIE-Container		{{RadioLinkSetupRequestFDD-IEs}},
	protocolExtensions		ProtocolExtensionContainer	{{RadioLinkSetupRequestFDD-Extensions}}			OPTIONAL,
	...
}

RadioLinkSetupRequestFDD-IEs NBAP-PROTOCOL-IES ::= {
	{ ID id-CRNC-CommunicationContextID						CRITICALITY reject	TYPE CRNC-CommunicationContextID					PRESENCE mandatory }|
	{ ID id-UL-DPCH-Information-RL-SetupRqstFDD				CRITICALITY reject	TYPE UL-DPCH-Information-RL-SetupRqstFDD			PRESENCE mandatory }|
	{ ID id-DL-DPCH-Information-RL-SetupRqstFDD				CRITICALITY reject	TYPE DL-DPCH-Information-RL-SetupRqstFDD			PRESENCE optional }|
	{ ID id-DCH-FDD-Information								CRITICALITY reject	TYPE DCH-FDD-Information					PRESENCE mandatory }|
	{ ID id-RL-InformationList-RL-SetupRqstFDD				CRITICALITY notify	TYPE RL-InformationList-RL-SetupRqstFDD			PRESENCE mandatory }|
	{ ID id-Transmission-Gap-Pattern-Sequence-Information	CRITICALITY reject	TYPE Transmission-Gap-Pattern-Sequence-Information								PRESENCE optional } |
	{ ID id-Active-Pattern-Sequence-Information				CRITICALITY reject	TYPE Active-Pattern-Sequence-Information			PRESENCE optional },
	...
}

RadioLinkSetupRequestFDD-Extensions NBAP-PROTOCOL-EXTENSION ::= {
	{ ID id-DL-PowerBalancing-Information			CRITICALITY ignore	EXTENSION DL-PowerBalancing-Information		PRESENCE optional }|
	{ ID id-HSDSCH-FDD-Information					CRITICALITY reject	EXTENSION HSDSCH-FDD-Information		PRESENCE optional }|
	{ ID id-HSDSCH-RNTI								CRITICALITY reject	EXTENSION HSDSCH-RNTI			PRESENCE conditional }|
	-- The IE shall be present if HS-DSCH Information IE is present
	{ ID id-HSPDSCH-RL-ID							CRITICALITY reject	EXTENSION RL-ID					PRESENCE conditional }|
	-- The IE shall be present if HS-DSCH Information IE is present
	{ ID id-E-DPCH-Information-RL-SetupRqstFDD		CRITICALITY reject	EXTENSION E-DPCH-Information-RL-SetupRqstFDD	PRESENCE optional }|
	{ ID id-E-DCH-FDD-Information					CRITICALITY reject	EXTENSION E-DCH-FDD-Information		PRESENCE conditional }|
	-- The IE shall be present if E-DPCH Information IE is present
	{ ID id-Serving-E-DCH-RL-ID						CRITICALITY reject	EXTENSION Serving-E-DCH-RL-ID		PRESENCE optional }|
	{ ID id-F-DPCH-Information-RL-SetupRqstFDD		CRITICALITY reject	EXTENSION F-DPCH-Information-RL-SetupRqstFDD	PRESENCE optional }|
	{ ID id-Initial-DL-DPCH-TimingAdjustment-Allowed		CRITICALITY ignore	EXTENSION Initial-DL-DPCH-TimingAdjustment-Allowed						PRESENCE optional }|
	{ ID id-DCH-Indicator-For-E-DCH-HSDPA-Operation			CRITICALITY reject	EXTENSION DCH-Indicator-For-E-DCH-HSDPA-Operation										PRESENCE optional }|
	{ ID id-Serving-Cell-Change-CFN 						CRITICALITY reject	EXTENSION CFN			PRESENCE optional }|
	{ ID id-ContinuousPacketConnectivityDTX-DRX-Information			CRITICALITY reject		EXTENSION ContinuousPacketConnectivityDTX-DRX-Information			PRESENCE optional }|
	{ ID id-ContinuousPacketConnectivityHS-SCCH-less-Information	CRITICALITY reject		EXTENSION ContinuousPacketConnectivityHS-SCCH-less-Information			PRESENCE optional }|
	{ ID id-Additional-HS-Cell-Information-RL-Setup					CRITICALITY reject		EXTENSION Additional-HS-Cell-Information-RL-Setup-List			PRESENCE optional },
	...
}

Additional-HS-Cell-Information-RL-Setup-List	::= SEQUENCE (SIZE (1..maxNrOfHSDSCH-1)) OF Additional-HS-Cell-Information-RL-Setup-ItemIEs

Additional-HS-Cell-Information-RL-Setup-ItemIEs	::=SEQUENCE{
	hSPDSCH-RL-ID									RL-ID,
	c-ID											C-ID,
	hS-DSCH-FDD-Secondary-Serving-Information		HS-DSCH-FDD-Secondary-Serving-Information,
	iE-Extensions					ProtocolExtensionContainer { { Additional-HS-Cell-Information-RL-Setup-ItemIEs-ExtIEs} } OPTIONAL,
	...
}

Additional-HS-Cell-Information-RL-Setup-ItemIEs-ExtIEs	NBAP-PROTOCOL-EXTENSION ::= {
	...
}

UL-DPCH-Information-RL-SetupRqstFDD ::= SEQUENCE {
	ul-ScramblingCode						UL-ScramblingCode,
	minUL-ChannelisationCodeLength			MinUL-ChannelisationCodeLength,
	maxNrOfUL-DPDCHs						MaxNrOfUL-DPDCHs		OPTIONAL,
	-- This IE shall be present if Min UL Channelisation Code length IE is set to 4 --
	ul-PunctureLimit						PunctureLimit,
	tFCS									TFCS,
	ul-DPCCH-SlotFormat						UL-DPCCH-SlotFormat,
	ul-SIR-Target							UL-SIR,
	diversityMode							DiversityMode,
	not-Used-sSDT-CellID-Length				NULL					OPTIONAL,
	not-Used-s-FieldLength					NULL					OPTIONAL,
	iE-Extensions							ProtocolExtensionContainer { { UL-DPCH-Information-RL-SetupRqstFDD-ExtIEs} }	OPTIONAL,
	...
}

UL-DPCH-Information-RL-SetupRqstFDD-ExtIEs NBAP-PROTOCOL-EXTENSION ::= {
	{ ID id-DPC-Mode								CRITICALITY reject	EXTENSION DPC-Mode						PRESENCE optional }|
	{ ID id-UL-DPDCH-Indicator-For-E-DCH-Operation	CRITICALITY reject	EXTENSION UL-DPDCH-Indicator-For-E-DCH-Operation		PRESENCE optional },
	...
}

DL-DPCH-Information-RL-SetupRqstFDD ::= SEQUENCE {
	tFCS									TFCS,
	dl-DPCH-SlotFormat						DL-DPCH-SlotFormat,
	tFCI-SignallingMode						TFCI-SignallingMode,
	tFCI-Presence							TFCI-Presence					OPTIONAL,
	-- this IE shall be present if the DL DPCH slot format IE is set to any of the values from 12 to 16 --	
	multiplexingPosition					MultiplexingPosition,
	not-Used-pDSCH-RL-ID					NULL							OPTIONAL,
	not-Used-pDSCH-CodeMapping				NULL							OPTIONAL,
	powerOffsetInformation					PowerOffsetInformation-RL-SetupRqstFDD,
	fdd-TPC-DownlinkStepSize				FDD-TPC-DownlinkStepSize,
	limitedPowerIncrease					LimitedPowerIncrease,
	innerLoopDLPCStatus						InnerLoopDLPCStatus,
	iE-Extensions							ProtocolExtensionContainer { { DL-DPCH-Information-RL-SetupRqstFDD-ExtIEs} }	OPTIONAL,
	...
}

DL-DPCH-Information-RL-SetupRqstFDD-ExtIEs NBAP-PROTOCOL-EXTENSION ::= {
	...
}

PowerOffsetInformation-RL-SetupRqstFDD ::= SEQUENCE {
	pO1-ForTFCI-Bits						PowerOffset,
	pO2-ForTPC-Bits							PowerOffset,
	pO3-ForPilotBits						PowerOffset,
	iE-Extensions							ProtocolExtensionContainer { { PowerOffsetInformation-RL-SetupRqstFDD-ExtIEs} }	OPTIONAL,
	...
}

PowerOffsetInformation-RL-SetupRqstFDD-ExtIEs NBAP-PROTOCOL-EXTENSION ::= {
	...
}

RL-InformationList-RL-SetupRqstFDD ::= SEQUENCE (SIZE (1..maxNrOfRLs)) OF
	ProtocolIE-Single-Container{{ RL-InformationItemIE-RL-SetupRqstFDD }}

RL-InformationItemIE-RL-SetupRqstFDD NBAP-PROTOCOL-IES ::= {
	{ ID id-RL-InformationItem-RL-SetupRqstFDD			CRITICALITY notify			TYPE RL-InformationItem-RL-SetupRqstFDD		PRESENCE mandatory }
}

RL-InformationItem-RL-SetupRqstFDD ::= SEQUENCE {
	rL-ID								RL-ID,
	c-ID								C-ID,
	firstRLS-indicator					FirstRLS-Indicator,
	frameOffset							FrameOffset,
	chipOffset							ChipOffset,
	propagationDelay					PropagationDelay				OPTIONAL,
	diversityControlField				DiversityControlField			OPTIONAL,
	-- This IE shall be present if the RL is not the first one in the RL Information IE
	dl-CodeInformation					FDD-DL-CodeInformation,
	initialDL-transmissionPower			DL-Power,
	maximumDL-power						DL-Power,
	minimumDL-power						DL-Power,
	not-Used-sSDT-Cell-Identity			NULL							OPTIONAL,
	transmitDiversityIndicator			TransmitDiversityIndicator		OPTIONAL,
	-- This IE shall be present if Diversity Mode IE in UL DPCH Information group is not set to “none”
	iE-Extensions						ProtocolExtensionContainer { { RL-InformationItem-RL-SetupRqstFDD-ExtIEs} }		OPTIONAL,
	...
}

RL-InformationItem-RL-SetupRqstFDD-ExtIEs NBAP-PROTOCOL-EXTENSION ::= {
	{ ID id-RL-Specific-DCH-Info						CRITICALITY ignore	EXTENSION RL-Specific-DCH-Info	PRESENCE optional }|
	{ ID id-DelayedActivation							CRITICALITY reject	EXTENSION DelayedActivation	PRESENCE optional }|
	{ ID id-Primary-CPICH-Usage-for-Channel-Estimation	CRITICALITY ignore	EXTENSION Primary-CPICH-Usage-for-Channel-Estimation	PRESENCE optional }|
	{ ID id-Secondary-CPICH-Information					CRITICALITY ignore	EXTENSION CommonPhysicalChannelID	PRESENCE optional }|
	{ ID id-E-DCH-RL-Indication							CRITICALITY reject	EXTENSION E-DCH-RL-Indication	PRESENCE optional }|
	{ ID id-RL-Specific-E-DCH-Info						CRITICALITY ignore	EXTENSION RL-Specific-E-DCH-Info	PRESENCE optional }|
	{ ID id-SynchronisationIndicator					CRITICALITY ignore	EXTENSION SynchronisationIndicator	PRESENCE optional }|
	{ ID id-ExtendedPropagationDelay					CRITICALITY ignore	EXTENSION ExtendedPropagationDelay	PRESENCE optional }|
	{ ID id-F-DPCH-SlotFormat							CRITICALITY reject	EXTENSION F-DPCH-SlotFormat					PRESENCE optional }|
	{ ID id-HSDSCH-PreconfigurationSetup				CRITICALITY ignore	EXTENSION HSDSCH-PreconfigurationSetup	PRESENCE optional},
	...
}
E-DPCH-Information-RL-SetupRqstFDD ::= SEQUENCE {
	maxSet-E-DPDCHs								Max-Set-E-DPDCHs,
	ul-PunctureLimit							PunctureLimit,
	e-TFCS-Information							E-TFCS-Information,
	e-TTI										E-TTI,
	e-DPCCH-PO									E-DPCCH-PO,
	e-RGCH-2-IndexStepThreshold					E-RGCH-2-IndexStepThreshold,
	e-RGCH-3-IndexStepThreshold					E-RGCH-3-IndexStepThreshold,
	hARQ-Info-for-E-DCH							HARQ-Info-for-E-DCH,
	hSDSCH-Configured-Indicator					HSDSCH-Configured-Indicator,
	iE-Extensions								ProtocolExtensionContainer { { E-DPCH-Information-RL-SetupRqstFDD-ExtIEs} }		OPTIONAL,
	...
}

E-DPCH-Information-RL-SetupRqstFDD-ExtIEs NBAP-PROTOCOL-EXTENSION ::= {
	{ ID id-E-RNTI									CRITICALITY reject	EXTENSION E-RNTI			PRESENCE optional }|
	{ ID id-MinimumReducedE-DPDCH-GainFactor		CRITICALITY ignore	EXTENSION MinimumReducedE-DPDCH-GainFactor	PRESENCE optional },
	...
}

F-DPCH-Information-RL-SetupRqstFDD ::= SEQUENCE {
	powerOffsetInformation				PowerOffsetInformation-F-DPCH-RL-SetupRqstFDD,
	fdd-TPC-DownlinkStepSize			FDD-TPC-DownlinkStepSize,
	limitedPowerIncrease				LimitedPowerIncrease,
	innerLoopDLPCStatus					InnerLoopDLPCStatus,
	iE-Extensions						ProtocolExtensionContainer { { F-DPCH-Information-RL-SetupRqstFDD-ExtIEs} }					OPTIONAL,
	...
}

F-DPCH-Information-RL-SetupRqstFDD-ExtIEs NBAP-PROTOCOL-EXTENSION ::= {
	...
}

PowerOffsetInformation-F-DPCH-RL-SetupRqstFDD ::= SEQUENCE {
	pO2-ForTPC-Bits						PowerOffset,
	--This IE shall be ignored by Node B
	iE-Extensions						ProtocolExtensionContainer { { PowerOffsetInformation-F-DPCH-RL-SetupRqstFDD-ExtIEs} }	OPTIONAL,
	...
}

PowerOffsetInformation-F-DPCH-RL-SetupRqstFDD-ExtIEs NBAP-PROTOCOL-EXTENSION ::= {
	...
}

-- **************************************************************
--
-- RADIO LINK SETUP REQUEST TDD
--
-- **************************************************************

RadioLinkSetupRequestTDD ::= SEQUENCE {
	protocolIEs				ProtocolIE-Container		{{RadioLinkSetupRequestTDD-IEs}},
	protocolExtensions		ProtocolExtensionContainer	{{RadioLinkSetupRequestTDD-Extensions}}		OPTIONAL,
	...
}

RadioLinkSetupRequestTDD-IEs NBAP-PROTOCOL-IES ::= {
	{ ID	id-CRNC-CommunicationContextID					CRITICALITY reject	TYPE CRNC-CommunicationContextID					PRESENCE mandatory }|
	{ ID	id-UL-CCTrCH-InformationList-RL-SetupRqstTDD	CRITICALITY notify	TYPE UL-CCTrCH-InformationList-RL-SetupRqstTDD	PRESENCE optional }|
	{ ID	id-DL-CCTrCH-InformationList-RL-SetupRqstTDD	CRITICALITY notify	TYPE DL-CCTrCH-InformationList-RL-SetupRqstTDD	PRESENCE optional }|
	{ ID	id-DCH-TDD-Information							CRITICALITY reject	TYPE DCH-TDD-Information					PRESENCE optional }|
	{ ID	id-DSCH-TDD-Information							CRITICALITY reject	TYPE DSCH-TDD-Information					PRESENCE optional }|
	{ ID	id-USCH-Information								CRITICALITY reject	TYPE USCH-Information					PRESENCE optional }|
	{ ID	id-RL-Information-RL-SetupRqstTDD				CRITICALITY reject	TYPE RL-Information-RL-SetupRqstTDD					PRESENCE mandatory },
	...
}

RadioLinkSetupRequestTDD-Extensions NBAP-PROTOCOL-EXTENSION ::= {
	{ ID id-HSDSCH-TDD-Information			CRITICALITY reject		EXTENSION HSDSCH-TDD-Information	PRESENCE optional	}|
	{ ID id-HSDSCH-RNTI						CRITICALITY reject		EXTENSION HSDSCH-RNTI			PRESENCE conditional	}|
	-- The IE shall be present if HS-DSCH Information IE is present
	{ ID id-HSPDSCH-RL-ID					CRITICALITY reject		EXTENSION RL-ID					PRESENCE conditional	}|
	-- The IE shall be present if HS-DSCH Information IE is present
	{ ID id-PDSCH-RL-ID						CRITICALITY ignore		EXTENSION RL-ID					PRESENCE optional }|
	{ ID id-E-DCH-Information				CRITICALITY reject		EXTENSION E-DCH-Information		PRESENCE optional	}|
	{ ID id-E-DCH-Serving-RL-ID				CRITICALITY reject		EXTENSION RL-ID					PRESENCE optional	}|
	{ ID id-E-DCH-768-Information			CRITICALITY reject		EXTENSION E-DCH-768-Information	PRESENCE optional	}|
	{ ID id-E-DCH-LCR-Information			CRITICALITY reject		EXTENSION E-DCH-LCR-Information						PRESENCE optional	}|
	{ ID id-PowerControlGAP					CRITICALITY ignore		EXTENSION ControlGAP									PRESENCE optional },
	 -- Applicable to 1.28Mcps TDD only
	...
}

UL-CCTrCH-InformationList-RL-SetupRqstTDD ::= SEQUENCE (SIZE(1..maxNrOfCCTrCHs)) OF
	ProtocolIE-Single-Container{{ UL-CCTrCH-InformationItemIE-RL-SetupRqstTDD }}

UL-CCTrCH-InformationItemIE-RL-SetupRqstTDD NBAP-PROTOCOL-IES ::= {
	{ ID id-UL-CCTrCH-InformationItem-RL-SetupRqstTDD		CRITICALITY notify		TYPE UL-CCTrCH-InformationItem-RL-SetupRqstTDD		PRESENCE mandatory }
}

UL-CCTrCH-InformationItem-RL-SetupRqstTDD ::= SEQUENCE {
	cCTrCH-ID								CCTrCH-ID,
	tFCS									TFCS,
	tFCI-Coding								TFCI-Coding,
	punctureLimit							PunctureLimit,
	uL-DPCH-Information						UL-DPCH-Information-RL-SetupRqstTDD		OPTIONAL, 	-- Applicable to 3.84Mcps TDD only
	iE-Extensions							ProtocolExtensionContainer { { UL-CCTrCH-InformationItem-RL-SetupRqstTDD-ExtIEs} }		OPTIONAL,
	...
}

UL-CCTrCH-InformationItem-RL-SetupRqstTDD-ExtIEs NBAP-PROTOCOL-EXTENSION ::= {
	{ ID id-UL-DPCH-LCR-Information-RL-SetupRqstTDD		CRITICALITY notify	EXTENSION UL-DPCH-LCR-Information-RL-SetupRqstTDD	PRESENCE optional	}|	-- Applicable to 1.28Mcps TDD only
	{ ID id-UL-SIRTarget								CRITICALITY reject	EXTENSION UL-SIR						PRESENCE optional	}|
	-- Mandatory for 1.28Mcps TDD, Not Applicable to 3.84Mcps TDD or 7.68Mcps TDD.
	{ ID id-TDD-TPC-UplinkStepSize-LCR-RL-SetupRqstTDD	CRITICALITY reject	EXTENSION TDD-TPC-UplinkStepSize-LCR					PRESENCE optional	}|
	-- Mandatory for 1.28Mcps TDD, Not Applicable to 3.84Mcps TDD or 7.68Mcps TDD.
	{ ID id-UL-DPCH-768-Information-RL-SetupRqstTDD		CRITICALITY notify	EXTENSION UL-DPCH-768-Information-RL-SetupRqstTDD	PRESENCE optional	},	-- Applicable to 7.68Mcps TDD only
	...
}

UL-DPCH-Information-RL-SetupRqstTDD ::= ProtocolIE-Single-Container{{ UL-DPCH-InformationIE-RL-SetupRqstTDD }}

UL-DPCH-InformationIE-RL-SetupRqstTDD NBAP-PROTOCOL-IES ::= {
	{ ID id-UL-DPCH-InformationList-RL-SetupRqstTDD		CRITICALITY notify	TYPE UL-DPCH-InformationItem-RL-SetupRqstTDD		PRESENCE mandatory	}
}

UL-DPCH-InformationItem-RL-SetupRqstTDD ::= SEQUENCE {
	repetitionPeriod						RepetitionPeriod,
	repetitionLength						RepetitionLength,
	tdd-DPCHOffset							TDD-DPCHOffset,
	uL-Timeslot-Information					UL-Timeslot-Information,
	iE-Extensions							ProtocolExtensionContainer { { UL-DPCH-InformationItem-RL-SetupRqstTDD-ExtIEs} }		OPTIONAL,
	...
}

UL-DPCH-InformationItem-RL-SetupRqstTDD-ExtIEs NBAP-PROTOCOL-EXTENSION ::= {
	...
}

UL-DPCH-LCR-Information-RL-SetupRqstTDD ::= SEQUENCE {
	repetitionPeriod						RepetitionPeriod,
	repetitionLength						RepetitionLength,
	tdd-DPCHOffset							TDD-DPCHOffset,
	uL-TimeslotLCR-Information				UL-TimeslotLCR-Information,
	iE-Extensions							ProtocolExtensionContainer { { UL-DPCH-LCR-InformationItem-RL-SetupRqstTDD-ExtIEs} }		OPTIONAL,
	...
}

UL-DPCH-LCR-InformationItem-RL-SetupRqstTDD-ExtIEs NBAP-PROTOCOL-EXTENSION ::= {
	...
}

UL-DPCH-768-Information-RL-SetupRqstTDD ::= SEQUENCE {
	repetitionPeriod						RepetitionPeriod,
	repetitionLength						RepetitionLength,
	tdd-DPCHOffset							TDD-DPCHOffset,
	uL-Timeslot768-Information				UL-Timeslot768-Information,
	iE-Extensions							ProtocolExtensionContainer { { UL-DPCH-768-InformationItem-RL-SetupRqstTDD-ExtIEs} }		OPTIONAL,
	...
}

UL-DPCH-768-InformationItem-RL-SetupRqstTDD-ExtIEs NBAP-PROTOCOL-EXTENSION ::= {
	...
}

DL-CCTrCH-InformationList-RL-SetupRqstTDD ::= SEQUENCE (SIZE (1..maxNrOfCCTrCHs)) OF ProtocolIE-Single-Container{{ DL-CCTrCH-InformationItemIE-RL-SetupRqstTDD }}

DL-CCTrCH-InformationItemIE-RL-SetupRqstTDD NBAP-PROTOCOL-IES ::= {
	{ ID id-DL-CCTrCH-InformationItem-RL-SetupRqstTDD	CRITICALITY notify	TYPE DL-CCTrCH-InformationItem-RL-SetupRqstTDD		PRESENCE mandatory}
}

DL-CCTrCH-InformationItem-RL-SetupRqstTDD ::= SEQUENCE {
	cCTrCH-ID								CCTrCH-ID,
	tFCS									TFCS,
	tFCI-Coding								TFCI-Coding,
	punctureLimit							PunctureLimit,
	tdd-TPC-DownlinkStepSize				TDD-TPC-DownlinkStepSize,
	cCTrCH-TPCList							CCTrCH-TPCList-RL-SetupRqstTDD			OPTIONAL,
	dL-DPCH-Information						DL-DPCH-Information-RL-SetupRqstTDD		OPTIONAL, 	-- Applicable to 3.84Mcps TDD only
	iE-Extensions							ProtocolExtensionContainer { { DL-CCTrCH-InformationItem-RL-SetupRqstTDD-ExtIEs} }		OPTIONAL,
	...
}

DL-CCTrCH-InformationItem-RL-SetupRqstTDD-ExtIEs NBAP-PROTOCOL-EXTENSION ::= {
	{ ID id-DL-DPCH-LCR-Information-RL-SetupRqstTDD		CRITICALITY notify		EXTENSION DL-DPCH-LCR-Information-RL-SetupRqstTDD		PRESENCE optional	}|	-- Applicable to 1.28Mcps TDD only
	{ ID id-CCTrCH-Initial-DL-Power-RL-SetupRqstTDD		CRITICALITY ignore		EXTENSION DL-Power		PRESENCE optional	}|
	{ ID id-CCTrCH-Maximum-DL-Power-RL-SetupRqstTDD		CRITICALITY ignore		EXTENSION DL-Power		PRESENCE optional	}|
	{ ID id-CCTrCH-Minimum-DL-Power-RL-SetupRqstTDD		CRITICALITY ignore		EXTENSION DL-Power		PRESENCE optional	}|
	{ ID id-DL-DPCH-768-Information-RL-SetupRqstTDD		CRITICALITY notify		EXTENSION DL-DPCH-768-Information-RL-SetupRqstTDD		PRESENCE optional	},	-- Applicable to 7.68Mcps TDD only
	...
}

CCTrCH-TPCList-RL-SetupRqstTDD ::= SEQUENCE (SIZE (1..maxNrOfCCTrCHs)) OF CCTrCH-TPCItem-RL-SetupRqstTDD

CCTrCH-TPCItem-RL-SetupRqstTDD	 ::= SEQUENCE {
	cCTrCH-ID								CCTrCH-ID,
	iE-Extensions							ProtocolExtensionContainer { { CCTrCH-TPCItem-RL-SetupRqstTDD-ExtIEs} }		OPTIONAL,
	...
}

CCTrCH-TPCItem-RL-SetupRqstTDD-ExtIEs NBAP-PROTOCOL-EXTENSION ::= {
	...
}

DL-DPCH-Information-RL-SetupRqstTDD ::= ProtocolIE-Single-Container{{ DL-DPCH-InformationIE-RL-SetupRqstTDD }}

DL-DPCH-InformationIE-RL-SetupRqstTDD NBAP-PROTOCOL-IES ::= {
	{ ID id-DL-DPCH-InformationList-RL-SetupRqstTDD		CRITICALITY notify	TYPE DL-DPCH-InformationItem-RL-SetupRqstTDD		PRESENCE mandatory	}
}

DL-DPCH-InformationItem-RL-SetupRqstTDD	 ::= SEQUENCE {
	repetitionPeriod						RepetitionPeriod,
	repetitionLength						RepetitionLength,
	tdd-DPCHOffset							TDD-DPCHOffset,
	dL-Timeslot-Information					DL-Timeslot-Information,
	iE-Extensions							ProtocolExtensionContainer { { DL-DPCH-InformationItem-RL-SetupRqstTDD-ExtIEs} }		OPTIONAL,
	...
}

DL-DPCH-InformationItem-RL-SetupRqstTDD-ExtIEs NBAP-PROTOCOL-EXTENSION ::= {
	...
}

DL-DPCH-LCR-Information-RL-SetupRqstTDD ::= SEQUENCE {
	repetitionPeriod						RepetitionPeriod,
	repetitionLength						RepetitionLength,
	tdd-DPCHOffset							TDD-DPCHOffset,
	dL-TimeslotLCR-Information				DL-TimeslotLCR-Information,
	tstdIndicator							TSTD-Indicator,
	iE-Extensions							ProtocolExtensionContainer { { DL-DPCH-LCR-InformationItem-RL-SetupRqstTDD-ExtIEs} }		OPTIONAL,
	...
}

DL-DPCH-LCR-InformationItem-RL-SetupRqstTDD-ExtIEs NBAP-PROTOCOL-EXTENSION ::= {
	...
}

DL-DPCH-768-Information-RL-SetupRqstTDD ::= SEQUENCE {
	repetitionPeriod						RepetitionPeriod,
	repetitionLength						RepetitionLength,
	tdd-DPCHOffset							TDD-DPCHOffset,
	dL-Timeslot768-Information				DL-Timeslot768-Information,
	iE-Extensions							ProtocolExtensionContainer { { DL-DPCH-768-InformationItem-RL-SetupRqstTDD-ExtIEs} }		OPTIONAL,
	...
}

DL-DPCH-768-InformationItem-RL-SetupRqstTDD-ExtIEs NBAP-PROTOCOL-EXTENSION ::= {
	...
}

RL-Information-RL-SetupRqstTDD ::= SEQUENCE {
	rL-ID									RL-ID,
	c-ID									C-ID,
	frameOffset								FrameOffset,
	specialBurstScheduling					SpecialBurstScheduling,
	initialDL-transmissionPower				DL-Power,
	maximumDL-power							DL-Power,
	minimumDL-power							DL-Power,
	dL-TimeSlotISCPInfo						DL-TimeslotISCPInfo	OPTIONAL, 	-- Applicable to 3.84Mcps TDD and 7.68Mcps TDD only
	iE-Extensions							ProtocolExtensionContainer { { RL-Information-RL-SetupRqstTDD-ExtIEs} }		OPTIONAL,
	...
}

RL-Information-RL-SetupRqstTDD-ExtIEs NBAP-PROTOCOL-EXTENSION ::= {
	{ ID id-TimeslotISCP-LCR-InfoList-RL-SetupRqstTDD	CRITICALITY reject		EXTENSION DL-TimeslotISCPInfoLCR				PRESENCE optional }|
	-- Applicable to 1.28Mcps TDD only
	{ ID id-RL-Specific-DCH-Info						CRITICALITY ignore		EXTENSION RL-Specific-DCH-Info				PRESENCE optional }|
	{ ID id-DelayedActivation							CRITICALITY reject		EXTENSION DelayedActivation 				PRESENCE optional }|
	{ ID id-UL-Synchronisation-Parameters-LCR			CRITICALITY reject		EXTENSION UL-Synchronisation-Parameters-LCR	PRESENCE optional }|
	-- Mandatory for 1.28Mcps TDD, Not Applicable to 3.84Mcps TDD or 7.68Mcps TDD
	{ ID id-UARFCNforNt									CRITICALITY reject		EXTENSION UARFCN				PRESENCE optional },
	-- Mandatory for 1.28Mcps TDD when using multiple frequencies
	...
}

-- **************************************************************
--
-- RADIO LINK SETUP RESPONSE FDD
--
-- **************************************************************

RadioLinkSetupResponseFDD ::= SEQUENCE {
	protocolIEs				ProtocolIE-Container		{{RadioLinkSetupResponseFDD-IEs}},
	protocolExtensions		ProtocolExtensionContainer	{{RadioLinkSetupResponseFDD-Extensions}}		OPTIONAL,
	...
}

RadioLinkSetupResponseFDD-IEs NBAP-PROTOCOL-IES ::= {
	{ ID id-CRNC-CommunicationContextID					CRITICALITY ignore	TYPE CRNC-CommunicationContextID					PRESENCE mandatory }|
	{ ID id-NodeB-CommunicationContextID				CRITICALITY ignore	TYPE NodeB-CommunicationContextID					PRESENCE mandatory }|
	{ ID id-CommunicationControlPortID					CRITICALITY ignore	TYPE CommunicationControlPortID					PRESENCE mandatory }|
	{ ID id-RL-InformationResponseList-RL-SetupRspFDD	CRITICALITY ignore	TYPE RL-InformationResponseList-RL-SetupRspFDD		PRESENCE mandatory }|
	{ ID id-CriticalityDiagnostics						CRITICALITY ignore	TYPE CriticalityDiagnostics					PRESENCE optional },
	...
}

RadioLinkSetupResponseFDD-Extensions NBAP-PROTOCOL-EXTENSION ::= {
	{ ID id-HSDSCH-FDD-Information-Response				CRITICALITY ignore	EXTENSION HSDSCH-FDD-Information-Response				PRESENCE optional }|
	{ ID id-ContinuousPacketConnectivityHS-SCCH-less-Information-Response		CRITICALITY ignore	EXTENSION	ContinuousPacketConnectivityHS-SCCH-less-Information-Response			PRESENCE optional }|
	{ ID id-Additional-HS-Cell-Information-Response		CRITICALITY ignore	EXTENSION	Additional-HS-Cell-Information-Response-List			PRESENCE optional },
	...
}
Additional-HS-Cell-Information-Response-List	::= SEQUENCE (SIZE (1..maxNrOfHSDSCH-1)) OF Additional-HS-Cell-Information-Response-ItemIEs

Additional-HS-Cell-Information-Response-ItemIEs	::=SEQUENCE{
	hSPDSCH-RL-ID										RL-ID,
	hS-DSCH-FDD-Secondary-Serving-Information-Response	HS-DSCH-FDD-Secondary-Serving-Information-Response,
	iE-Extensions					ProtocolExtensionContainer { { Additional-HS-Cell-Information-Response-ItemIEs-ExtIEs} } OPTIONAL,
	...
}

Additional-HS-Cell-Information-Response-ItemIEs-ExtIEs	NBAP-PROTOCOL-EXTENSION ::= {
	...
}

RL-InformationResponseList-RL-SetupRspFDD ::= SEQUENCE (SIZE (1..maxNrOfRLs)) OF ProtocolIE-Single-Container{{ RL-InformationResponseItemIE-RL-SetupRspFDD }}
	
RL-InformationResponseItemIE-RL-SetupRspFDD NBAP-PROTOCOL-IES ::= {
	{ ID id-RL-InformationResponseItem-RL-SetupRspFDD	CRITICALITY ignore	TYPE RL-InformationResponseItem-RL-SetupRspFDD	PRESENCE mandatory }
}

RL-InformationResponseItem-RL-SetupRspFDD ::= SEQUENCE {
	rL-ID											RL-ID,
	rL-Set-ID										RL-Set-ID,
	received-total-wide-band-power					Received-total-wide-band-power-Value,
	diversityIndication								DiversityIndication-RL-SetupRspFDD,
	not-Used-dSCH-InformationResponseList			NULL							OPTIONAL,
	sSDT-SupportIndicator							SSDT-SupportIndicator,
	iE-Extensions									ProtocolExtensionContainer { { RL-InformationResponseItem-RL-SetupRspFDD-ExtIEs} }		OPTIONAL,
	...
}

RL-InformationResponseItem-RL-SetupRspFDD-ExtIEs NBAP-PROTOCOL-EXTENSION ::= {
	{ ID id-DL-PowerBalancing-ActivationIndicator		CRITICALITY ignore	EXTENSION DL-PowerBalancing-ActivationIndicator			PRESENCE optional }|
	{ ID id-E-DCH-RL-Set-ID								CRITICALITY ignore	EXTENSION RL-Set-ID							PRESENCE optional }|
	{ ID id-E-DCH-FDD-DL-Control-Channel-Information	CRITICALITY ignore	EXTENSION E-DCH-FDD-DL-Control-Channel-Information		PRESENCE optional }|
	{ ID id-Initial-DL-DPCH-TimingAdjustment			CRITICALITY ignore	EXTENSION DL-DPCH-TimingAdjustment						PRESENCE optional }|
	{ ID id-HSDSCH-PreconfigurationInfo					CRITICALITY ignore	EXTENSION HSDSCH-PreconfigurationInfo					PRESENCE optional},
	...
}

DiversityIndication-RL-SetupRspFDD ::= CHOICE {
	combining									Combining-RL-SetupRspFDD,
	nonCombiningOrFirstRL						NonCombiningOrFirstRL-RL-SetupRspFDD
}

Combining-RL-SetupRspFDD ::= SEQUENCE {
	rL-ID										RL-ID,
	iE-Extensions								ProtocolExtensionContainer { { Combining-RL-SetupRspFDD-ExtIEs} }		OPTIONAL,
	...
}

Combining-RL-SetupRspFDD-ExtIEs NBAP-PROTOCOL-EXTENSION ::= {
	...
}

NonCombiningOrFirstRL-RL-SetupRspFDD ::= SEQUENCE {
	dCH-InformationResponse						DCH-InformationResponse,
	iE-Extensions								ProtocolExtensionContainer { { NonCombiningOrFirstRLItem-RL-SetupRspFDD-ExtIEs} }		OPTIONAL,
	...
}

NonCombiningOrFirstRLItem-RL-SetupRspFDD-ExtIEs NBAP-PROTOCOL-EXTENSION ::= {
	{ ID id-E-DCH-FDD-Information-Response		CRITICALITY ignore	EXTENSION E-DCH-FDD-Information-Response		PRESENCE optional },
	...
}

-- **************************************************************
--
-- RADIO LINK SETUP RESPONSE TDD
--
-- **************************************************************

RadioLinkSetupResponseTDD ::= SEQUENCE {
	protocolIEs				ProtocolIE-Container		{{RadioLinkSetupResponseTDD-IEs}},
	protocolExtensions		ProtocolExtensionContainer	{{RadioLinkSetupResponseTDD-Extensions}}		OPTIONAL,
	...
}

RadioLinkSetupResponseTDD-IEs NBAP-PROTOCOL-IES ::= {
	{ ID id-CRNC-CommunicationContextID				CRITICALITY ignore	TYPE CRNC-CommunicationContextID				PRESENCE mandatory }|
	{ ID id-NodeB-CommunicationContextID			CRITICALITY ignore	TYPE NodeB-CommunicationContextID				PRESENCE mandatory }|
	{ ID id-CommunicationControlPortID				CRITICALITY ignore	TYPE CommunicationControlPortID				PRESENCE mandatory }|
	{ ID id-RL-InformationResponse-RL-SetupRspTDD	CRITICALITY ignore	TYPE RL-InformationResponse-RL-SetupRspTDD				PRESENCE optional }|
	-- Mandatory for 3.84Mcps TDD and 7.68Mcps TDD, Not Applicable to 1.28Mcps TDD
	{ ID id-CriticalityDiagnostics					CRITICALITY ignore	TYPE CriticalityDiagnostics				PRESENCE optional },
	...
}

RadioLinkSetupResponseTDD-Extensions NBAP-PROTOCOL-EXTENSION ::= {
	{ ID id-RL-InformationResponse-LCR-RL-SetupRspTDD	CRITICALITY ignore	EXTENSION RL-InformationResponse-LCR-RL-SetupRspTDD		PRESENCE 	optional	}|	-- Mandatory for 1.28Mcps TDD, Not Applicable to 3.84Mcps TDD or 7.68Mcps TDD
	{ ID id-HSDSCH-TDD-Information-Response			CRITICALITY ignore		EXTENSION HSDSCH-TDD-Information-Response		PRESENCE optional	}|
	{ ID id-E-DCH-Information-Response				CRITICALITY ignore		EXTENSION E-DCH-Information-Response			PRESENCE optional	},
	...
}

RL-InformationResponse-RL-SetupRspTDD ::= SEQUENCE {
	rL-ID											RL-ID,
	uL-TimeSlot-ISCP-Info							UL-TimeSlot-ISCP-Info,
	ul-PhysCH-SF-Variation							UL-PhysCH-SF-Variation,
	dCH-InformationResponseList						DCH-InformationResponseList-RL-SetupRspTDD			OPTIONAL,
	dSCH-InformationResponseList					DSCH-InformationResponseList-RL-SetupRspTDD			OPTIONAL,
	uSCH-InformationResponseList					USCH-InformationResponseList-RL-SetupRspTDD			OPTIONAL,
	iE-Extensions									ProtocolExtensionContainer { { RL-InformationResponseList-RL-SetupRspTDD-ExtIEs} }		OPTIONAL,
	...
}

RL-InformationResponseList-RL-SetupRspTDD-ExtIEs NBAP-PROTOCOL-EXTENSION ::= {
	...
}

DCH-InformationResponseList-RL-SetupRspTDD ::= ProtocolIE-Single-Container{{ DCH-InformationResponseListIEs-RL-SetupRspTDD }}

DCH-InformationResponseListIEs-RL-SetupRspTDD NBAP-PROTOCOL-IES ::= {
	{ ID id-DCH-InformationResponse	CRITICALITY 	ignore		TYPE 	DCH-InformationResponse  PRESENCE	mandatory}
 }

DSCH-InformationResponseList-RL-SetupRspTDD ::= ProtocolIE-Single-Container {{ DSCH-InformationResponseListIEs-RL-SetupRspTDD }}

DSCH-InformationResponseListIEs-RL-SetupRspTDD NBAP-PROTOCOL-IES ::= {
	{ ID id-DSCH-InformationResponse   CRITICALITY ignore	TYPE DSCH-InformationResponse		PRESENCE mandatory }
}

USCH-InformationResponseList-RL-SetupRspTDD ::= ProtocolIE-Single-Container {{ USCH-InformationResponseListIEs-RL-SetupRspTDD }}

USCH-InformationResponseListIEs-RL-SetupRspTDD NBAP-PROTOCOL-IES ::= {
	{ ID id-USCH-InformationResponse   CRITICALITY ignore	TYPE USCH-InformationResponse		PRESENCE mandatory }
}

RL-InformationResponse-LCR-RL-SetupRspTDD ::= SEQUENCE {
	rL-ID											RL-ID,
	uL-TimeSlot-ISCP-LCR-Info						UL-TimeSlot-ISCP-LCR-Info,
	ul-PhysCH-SF-Variation							UL-PhysCH-SF-Variation,
	dCH-InformationResponseList						DCH-InformationResponseList-RL-SetupRspTDD			OPTIONAL,
	dSCH-InformationResponseList					DSCH-InformationResponseList-RL-SetupRspTDD			OPTIONAL,
	uSCH-InformationResponseList					USCH-InformationResponseList-RL-SetupRspTDD			OPTIONAL,
	iE-Extensions									ProtocolExtensionContainer { { RL-InformationResponseList-LCR-RL-SetupRspTDD-ExtIEs} }		OPTIONAL,
	...
}

RL-InformationResponseList-LCR-RL-SetupRspTDD-ExtIEs NBAP-PROTOCOL-EXTENSION ::= {
	...
}

-- **************************************************************
--
-- RADIO LINK SETUP FAILURE FDD
--
-- **************************************************************

RadioLinkSetupFailureFDD ::= SEQUENCE {
	protocolIEs				ProtocolIE-Container		{{RadioLinkSetupFailureFDD-IEs}},
	protocolExtensions		ProtocolExtensionContainer	{{RadioLinkSetupFailureFDD-Extensions}}		OPTIONAL,
	...
}

RadioLinkSetupFailureFDD-IEs NBAP-PROTOCOL-IES ::= {
	{ ID id-CRNC-CommunicationContextID			CRITICALITY ignore	TYPE CRNC-CommunicationContextID		PRESENCE mandatory }|
	{ ID id-NodeB-CommunicationContextID		CRITICALITY ignore	TYPE NodeB-CommunicationContextID		PRESENCE conditional }|
	-- This IE shall be present if at least one of the radio links has been successfully set up
	{ ID id-CommunicationControlPortID			CRITICALITY ignore	TYPE CommunicationControlPortID		PRESENCE optional }|
	{ ID id-CauseLevel-RL-SetupFailureFDD		CRITICALITY ignore	TYPE CauseLevel-RL-SetupFailureFDD		PRESENCE mandatory }|
	{ ID id-CriticalityDiagnostics				CRITICALITY ignore	TYPE CriticalityDiagnostics			PRESENCE optional },
	...
}

RadioLinkSetupFailureFDD-Extensions NBAP-PROTOCOL-EXTENSION ::= {
	...
}

CauseLevel-RL-SetupFailureFDD ::= CHOICE {
	generalCause		GeneralCauseList-RL-SetupFailureFDD,
	rLSpecificCause		RLSpecificCauseList-RL-SetupFailureFDD,
	...
}

GeneralCauseList-RL-SetupFailureFDD ::= SEQUENCE {
	cause										Cause,
	iE-Extensions								ProtocolExtensionContainer { { GeneralCauseItem-RL-SetupFailureFDD-ExtIEs} }		OPTIONAL,
	...
}

GeneralCauseItem-RL-SetupFailureFDD-ExtIEs NBAP-PROTOCOL-EXTENSION ::= {
	...
}

RLSpecificCauseList-RL-SetupFailureFDD ::= SEQUENCE {
	unsuccessful-RL-InformationRespList-RL-SetupFailureFDD		Unsuccessful-RL-InformationRespList-RL-SetupFailureFDD,
	successful-RL-InformationRespList-RL-SetupFailureFDD		Successful-RL-InformationRespList-RL-SetupFailureFDD	OPTIONAL,
	iE-Extensions								ProtocolExtensionContainer { { RLSpecificCauseItem-RL-SetupFailureFDD-ExtIEs} }		OPTIONAL,
	...
}

RLSpecificCauseItem-RL-SetupFailureFDD-ExtIEs NBAP-PROTOCOL-EXTENSION ::= {
	{ ID id-HSDSCH-FDD-Information-Response		CRITICALITY ignore		EXTENSION HSDSCH-FDD-Information-Response			PRESENCE optional }|
	{ ID id-ContinuousPacketConnectivityHS-SCCH-less-Information-Response		CRITICALITY ignore		EXTENSION	ContinuousPacketConnectivityHS-SCCH-less-Information-Response			PRESENCE optional }|
	{ ID id-Additional-HS-Cell-Information-Response		CRITICALITY ignore	EXTENSION	Additional-HS-Cell-Information-Response-List			PRESENCE optional},
	...
}

Unsuccessful-RL-InformationRespList-RL-SetupFailureFDD ::= SEQUENCE (SIZE (1..maxNrOfRLs))	OF ProtocolIE-Single-Container {{ Unsuccessful-RL-InformationRespItemIE-RL-SetupFailureFDD }}

Unsuccessful-RL-InformationRespItemIE-RL-SetupFailureFDD NBAP-PROTOCOL-IES ::= {
	{ ID id-Unsuccessful-RL-InformationRespItem-RL-SetupFailureFDD	CRITICALITY ignore		TYPE Unsuccessful-RL-InformationRespItem-RL-SetupFailureFDD	PRESENCE mandatory }
}

Unsuccessful-RL-InformationRespItem-RL-SetupFailureFDD ::= SEQUENCE {
	rL-ID								RL-ID,
	cause								Cause,
	iE-Extensions						ProtocolExtensionContainer { { Unsuccessful-RL-InformationRespItem-RL-SetupFailureFDD-ExtIEs} }		OPTIONAL,
	...
}

Unsuccessful-RL-InformationRespItem-RL-SetupFailureFDD-ExtIEs NBAP-PROTOCOL-EXTENSION ::= {
	...
}

Successful-RL-InformationRespList-RL-SetupFailureFDD ::= SEQUENCE (SIZE (1.. maxNrOfRLs)) OF ProtocolIE-Single-Container	{{ Successful-RL-InformationRespItemIE-RL-SetupFailureFDD }}

Successful-RL-InformationRespItemIE-RL-SetupFailureFDD NBAP-PROTOCOL-IES ::= {
	{ ID id-Successful-RL-InformationRespItem-RL-SetupFailureFDD		CRITICALITY ignore 		TYPE Successful-RL-InformationRespItem-RL-SetupFailureFDD	PRESENCE mandatory }
}

Successful-RL-InformationRespItem-RL-SetupFailureFDD ::= SEQUENCE {
	rL-ID										RL-ID,
	rL-Set-ID									RL-Set-ID,
	received-total-wide-band-power				Received-total-wide-band-power-Value,
	diversityIndication							DiversityIndication-RL-SetupFailureFDD,
	not-Used-dSCH-InformationResponseList		NULL						OPTIONAL,
	not-Used-tFCI2-BearerInformationResponse	NULL						OPTIONAL,
	sSDT-SupportIndicator						SSDT-SupportIndicator,
	iE-Extensions								ProtocolExtensionContainer { { Successful-RL-InformationRespItem-RL-SetupFailureFDD-ExtIEs} }		OPTIONAL,
	...
}

Successful-RL-InformationRespItem-RL-SetupFailureFDD-ExtIEs NBAP-PROTOCOL-EXTENSION ::= {
	{ ID id-DL-PowerBalancing-ActivationIndicator		CRITICALITY ignore	EXTENSION DL-PowerBalancing-ActivationIndicator			PRESENCE optional }|
	{ ID id-E-DCH-RL-Set-ID								CRITICALITY ignore	EXTENSION RL-Set-ID							PRESENCE optional }|
	{ ID id-E-DCH-FDD-DL-Control-Channel-Information	CRITICALITY ignore	EXTENSION E-DCH-FDD-DL-Control-Channel-Information		PRESENCE optional }|
	{ ID id-Initial-DL-DPCH-TimingAdjustment			CRITICALITY ignore	EXTENSION DL-DPCH-TimingAdjustment						PRESENCE optional }|
	{ ID id-HSDSCH-PreconfigurationInfo					CRITICALITY ignore	EXTENSION HSDSCH-PreconfigurationInfo					PRESENCE optional },
	...
}

DiversityIndication-RL-SetupFailureFDD ::= CHOICE {
 	combining									Combining-RL-SetupFailureFDD,
 	nonCombiningOrFirstRL						NonCombiningOrFirstRL-RL-SetupFailureFDD
}

Combining-RL-SetupFailureFDD ::= SEQUENCE {
 	rL-ID										RL-ID,
	iE-Extensions								ProtocolExtensionContainer { { CombiningItem-RL-SetupFailureFDD-ExtIEs} }		OPTIONAL,
	...
 }

CombiningItem-RL-SetupFailureFDD-ExtIEs NBAP-PROTOCOL-EXTENSION ::= {
	...
}

NonCombiningOrFirstRL-RL-SetupFailureFDD ::= SEQUENCE {
 	dCH-InformationResponse						DCH-InformationResponse,
	iE-Extensions									ProtocolExtensionContainer { { NonCombiningOrFirstRLItem-RL-SetupFailureFDD-ExtIEs} }		OPTIONAL,
	...
}

NonCombiningOrFirstRLItem-RL-SetupFailureFDD-ExtIEs NBAP-PROTOCOL-EXTENSION ::= {
	{ ID id-E-DCH-FDD-Information-Response		CRITICALITY ignore	EXTENSION E-DCH-FDD-Information-Response		PRESENCE optional },
	...
}

-- **************************************************************
--
-- RADIO LINK SETUP FAILURE TDD
--
-- **************************************************************

RadioLinkSetupFailureTDD ::= SEQUENCE {
	protocolIEs				ProtocolIE-Container		{{RadioLinkSetupFailureTDD-IEs}},
	protocolExtensions		ProtocolExtensionContainer	{{RadioLinkSetupFailureTDD-Extensions}}			OPTIONAL,
	...
}

RadioLinkSetupFailureTDD-IEs NBAP-PROTOCOL-IES ::= {
	{ ID	id-CRNC-CommunicationContextID			CRITICALITY ignore	TYPE CRNC-CommunicationContextID		PRESENCE mandatory	}|
	{ ID	id-CauseLevel-RL-SetupFailureTDD		CRITICALITY ignore	TYPE CauseLevel-RL-SetupFailureTDD		PRESENCE mandatory	}|
	{ ID	id-CriticalityDiagnostics				CRITICALITY ignore	TYPE CriticalityDiagnostics		PRESENCE optional	},
	...
}

RadioLinkSetupFailureTDD-Extensions NBAP-PROTOCOL-EXTENSION ::= {
	...
}

CauseLevel-RL-SetupFailureTDD ::= CHOICE {
	generalCause		GeneralCauseList-RL-SetupFailureTDD,
	rLSpecificCause		RLSpecificCauseList-RL-SetupFailureTDD,
	...
}

GeneralCauseList-RL-SetupFailureTDD ::= SEQUENCE {
	cause						Cause,
	iE-Extensions				ProtocolExtensionContainer { { GeneralCauseItem-RL-SetupFailureTDD-ExtIEs} }		OPTIONAL,
	...
}

GeneralCauseItem-RL-SetupFailureTDD-ExtIEs NBAP-PROTOCOL-EXTENSION ::= {
	...
}

RLSpecificCauseList-RL-SetupFailureTDD ::= SEQUENCE {
	unsuccessful-RL-InformationRespItem-RL-SetupFailureTDD	Unsuccessful-RL-InformationRespItem-RL-SetupFailureTDD,
	iE-Extensions											ProtocolExtensionContainer { { RLSpecificCauseItem-RL-SetupFailureTDD-ExtIEs} }		OPTIONAL,
	...
}

RLSpecificCauseItem-RL-SetupFailureTDD-ExtIEs NBAP-PROTOCOL-EXTENSION ::= {
	...
}

Unsuccessful-RL-InformationRespItem-RL-SetupFailureTDD ::= ProtocolIE-Single-Container { {Unsuccessful-RL-InformationRespItemIE-RL-SetupFailureTDD} }

Unsuccessful-RL-InformationRespItemIE-RL-SetupFailureTDD NBAP-PROTOCOL-IES ::= {
	{ ID id-Unsuccessful-RL-InformationResp-RL-SetupFailureTDD	CRITICALITY	ignore 	TYPE Unsuccessful-RL-InformationResp-RL-SetupFailureTDD		PRESENCE mandatory	}
}

Unsuccessful-RL-InformationResp-RL-SetupFailureTDD ::= SEQUENCE {
	rL-ID								RL-ID,
	cause								Cause,
	iE-Extensions						ProtocolExtensionContainer { { Unsuccessful-RL-InformationResp-RL-SetupFailureTDD-ExtIEs} }		OPTIONAL,
	...
}

Unsuccessful-RL-InformationResp-RL-SetupFailureTDD-ExtIEs NBAP-PROTOCOL-EXTENSION ::= {
	...
}

-- **************************************************************
--
-- RADIO LINK ADDITION REQUEST FDD
--
-- **************************************************************

RadioLinkAdditionRequestFDD ::= SEQUENCE {
	protocolIEs				ProtocolIE-Container		{{RadioLinkAdditionRequestFDD-IEs}},
	protocolExtensions		ProtocolExtensionContainer	{{RadioLinkAdditionRequestFDD-Extensions}}			OPTIONAL,
	...
}

RadioLinkAdditionRequestFDD-IEs NBAP-PROTOCOL-IES ::= {
	{ ID id-NodeB-CommunicationContextID			CRITICALITY reject	TYPE NodeB-CommunicationContextID		PRESENCE	mandatory	} |
	{ ID id-Compressed-Mode-Deactivation-Flag		CRITICALITY reject	TYPE Compressed-Mode-Deactivation-Flag		PRESENCE optional }|
	{ ID id-RL-InformationList-RL-AdditionRqstFDD	CRITICALITY notify	TYPE RL-InformationList-RL-AdditionRqstFDD		PRESENCE	mandatory	},
	...
}

RadioLinkAdditionRequestFDD-Extensions NBAP-PROTOCOL-EXTENSION ::= {
	{ ID id-Initial-DL-DPCH-TimingAdjustment-Allowed		CRITICALITY ignore	EXTENSION Initial-DL-DPCH-TimingAdjustment-Allowed						PRESENCE optional }|
	{ ID id-Serving-E-DCH-RL-ID						CRITICALITY reject	EXTENSION Serving-E-DCH-RL-ID							PRESENCE optional }|
	{ ID id-Serving-Cell-Change-CFN					CRITICALITY reject	EXTENSION CFN												PRESENCE optional }|
	{ ID id-HS-DSCH-Serving-Cell-Change-Info		CRITICALITY reject	EXTENSION HS-DSCH-Serving-Cell-Change-Info			PRESENCE optional }|
	{ ID id-E-DPCH-Information-RL-AdditionReqFDD	CRITICALITY reject	EXTENSION E-DPCH-Information-RL-AdditionReqFDD		PRESENCE optional }|
	{ ID id-E-DCH-FDD-Information					CRITICALITY reject	EXTENSION E-DCH-FDD-Information			PRESENCE conditional }|
	-- This IE shall be present if E-DPCH Information is present
	{ ID id-Additional-HS-Cell-Information-RL-Addition		CRITICALITY reject	EXTENSION Additional-HS-Cell-Information-RL-Addition-List			PRESENCE conditional },
	...
}

Additional-HS-Cell-Information-RL-Addition-List	::= SEQUENCE (SIZE (1..maxNrOfHSDSCH-1)) OF Additional-HS-Cell-Information-RL-Addition-ItemIEs

Additional-HS-Cell-Information-RL-Addition-ItemIEs	::=SEQUENCE{
	hSPDSCH-RL-ID								RL-ID,
	c-ID										C-ID										OPTIONAL,
	hS-DSCH-FDD-Secondary-Serving-Information	HS-DSCH-FDD-Secondary-Serving-Information	OPTIONAL,
	iE-Extensions					ProtocolExtensionContainer { { Additional-HS-Cell-Information-RL-Addition-ItemIEs-ExtIEs} } OPTIONAL,
	...
}

Additional-HS-Cell-Information-RL-Addition-ItemIEs-ExtIEs	NBAP-PROTOCOL-EXTENSION ::= {
	...
}

RL-InformationList-RL-AdditionRqstFDD	::= SEQUENCE (SIZE (1..maxNrOfRLs-1)) OF ProtocolIE-Single-Container {{ RL-InformationItemIE-RL-AdditionRqstFDD}}

RL-InformationItemIE-RL-AdditionRqstFDD NBAP-PROTOCOL-IES ::= {
	{ ID id-RL-InformationItem-RL-AdditionRqstFDD	CRITICALITY notify	TYPE RL-InformationItem-RL-AdditionRqstFDD			PRESENCE	mandatory}
}

RL-InformationItem-RL-AdditionRqstFDD ::= SEQUENCE {
	rL-ID										RL-ID,
	c-ID										C-ID,
	frameOffset									FrameOffset,
	chipOffset									ChipOffset,
	diversityControlField						DiversityControlField,
	dl-CodeInformation							FDD-DL-CodeInformation,
	initialDL-TransmissionPower					DL-Power						OPTIONAL,
 	maximumDL-Power								DL-Power						OPTIONAL,
 	minimumDL-Power								DL-Power						OPTIONAL,
 	not-Used-sSDT-CellIdentity					NULL							OPTIONAL,
	transmitDiversityIndicator					TransmitDiversityIndicator		OPTIONAL,
	iE-Extensions								ProtocolExtensionContainer { { RL-InformationItem-RL-AdditionRqstFDD-ExtIEs} }		OPTIONAL,
	...
}

RL-InformationItem-RL-AdditionRqstFDD-ExtIEs NBAP-PROTOCOL-EXTENSION ::= {
	{ ID id-DLReferencePower							CRITICALITY ignore	EXTENSION DL-Power							PRESENCE optional }|
	{ ID id-RL-Specific-DCH-Info						CRITICALITY ignore	EXTENSION RL-Specific-DCH-Info						PRESENCE optional }|
	{ ID id-DelayedActivation							CRITICALITY reject	EXTENSION DelayedActivation						PRESENCE optional }|
	{ ID id-E-DCH-RL-Indication							CRITICALITY reject	EXTENSION E-DCH-RL-Indication						PRESENCE optional }|
	{ ID id-RL-Specific-E-DCH-Info						CRITICALITY ignore	EXTENSION RL-Specific-E-DCH-Info						PRESENCE optional }|
	{ ID id-SynchronisationIndicator					CRITICALITY ignore	EXTENSION SynchronisationIndicator						PRESENCE optional }|
	{ ID id-F-DPCH-SlotFormat							CRITICALITY reject	EXTENSION F-DPCH-SlotFormat										PRESENCE optional }|
	{ ID id-HSDSCH-PreconfigurationSetup				CRITICALITY ignore	EXTENSION HSDSCH-PreconfigurationSetup						PRESENCE optional },
	...
}

E-DPCH-Information-RL-AdditionReqFDD ::= SEQUENCE {
	maxSet-E-DPDCHs								Max-Set-E-DPDCHs,
	ul-PunctureLimit							PunctureLimit,
	e-TFCS-Information							E-TFCS-Information,
	e-TTI										E-TTI,
	e-DPCCH-PO									E-DPCCH-PO,
	e-RGCH-2-IndexStepThreshold					E-RGCH-2-IndexStepThreshold,
	e-RGCH-3-IndexStepThreshold					E-RGCH-3-IndexStepThreshold,
	hARQ-Info-for-E-DCH							HARQ-Info-for-E-DCH,
	iE-Extensions								ProtocolExtensionContainer { { E-DPCH-Information-RL-AdditionReqFDD-ExtIEs} }		OPTIONAL,
	...
}

E-DPCH-Information-RL-AdditionReqFDD-ExtIEs NBAP-PROTOCOL-EXTENSION ::= {
	{ ID id-HSDSCH-Configured-Indicator		CRITICALITY	reject	EXTENSION	HSDSCH-Configured-Indicator		PRESENCE mandatory }|
	-- This shall be present for EDPCH configuration with HSDCH
	{ ID id-MinimumReducedE-DPDCH-GainFactor		CRITICALITY ignore	EXTENSION MinimumReducedE-DPDCH-GainFactor	PRESENCE optional },
	...
}


-- **************************************************************
--
-- RADIO LINK ADDITION REQUEST TDD
--
-- **************************************************************

RadioLinkAdditionRequestTDD ::= SEQUENCE {
	protocolIEs				ProtocolIE-Container		{{RadioLinkAdditionRequestTDD-IEs}},
	protocolExtensions		ProtocolExtensionContainer	{{RadioLinkAdditionRequestTDD-Extensions}}		OPTIONAL,
	...
}

RadioLinkAdditionRequestTDD-IEs NBAP-PROTOCOL-IES ::= {
	{ ID id-NodeB-CommunicationContextID					CRITICALITY reject	TYPE NodeB-CommunicationContextID						PRESENCE mandatory }|
	{ ID id-UL-CCTrCH-InformationList-RL-AdditionRqstTDD	CRITICALITY reject	TYPE UL-CCTrCH-InformationList-RL-AdditionRqstTDD	PRESENCE optional }|
	{ ID id-DL-CCTrCH-InformationList-RL-AdditionRqstTDD	CRITICALITY reject	TYPE DL-CCTrCH-InformationList-RL-AdditionRqstTDD	PRESENCE optional }|
	{ ID id-RL-Information-RL-AdditionRqstTDD				CRITICALITY reject	TYPE RL-Information-RL-AdditionRqstTDD					PRESENCE mandatory },
	...
}

RadioLinkAdditionRequestTDD-Extensions NBAP-PROTOCOL-EXTENSION ::= {
	{ ID id-HSDSCH-TDD-Information			CRITICALITY reject		EXTENSION HSDSCH-TDD-Information	PRESENCE optional	}|
	{ ID id-HSDSCH-RNTI						CRITICALITY reject		EXTENSION HSDSCH-RNTI			PRESENCE conditional	}|
	-- The IE shall be present if HS-PDSCH RL ID IE is present.
	{ ID id-HSPDSCH-RL-ID					CRITICALITY reject		EXTENSION RL-ID					PRESENCE optional	}|
	{ ID id-E-DCH-Information				CRITICALITY reject		EXTENSION E-DCH-Information		PRESENCE optional	}|
	{ ID id-E-DCH-Serving-RL-ID				CRITICALITY reject		EXTENSION RL-ID					PRESENCE optional	}|
	{ ID id-E-DCH-768-Information			CRITICALITY reject		EXTENSION E-DCH-768-Information	PRESENCE optional	}|
	{ ID id-E-DCH-LCR-Information			CRITICALITY reject		EXTENSION E-DCH-LCR-Information						PRESENCE optional	}|
	{ ID id-PowerControlGAP					CRITICALITY ignore		EXTENSION ControlGAP									PRESENCE optional },
	 -- Applicable to 1.28Mcps TDD only
	...
}

UL-CCTrCH-InformationList-RL-AdditionRqstTDD ::= SEQUENCE (SIZE (1..maxNrOfCCTrCHs)) OF UL-CCTrCH-InformationItem-RL-AdditionRqstTDD

UL-CCTrCH-InformationItem-RL-AdditionRqstTDD ::= SEQUENCE {
	cCTrCH-ID									CCTrCH-ID,
	uL-DPCH-Information							UL-DPCH-InformationList-RL-AdditionRqstTDD		OPTIONAL, -- Applicable to 3.84cps TDD only
	iE-Extensions								ProtocolExtensionContainer { { UL-CCTrCH-InformationItem-RL-AdditionRqstTDD-ExtIEs} }		OPTIONAL,
	...
}

UL-CCTrCH-InformationItem-RL-AdditionRqstTDD-ExtIEs NBAP-PROTOCOL-EXTENSION ::= {
	{ ID id-UL-DPCH-InformationItem-LCR-RL-AdditionRqstTDD	CRITICALITY notify	EXTENSION UL-DPCH-InformationItem-LCR-RL-AdditionRqstTDD			PRESENCE	optional }|	-- Applicable to 1.28cps TDD only
	{ ID id-TDD-TPC-UplinkStepSize-LCR-RL-AdditionRqstTDD	CRITICALITY reject	EXTENSION TDD-TPC-UplinkStepSize-LCR	PRESENCE optional	}|-- Applicable to 1.28cps TDD only
	{ ID id-UL-DPCH-InformationItem-768-RL-AdditionRqstTDD	CRITICALITY notify	EXTENSION UL-DPCH-InformationItem-768-RL-AdditionRqstTDD			PRESENCE	optional },	-- Applicable to 7.68Mcps TDD only
	...
}

UL-DPCH-InformationList-RL-AdditionRqstTDD ::= ProtocolIE-Single-Container {{ UL-DPCH-InformationItemIE-RL-AdditionRqstTDD }}

UL-DPCH-InformationItemIE-RL-AdditionRqstTDD NBAP-PROTOCOL-IES ::= {
	{ ID id-UL-DPCH-InformationItem-RL-AdditionRqstTDD	CRITICALITY notify	TYPE UL-DPCH-InformationItem-RL-AdditionRqstTDD	PRESENCE optional }
	-- For 3.84Mcps TDD only
}

UL-DPCH-InformationItem-RL-AdditionRqstTDD ::= SEQUENCE {	
	repetitionPeriod						RepetitionPeriod,
	repetitionLength						RepetitionLength,
	tdd-DPCHOffset							TDD-DPCHOffset,
	uL-Timeslot-Information					UL-Timeslot-Information,
	iE-Extensions							ProtocolExtensionContainer { { UL-DPCH-InformationItem-RL-AdditionRqstTDD-ExtIEs} }		OPTIONAL,
	...
}

UL-DPCH-InformationItem-RL-AdditionRqstTDD-ExtIEs  NBAP-PROTOCOL-EXTENSION ::= {
	...
}

UL-DPCH-InformationItem-LCR-RL-AdditionRqstTDD ::= SEQUENCE {
	repetitionPeriod						RepetitionPeriod,
	repetitionLength						RepetitionLength,
	tdd-DPCHOffset							TDD-DPCHOffset,
	uL-TimeslotLCR-Information				UL-TimeslotLCR-Information,
	iE-Extensions							ProtocolExtensionContainer { { UL-DPCH-InformationItem-LCR-RL-AdditionRqstTDD-ExtIEs} }		OPTIONAL,
	...
}

UL-DPCH-InformationItem-LCR-RL-AdditionRqstTDD-ExtIEs NBAP-PROTOCOL-EXTENSION ::= {
	...
}

UL-DPCH-InformationItem-768-RL-AdditionRqstTDD ::= SEQUENCE {
	repetitionPeriod						RepetitionPeriod,
	repetitionLength						RepetitionLength,
	tdd-DPCHOffset							TDD-DPCHOffset,
	uL-Timeslot768-Information				UL-Timeslot768-Information,
	iE-Extensions							ProtocolExtensionContainer { { UL-DPCH-InformationItem-768-RL-AdditionRqstTDD-ExtIEs} }		OPTIONAL,
	...
}

UL-DPCH-InformationItem-768-RL-AdditionRqstTDD-ExtIEs NBAP-PROTOCOL-EXTENSION ::= {
	...
}

DL-CCTrCH-InformationList-RL-AdditionRqstTDD ::= SEQUENCE (SIZE (1..maxNrOfCCTrCHs)) OF DL-CCTrCH-InformationItem-RL-AdditionRqstTDD

DL-CCTrCH-InformationItem-RL-AdditionRqstTDD ::= SEQUENCE {
	cCTrCH-ID						CCTrCH-ID,
	dL-DPCH-Information				DL-DPCH-InformationList-RL-AdditionRqstTDD		OPTIONAL, 	-- Applicable to 3.84Mcps TDD only
	iE-Extensions					ProtocolExtensionContainer { { DL-CCTrCH-InformationItem-RL-AdditionRqstTDD-ExtIEs} }		OPTIONAL,
	...
}

DL-CCTrCH-InformationItem-RL-AdditionRqstTDD-ExtIEs  NBAP-PROTOCOL-EXTENSION ::= {
	{ ID	id-DL-DPCH-InformationItem-LCR-RL-AdditionRqstTDD	CRITICALITY notify		EXTENSION DL-DPCH-InformationItem-LCR-RL-AdditionRqstTDD			PRESENCE	optional }|	-- Applicable to 1.28Mcps TDD only
	{ ID id-CCTrCH-Initial-DL-Power-RL-AdditionRqstTDD			CRITICALITY ignore		EXTENSION DL-Power				PRESENCE optional	}|
	{ ID id-TDD-TPC-DownlinkStepSize-RL-AdditionRqstTDD			CRITICALITY reject		EXTENSION TDD-TPC-DownlinkStepSize	PRESENCE optional	}|
	{ ID id-CCTrCH-Maximum-DL-Power-RL-AdditionRqstTDD			CRITICALITY ignore		EXTENSION DL-Power				PRESENCE optional	}|
	{ ID id-CCTrCH-Minimum-DL-Power-RL-AdditionRqstTDD			CRITICALITY ignore		EXTENSION DL-Power				PRESENCE optional	}|
	{ ID	id-DL-DPCH-InformationItem-768-RL-AdditionRqstTDD	CRITICALITY notify		EXTENSION DL-DPCH-InformationItem-768-RL-AdditionRqstTDD			PRESENCE	optional },	-- Applicable to 7.68Mcps TDD only
	...
}

DL-DPCH-InformationList-RL-AdditionRqstTDD ::= ProtocolIE-Single-Container {{ DL-DPCH-InformationItemIE-RL-AdditionRqstTDD }}

DL-DPCH-InformationItemIE-RL-AdditionRqstTDD NBAP-PROTOCOL-IES ::= {
	{ ID id-DL-DPCH-InformationItem-RL-AdditionRqstTDD	CRITICALITY notify	TYPE DL-DPCH-InformationItem-RL-AdditionRqstTDD		PRESENCE mandatory }
}

DL-DPCH-InformationItem-RL-AdditionRqstTDD ::= SEQUENCE {
	repetitionPeriod						RepetitionPeriod,
	repetitionLength						RepetitionLength,
	tdd-DPCHOffset							TDD-DPCHOffset,
	dL-Timeslot-Information					DL-Timeslot-Information,
	iE-Extensions							ProtocolExtensionContainer { { DL-DPCH-InformationItem-RL-AdditionRqstTDD-ExtIEs} }			OPTIONAL,
	...
}

DL-DPCH-InformationItem-RL-AdditionRqstTDD-ExtIEs  NBAP-PROTOCOL-EXTENSION ::= {
	...
}

DL-DPCH-InformationItem-LCR-RL-AdditionRqstTDD ::= SEQUENCE {
	repetitionPeriod						RepetitionPeriod,
	repetitionLength						RepetitionLength,
	tdd-DPCHOffset							TDD-DPCHOffset,
	dL-TimeslotLCR-Information				DL-TimeslotLCR-Information,
	iE-Extensions							ProtocolExtensionContainer { { DL-DPCH-InformationItem-LCR-RL-AdditionRqstTDD-ExtIEs} }		OPTIONAL,
	...
}

DL-DPCH-InformationItem-LCR-RL-AdditionRqstTDD-ExtIEs NBAP-PROTOCOL-EXTENSION ::= {
	...
}

DL-DPCH-InformationItem-768-RL-AdditionRqstTDD ::= SEQUENCE {
	repetitionPeriod						RepetitionPeriod,
	repetitionLength						RepetitionLength,
	tdd-DPCHOffset							TDD-DPCHOffset,
	dL-Timeslot768-Information				DL-Timeslot768-Information,
	iE-Extensions							ProtocolExtensionContainer { { DL-DPCH-InformationItem-768-RL-AdditionRqstTDD-ExtIEs} }		OPTIONAL,
	...
}

DL-DPCH-InformationItem-768-RL-AdditionRqstTDD-ExtIEs NBAP-PROTOCOL-EXTENSION ::= {
	...
}

RL-Information-RL-AdditionRqstTDD ::= SEQUENCE {
 	rL-ID										RL-ID,
 	c-ID										C-ID,
 	frameOffset									FrameOffset,
 	diversityControlField						DiversityControlField,
	initial-DL-Transmission-Power				DL-Power			OPTIONAL,
 	maximumDL-Power								DL-Power			OPTIONAL,
 	minimumDL-Power								DL-Power			OPTIONAL,
	dL-TimeSlotISCPInfo							DL-TimeslotISCPInfo	OPTIONAL, 	-- Applicable to 3.84Mcps TDD and 7.68Mcps TDD only
	iE-Extensions								ProtocolExtensionContainer { { RL-information-RL-AdditionRqstTDD-ExtIEs} }			OPTIONAL,
	...
 }

RL-information-RL-AdditionRqstTDD-ExtIEs  NBAP-PROTOCOL-EXTENSION ::= {
	{ ID id-TimeslotISCP-InformationList-LCR-RL-AdditionRqstTDD	CRITICALITY reject	EXTENSION DL-TimeslotISCPInfoLCR			PRESENCE optional }|
	-- Applicable to 1.28Mcps TDD only
	{ ID id-RL-Specific-DCH-Info								CRITICALITY ignore	EXTENSION RL-Specific-DCH-Info		PRESENCE 	optional	}|
	{ ID id-DelayedActivation 									CRITICALITY reject	EXTENSION DelayedActivation PRESENCE optional }|
	{ ID id-UL-Synchronisation-Parameters-LCR					CRITICALITY reject	EXTENSION UL-Synchronisation-Parameters-LCR		PRESENCE 	optional }|	-- Mandatory for 1.28Mcps TDD, Not Applicable to 3.84Mcps TDD or 7.68Mcps TDD
	{ ID id-UARFCNforNt											CRITICALITY reject	EXTENSION UARFCN		PRESENCE optional },
	  -- Mandatory for 1.28Mcps TDD when using multiple frequencies
	...
}

-- **************************************************************
--
-- RADIO LINK ADDITION RESPONSE FDD
--
-- **************************************************************

RadioLinkAdditionResponseFDD ::= SEQUENCE {
	protocolIEs				ProtocolIE-Container		{{RadioLinkAdditionResponseFDD-IEs}},
	protocolExtensions		ProtocolExtensionContainer	{{RadioLinkAdditionResponseFDD-Extensions}}			OPTIONAL,
	...
}

RadioLinkAdditionResponseFDD-IEs NBAP-PROTOCOL-IES ::= {
	{ ID id-CRNC-CommunicationContextID						CRITICALITY ignore	TYPE CRNC-CommunicationContextID						PRESENCE mandatory }|
	{ ID id-RL-InformationResponseList-RL-AdditionRspFDD	CRITICALITY ignore	TYPE RL-InformationResponseList-RL-AdditionRspFDD	PRESENCE mandatory }|
	{ ID id-CriticalityDiagnostics							CRITICALITY ignore	TYPE CriticalityDiagnostics						PRESENCE optional },
	...
}

RadioLinkAdditionResponseFDD-Extensions NBAP-PROTOCOL-EXTENSION ::= {
{ ID id-HS-DSCH-Serving-Cell-Change-Info-Response			CRITICALITY ignore	EXTENSION HS-DSCH-Serving-Cell-Change-Info-Response				PRESENCE optional }|
{ ID id-E-DCH-Serving-Cell-Change-Info-Response				CRITICALITY ignore	EXTENSION E-DCH-Serving-Cell-Change-Info-Response					PRESENCE optional }|
{ ID id-MAChs-ResetIndicator								CRITICALITY ignore	EXTENSION MAChs-ResetIndicator												PRESENCE optional }|
{ ID id-Additional-HS-Cell-Change-Information-Response		CRITICALITY ignore	EXTENSION Additional-HS-Cell-Change-Information-Response-List				PRESENCE optional },
	...
}

Additional-HS-Cell-Change-Information-Response-List	::= SEQUENCE (SIZE (1..maxNrOfHSDSCH-1)) OF Additional-HS-Cell-Change-Information-Response-ItemIEs

Additional-HS-Cell-Change-Information-Response-ItemIEs	::=SEQUENCE{
	hSPDSCH-RL-ID												RL-ID,
	hS-DSCH-Secondary-Serving-Cell-Change-Information-Response	HS-DSCH-Secondary-Serving-Cell-Change-Information-Response,
	iE-Extensions					ProtocolExtensionContainer { { Additional-HS-Cell-Change-Information-Response-ItemIEs-ExtIEs} } OPTIONAL,
	...
}

Additional-HS-Cell-Change-Information-Response-ItemIEs-ExtIEs	NBAP-PROTOCOL-EXTENSION ::= {
	...
}

RL-InformationResponseList-RL-AdditionRspFDD ::= SEQUENCE (SIZE (1..maxNrOfRLs-1)) OF ProtocolIE-Single-Container {{ RL-InformationResponseItemIE-RL-AdditionRspFDD }}

RL-InformationResponseItemIE-RL-AdditionRspFDD NBAP-PROTOCOL-IES ::= {
	{ ID id-RL-InformationResponseItem-RL-AdditionRspFDD	CRITICALITY ignore	TYPE RL-InformationResponseItem-RL-AdditionRspFDD	PRESENCE mandatory }
}

RL-InformationResponseItem-RL-AdditionRspFDD ::= SEQUENCE {
	rL-ID								RL-ID,
	rL-Set-ID							RL-Set-ID,
	received-total-wide-band-power		Received-total-wide-band-power-Value,
	diversityIndication					DiversityIndication-RL-AdditionRspFDD,
	sSDT-SupportIndicator				SSDT-SupportIndicator,
	iE-Extensions						ProtocolExtensionContainer { { RL-InformationResponseItem-RL-AdditionRspFDD-ExtIEs} }		OPTIONAL,
	...
}

RL-InformationResponseItem-RL-AdditionRspFDD-ExtIEs  NBAP-PROTOCOL-EXTENSION ::= {
	{ ID id-DL-PowerBalancing-ActivationIndicator		CRITICALITY ignore	EXTENSION DL-PowerBalancing-ActivationIndicator			PRESENCE optional }|
	{ ID id-E-DCH-RL-Set-ID								CRITICALITY ignore	EXTENSION RL-Set-ID							PRESENCE optional }|
	{ ID id-E-DCH-FDD-DL-Control-Channel-Information	CRITICALITY ignore	EXTENSION E-DCH-FDD-DL-Control-Channel-Information		PRESENCE optional }|
	{ ID id-Initial-DL-DPCH-TimingAdjustment			CRITICALITY ignore	EXTENSION DL-DPCH-TimingAdjustment						PRESENCE optional }|
	{ ID id-HSDSCH-PreconfigurationInfo					CRITICALITY ignore	EXTENSION HSDSCH-PreconfigurationInfo					PRESENCE optional},
	...
}

DiversityIndication-RL-AdditionRspFDD ::= CHOICE {
	combining										Combining-RL-AdditionRspFDD,
	non-combining									Non-Combining-RL-AdditionRspFDD
}

Combining-RL-AdditionRspFDD ::= SEQUENCE {
	rL-ID											RL-ID,
	iE-Extensions									ProtocolExtensionContainer { { CombiningItem-RL-AdditionRspFDD-ExtIEs} }		OPTIONAL,
	...
}

CombiningItem-RL-AdditionRspFDD-ExtIEs  NBAP-PROTOCOL-EXTENSION ::= {
	{ ID id-E-DCH-FDD-Information-Response				CRITICALITY ignore	EXTENSION E-DCH-FDD-Information-Response				PRESENCE optional },
	...
}

Non-Combining-RL-AdditionRspFDD ::= SEQUENCE {
	dCH-InformationResponse						DCH-InformationResponse,
	iE-Extensions								ProtocolExtensionContainer { { Non-CombiningItem-RL-AdditionRspFDD-ExtIEs} }		OPTIONAL,
	...
}

Non-CombiningItem-RL-AdditionRspFDD-ExtIEs  NBAP-PROTOCOL-EXTENSION ::= {
	{ ID id-E-DCH-FDD-Information-Response				CRITICALITY ignore	EXTENSION E-DCH-FDD-Information-Response				PRESENCE optional },
	...
}

-- **************************************************************
--
-- RADIO LINK ADDITION RESPONSE TDD
--
-- **************************************************************

RadioLinkAdditionResponseTDD ::= SEQUENCE {
	protocolIEs				ProtocolIE-Container		{{RadioLinkAdditionResponseTDD-IEs}},
	protocolExtensions		ProtocolExtensionContainer	{{RadioLinkAdditionResponseTDD-Extensions}}		OPTIONAL,
	...
}

RadioLinkAdditionResponseTDD-IEs NBAP-PROTOCOL-IES ::= {
	{ ID id-CRNC-CommunicationContextID					CRITICALITY ignore	TYPE CRNC-CommunicationContextID						PRESENCE mandatory	}|
	{ ID id-RL-InformationResponse-RL-AdditionRspTDD	CRITICALITY ignore	TYPE RL-InformationResponse-RL-AdditionRspTDD				PRESENCE optional	}|		-- Mandatory for 3.84Mcps TDD and 7.68Mcps TDD, Not Applicable to 1.28Mcps TDD
	{ ID id-CriticalityDiagnostics						CRITICALITY ignore	TYPE CriticalityDiagnostics						PRESENCE optional	},
	...
}

RadioLinkAdditionResponseTDD-Extensions NBAP-PROTOCOL-EXTENSION ::= {
	{ ID id-RL-InformationResponse-LCR-RL-AdditionRspTDD		CRITICALITY ignore			EXTENSION RL-InformationResponse-LCR-RL-AdditionRspTDD 	PRESENCE optional }|	-- Mandatory for 1.28Mcps TDD, Not Applicable to 3.84Mcps TDD or 7.68Mcps TDD
	{ ID id-HSDSCH-TDD-Information-Response						CRITICALITY ignore			EXTENSION HSDSCH-TDD-Information-Response				PRESENCE optional}|
	{ ID id-E-DCH-Information-Response							CRITICALITY ignore			EXTENSION E-DCH-Information-Response					PRESENCE optional	},
	...
}

RL-InformationResponse-RL-AdditionRspTDD ::= SEQUENCE {
	rL-ID										RL-ID,
	uL-TimeSlot-ISCP-Info						UL-TimeSlot-ISCP-Info,
	ul-PhysCH-SF-Variation						UL-PhysCH-SF-Variation,
	dCH-Information								DCH-Information-RL-AdditionRspTDD					OPTIONAL,
	dSCH-InformationResponseList				DSCH-InformationResponseList-RL-AdditionRspTDD		OPTIONAL,
	uSCH-InformationResponseList				USCH-InformationResponseList-RL-AdditionRspTDD		OPTIONAL,
	iE-Extensions								ProtocolExtensionContainer { { RL-InformationResponse-RL-AdditionRspTDD-ExtIEs} }		OPTIONAL,
	...
}

RL-InformationResponse-RL-AdditionRspTDD-ExtIEs  NBAP-PROTOCOL-EXTENSION ::= {
	...
}

DCH-Information-RL-AdditionRspTDD ::= SEQUENCE {
	diversityIndication					DiversityIndication-RL-AdditionRspTDD,
	iE-Extensions						ProtocolExtensionContainer { { DCH-Information-RL-AdditionRspTDD-ExtIEs} } OPTIONAL,
	...
}

DCH-Information-RL-AdditionRspTDD-ExtIEs NBAP-PROTOCOL-EXTENSION ::= {
	...
}

DiversityIndication-RL-AdditionRspTDD ::= CHOICE {
	combining									Combining-RL-AdditionRspTDD,	-- Indicates whether the old Transport Bearer shall be reused or not
	non-Combining								Non-Combining-RL-AdditionRspTDD
}

Combining-RL-AdditionRspTDD ::= SEQUENCE {
	rL-ID										RL-ID,	-- Reference RL
	iE-Extensions								ProtocolExtensionContainer { { CombiningItem-RL-AdditionRspTDD-ExtIEs} }		OPTIONAL,
	...
}

CombiningItem-RL-AdditionRspTDD-ExtIEs  NBAP-PROTOCOL-EXTENSION ::= {
	...
}

Non-Combining-RL-AdditionRspTDD ::= SEQUENCE {
	dCH-InformationResponse						DCH-InformationResponse,
	iE-Extensions								ProtocolExtensionContainer { { Non-CombiningItem-RL-AdditionRspTDD-ExtIEs} }			OPTIONAL,
	...
}

Non-CombiningItem-RL-AdditionRspTDD-ExtIEs  NBAP-PROTOCOL-EXTENSION ::= {
	...
}

DSCH-InformationResponseList-RL-AdditionRspTDD ::= ProtocolIE-Single-Container {{ DSCH-InformationResponseListIEs-RL-AdditionRspTDD }}

DSCH-InformationResponseListIEs-RL-AdditionRspTDD NBAP-PROTOCOL-IES ::= {
	{ ID id-DSCH-InformationResponse   CRITICALITY ignore	TYPE DSCH-InformationResponse		PRESENCE mandatory }
}

USCH-InformationResponseList-RL-AdditionRspTDD ::= ProtocolIE-Single-Container {{ USCH-InformationResponseListIEs-RL-AdditionRspTDD }}

USCH-InformationResponseListIEs-RL-AdditionRspTDD NBAP-PROTOCOL-IES ::= {
	{ ID id-USCH-InformationResponse   CRITICALITY ignore	TYPE USCH-InformationResponse		PRESENCE mandatory }
}

RL-InformationResponse-LCR-RL-AdditionRspTDD ::= SEQUENCE {
	rL-ID										RL-ID,
	uL-TimeSlot-ISCP-InfoLCR					UL-TimeSlot-ISCP-LCR-Info,
	ul-PhysCH-SF-Variation						UL-PhysCH-SF-Variation,
	dCH-Information								DCH-Information-RL-AdditionRspTDD					OPTIONAL,
	dSCH-InformationResponseList				DSCH-InformationResponseList-RL-AdditionRspTDD		OPTIONAL,
	uSCH-InformationResponseList				USCH-InformationResponseList-RL-AdditionRspTDD		OPTIONAL,
	iE-Extensions								ProtocolExtensionContainer { { RL-InformationResponse-LCR-RL-AdditionRspTDD-ExtIEs} }		OPTIONAL,
	...
}

RL-InformationResponse-LCR-RL-AdditionRspTDD-ExtIEs  NBAP-PROTOCOL-EXTENSION ::= {
	...
}

-- **************************************************************
--
-- RADIO LINK ADDITION FAILURE FDD
--
-- **************************************************************

RadioLinkAdditionFailureFDD ::= SEQUENCE {
	protocolIEs				ProtocolIE-Container		{{RadioLinkAdditionFailureFDD-IEs}},
	protocolExtensions		ProtocolExtensionContainer	{{RadioLinkAdditionFailureFDD-Extensions}}		OPTIONAL,
	...
}

RadioLinkAdditionFailureFDD-IEs NBAP-PROTOCOL-IES ::= {
	{ ID id-CRNC-CommunicationContextID				CRITICALITY ignore		TYPE CRNC-CommunicationContextID					PRESENCE mandatory }|
	{ ID id-CauseLevel-RL-AdditionFailureFDD		CRITICALITY ignore		TYPE CauseLevel-RL-AdditionFailureFDD					PRESENCE mandatory }|
	{ ID id-CriticalityDiagnostics					CRITICALITY ignore		TYPE CriticalityDiagnostics					PRESENCE optional },
	...
}

RadioLinkAdditionFailureFDD-Extensions NBAP-PROTOCOL-EXTENSION ::= {
{ ID id-HS-DSCH-Serving-Cell-Change-Info-Response			CRITICALITY ignore	EXTENSION HS-DSCH-Serving-Cell-Change-Info-Response				PRESENCE optional }|
{ ID id-E-DCH-Serving-Cell-Change-Info-Response				CRITICALITY ignore	EXTENSION E-DCH-Serving-Cell-Change-Info-Response					PRESENCE optional }|
{ ID id-Additional-HS-Cell-Change-Information-Response			CRITICALITY ignore	EXTENSION Additional-HS-Cell-Change-Information-Response-List			PRESENCE optional },
	...
}

CauseLevel-RL-AdditionFailureFDD ::= CHOICE {
	generalCause		GeneralCauseList-RL-AdditionFailureFDD,
	rLSpecificCause		RLSpecificCauseList-RL-AdditionFailureFDD,
	...
}

GeneralCauseList-RL-AdditionFailureFDD ::= SEQUENCE {
	cause										Cause,
	iE-Extensions								ProtocolExtensionContainer { { GeneralCauseItem-RL-AdditionFailureFDD-ExtIEs} }			OPTIONAL,
	...
}

GeneralCauseItem-RL-AdditionFailureFDD-ExtIEs  NBAP-PROTOCOL-EXTENSION ::= {
	...
}

RLSpecificCauseList-RL-AdditionFailureFDD ::= SEQUENCE {
	unsuccessful-RL-InformationRespList-RL-AdditionFailureFDD		Unsuccessful-RL-InformationRespList-RL-AdditionFailureFDD,
	successful-RL-InformationRespList-RL-AdditionFailureFDD			Successful-RL-InformationRespList-RL-AdditionFailureFDD					OPTIONAL,
	iE-Extensions								ProtocolExtensionContainer { { RLSpecificCauseItem-RL-AdditionFailureFDD-ExtIEs} }			OPTIONAL,
	...
}

RLSpecificCauseItem-RL-AdditionFailureFDD-ExtIEs  NBAP-PROTOCOL-EXTENSION ::= {
	...
}

Unsuccessful-RL-InformationRespList-RL-AdditionFailureFDD ::= SEQUENCE	(SIZE (1..maxNrOfRLs-1)) OF ProtocolIE-Single-Container {{ Unsuccessful-RL-InformationRespItemIE-RL-AdditionFailureFDD }}

Unsuccessful-RL-InformationRespItemIE-RL-AdditionFailureFDD NBAP-PROTOCOL-IES ::= {
	{ ID id-Unsuccessful-RL-InformationRespItem-RL-AdditionFailureFDD	CRITICALITY ignore	TYPE Unsuccessful-RL-InformationRespItem-RL-AdditionFailureFDD	PRESENCE mandatory }
}

Unsuccessful-RL-InformationRespItem-RL-AdditionFailureFDD ::= SEQUENCE {
	rL-ID						RL-ID,
	cause						Cause,
	iE-Extensions				ProtocolExtensionContainer { { Unsuccessful-RL-InformationRespItem-RL-AdditionFailureFDD-ExtIEs} }			OPTIONAL,
	...
}

Unsuccessful-RL-InformationRespItem-RL-AdditionFailureFDD-ExtIEs  NBAP-PROTOCOL-EXTENSION ::= {
	...
}

Successful-RL-InformationRespList-RL-AdditionFailureFDD ::= SEQUENCE (SIZE (1..maxNrOfRLs-2)) OF ProtocolIE-Single-Container {{ Successful-RL-InformationRespItemIE-RL-AdditionFailureFDD }}

Successful-RL-InformationRespItemIE-RL-AdditionFailureFDD NBAP-PROTOCOL-IES ::= {
	{ ID id-Successful-RL-InformationRespItem-RL-AdditionFailureFDD	CRITICALITY ignore	TYPE Successful-RL-InformationRespItem-RL-AdditionFailureFDD	PRESENCE mandatory }
}

Successful-RL-InformationRespItem-RL-AdditionFailureFDD ::= SEQUENCE {
	rL-ID										RL-ID,
	rL-Set-ID									RL-Set-ID,
	received-total-wide-band-power				Received-total-wide-band-power-Value,
	diversityIndication							DiversityIndication-RL-AdditionFailureFDD,
	sSDT-SupportIndicator						SSDT-SupportIndicator,
	iE-Extensions								ProtocolExtensionContainer { { Successful-RL-InformationRespItem-RL-AdditionFailureFDD-ExtIEs} }		OPTIONAL,
	...
}

Successful-RL-InformationRespItem-RL-AdditionFailureFDD-ExtIEs  NBAP-PROTOCOL-EXTENSION ::= {
	{ ID id-DL-PowerBalancing-ActivationIndicator		CRITICALITY ignore	EXTENSION DL-PowerBalancing-ActivationIndicator			PRESENCE optional }|
	{ ID id-E-DCH-RL-Set-ID								CRITICALITY ignore	EXTENSION RL-Set-ID							PRESENCE optional }|
	{ ID id-E-DCH-FDD-DL-Control-Channel-Information	CRITICALITY ignore	EXTENSION E-DCH-FDD-DL-Control-Channel-Information		PRESENCE optional }|
	{ ID id-Initial-DL-DPCH-TimingAdjustment			CRITICALITY ignore	EXTENSION DL-DPCH-TimingAdjustment						PRESENCE optional }|
	{ ID id-HSDSCH-PreconfigurationInfo					CRITICALITY ignore	EXTENSION HSDSCH-PreconfigurationInfo					PRESENCE optional },
	...
}

DiversityIndication-RL-AdditionFailureFDD ::= CHOICE {
 	combining						Combining-RL-AdditionFailureFDD,
 	non-Combining					Non-Combining-RL-AdditionFailureFDD
}

Combining-RL-AdditionFailureFDD ::= SEQUENCE {
	rL-ID										RL-ID,
	iE-Extensions								ProtocolExtensionContainer { { CombiningItem-RL-AdditionFailureFDD-ExtIEs} }			OPTIONAL,
	...
 }

CombiningItem-RL-AdditionFailureFDD-ExtIEs NBAP-PROTOCOL-EXTENSION ::= {
	{ ID id-E-DCH-FDD-Information-Response				CRITICALITY ignore	EXTENSION E-DCH-FDD-Information-Response				PRESENCE optional },
	...
}

Non-Combining-RL-AdditionFailureFDD ::= SEQUENCE {
	dCH-InformationResponse						DCH-InformationResponse,
	iE-Extensions								ProtocolExtensionContainer { { Non-CombiningItem-RL-AdditionFailureFDD-ExtIEs} }			OPTIONAL,
	...
}

Non-CombiningItem-RL-AdditionFailureFDD-ExtIEs NBAP-PROTOCOL-EXTENSION ::= {
	{ ID id-E-DCH-FDD-Information-Response				CRITICALITY ignore	EXTENSION E-DCH-FDD-Information-Response				PRESENCE optional },
	...
}

-- **************************************************************
--
-- RADIO LINK ADDITION FAILURE TDD
--
-- **************************************************************

RadioLinkAdditionFailureTDD ::= SEQUENCE {
	protocolIEs				ProtocolIE-Container		{{RadioLinkAdditionFailureTDD-IEs}},
	protocolExtensions		ProtocolExtensionContainer	{{RadioLinkAdditionFailureTDD-Extensions}}		OPTIONAL,
	...
}

RadioLinkAdditionFailureTDD-IEs NBAP-PROTOCOL-IES ::= {
	{ ID	id-CRNC-CommunicationContextID				CRITICALITY ignore		TYPE CRNC-CommunicationContextID			PRESENCE mandatory }|
	{ ID    id-CauseLevel-RL-AdditionFailureTDD			CRITICALITY ignore		TYPE CauseLevel-RL-AdditionFailureTDD		PRESENCE mandatory }|
	{ ID	id-CriticalityDiagnostics					CRITICALITY ignore		TYPE CriticalityDiagnostics			PRESENCE optional },
	...
}

RadioLinkAdditionFailureTDD-Extensions NBAP-PROTOCOL-EXTENSION ::= {
	...
}

CauseLevel-RL-AdditionFailureTDD ::= CHOICE {
	generalCause		GeneralCauseList-RL-AdditionFailureTDD,
	rLSpecificCause		RLSpecificCauseList-RL-AdditionFailureTDD,
	...
}

GeneralCauseList-RL-AdditionFailureTDD ::= SEQUENCE {
	cause						Cause,
	iE-Extensions				ProtocolExtensionContainer { { GeneralCauseItem-RL-AdditionFailureTDD-ExtIEs} }		OPTIONAL,
	...
}

GeneralCauseItem-RL-AdditionFailureTDD-ExtIEs NBAP-PROTOCOL-EXTENSION ::= {
	...
}

RLSpecificCauseList-RL-AdditionFailureTDD ::= SEQUENCE {
	unsuccessful-RL-InformationRespItem-RL-AdditionFailureTDD	Unsuccessful-RL-InformationRespItem-RL-AdditionFailureTDD,
	iE-Extensions												ProtocolExtensionContainer { { RLSpecificCauseItem-RL-AdditionFailureTDD-ExtIEs} }		OPTIONAL,
	...
}

RLSpecificCauseItem-RL-AdditionFailureTDD-ExtIEs NBAP-PROTOCOL-EXTENSION ::= {
	...
}

Unsuccessful-RL-InformationRespItem-RL-AdditionFailureTDD ::= ProtocolIE-Single-Container { {Unsuccessful-RL-InformationRespItemIE-RL-AdditionFailureTDD} }

Unsuccessful-RL-InformationRespItemIE-RL-AdditionFailureTDD NBAP-PROTOCOL-IES ::= {
	{ ID id-Unsuccessful-RL-InformationResp-RL-AdditionFailureTDD	CRITICALITY ignore	TYPE Unsuccessful-RL-InformationResp-RL-AdditionFailureTDD	PRESENCE mandatory }
}

Unsuccessful-RL-InformationResp-RL-AdditionFailureTDD ::= SEQUENCE {
	rL-ID							RL-ID,
	cause							Cause,
	iE-Extensions					ProtocolExtensionContainer { { Unsuccessful-RL-InformationResp-RL-AdditionFailureTDD-ExtIEs} }		OPTIONAL,
	...
}

Unsuccessful-RL-InformationResp-RL-AdditionFailureTDD-ExtIEs  NBAP-PROTOCOL-EXTENSION ::= {
	...
}

-- **************************************************************
--
-- RADIO LINK RECONFIGURATION PREPARE FDD
--
-- **************************************************************

RadioLinkReconfigurationPrepareFDD ::= SEQUENCE {
	protocolIEs				ProtocolIE-Container		{{RadioLinkReconfigurationPrepareFDD-IEs}},
	protocolExtensions		ProtocolExtensionContainer	{{RadioLinkReconfigurationPrepareFDD-Extensions}}		OPTIONAL,
	...
}

RadioLinkReconfigurationPrepareFDD-IEs NBAP-PROTOCOL-IES ::= {
	{ ID id-NodeB-CommunicationContextID					CRITICALITY reject	TYPE NodeB-CommunicationContextID							PRESENCE mandatory }|
	{ ID id-UL-DPCH-Information-RL-ReconfPrepFDD			CRITICALITY reject	TYPE UL-DPCH-Information-RL-ReconfPrepFDD					PRESENCE optional }|
	{ ID id-DL-DPCH-Information-RL-ReconfPrepFDD			CRITICALITY reject	TYPE DL-DPCH-Information-RL-ReconfPrepFDD					PRESENCE optional }|
	{ ID id-FDD-DCHs-to-Modify								CRITICALITY reject	TYPE FDD-DCHs-to-Modify							PRESENCE optional }|
	{ ID id-DCHs-to-Add-FDD									CRITICALITY reject	TYPE DCH-FDD-Information							PRESENCE optional }|
	{ ID id-DCH-DeleteList-RL-ReconfPrepFDD					CRITICALITY reject	TYPE DCH-DeleteList-RL-ReconfPrepFDD						PRESENCE optional }|
	{ ID id-RL-InformationList-RL-ReconfPrepFDD				CRITICALITY reject	TYPE RL-InformationList-RL-ReconfPrepFDD					PRESENCE optional }|
	{ ID id-Transmission-Gap-Pattern-Sequence-Information	CRITICALITY reject	TYPE Transmission-Gap-Pattern-Sequence-Information		PRESENCE optional },
	...
}

RadioLinkReconfigurationPrepareFDD-Extensions NBAP-PROTOCOL-EXTENSION ::= {
	{ ID id-SignallingBearerRequestIndicator		CRITICALITY reject	EXTENSION SignallingBearerRequestIndicator				PRESENCE optional }|
	{ ID id-HSDSCH-FDD-Information					CRITICALITY reject	EXTENSION HSDSCH-FDD-Information				PRESENCE optional }|
	{ ID id-HSDSCH-Information-to-Modify			CRITICALITY reject	EXTENSION HSDSCH-Information-to-Modify				PRESENCE optional }|
	{ ID id-HSDSCH-MACdFlows-to-Add					CRITICALITY reject	EXTENSION HSDSCH-MACdFlows-Information				PRESENCE optional }|
	{ ID id-HSDSCH-MACdFlows-to-Delete				CRITICALITY reject	EXTENSION HSDSCH-MACdFlows-to-Delete				PRESENCE optional }|
	{ ID id-HSDSCH-RNTI								CRITICALITY reject	EXTENSION HSDSCH-RNTI					PRESENCE conditional }|
	-- The IE shall be present if HS-PDSCH RL ID IE is present.
	{ ID id-HSPDSCH-RL-ID							CRITICALITY reject	EXTENSION RL-ID							PRESENCE optional }|
	{ ID id-E-DPCH-Information-RL-ReconfPrepFDD		CRITICALITY reject	EXTENSION E-DPCH-Information-RL-ReconfPrepFDD			PRESENCE optional }|
	{ ID id-E-DCH-FDD-Information					CRITICALITY reject	EXTENSION E-DCH-FDD-Information				PRESENCE optional }|
	{ ID id-E-DCH-FDD-Information-to-Modify			CRITICALITY reject	EXTENSION E-DCH-FDD-Information-to-Modify				PRESENCE optional }|
	{ ID id-E-DCH-MACdFlows-to-Add					CRITICALITY reject	EXTENSION E-DCH-MACdFlows-Information				PRESENCE optional }|
	{ ID id-E-DCH-MACdFlows-to-Delete				CRITICALITY reject	EXTENSION E-DCH-MACdFlows-to-Delete				PRESENCE optional }|
	{ ID id-Serving-E-DCH-RL-ID						CRITICALITY reject	EXTENSION Serving-E-DCH-RL-ID				PRESENCE optional }|
	{ ID id-F-DPCH-Information-RL-ReconfPrepFDD		CRITICALITY reject	EXTENSION F-DPCH-Information-RL-ReconfPrepFDD			PRESENCE optional }|
	{ ID id-Fast-Reconfiguration-Mode				CRITICALITY ignore	EXTENSION Fast-Reconfiguration-Mode				PRESENCE optional }|
	{ ID id-CPC-Information							CRITICALITY reject	EXTENSION CPC-Information				PRESENCE optional }|
	{ ID id-Additional-HS-Cell-Information-RL-Reconf-Prep	CRITICALITY reject	EXTENSION Additional-HS-Cell-Information-RL-Reconf-Prep			PRESENCE optional },
	...
}

Additional-HS-Cell-Information-RL-Reconf-Prep	::= SEQUENCE (SIZE (1..maxNrOfHSDSCH-1)) OF Additional-HS-Cell-Information-RL-Reconf-Prep-ItemIEs

Additional-HS-Cell-Information-RL-Reconf-Prep-ItemIEs	::=SEQUENCE{
	hSPDSCH-RL-ID									RL-ID,
	c-ID											C-ID												OPTIONAL,
	hS-DSCH-FDD-Secondary-Serving-Information		HS-DSCH-FDD-Secondary-Serving-Information			OPTIONAL,
	hS-DSCH-Secondary-Serving-Information-To-Modify	HS-DSCH-Secondary-Serving-Information-To-Modify	OPTIONAL,
	hS-HS-DSCH-Secondary-Serving-Remove				HS-DSCH-Secondary-Serving-Remove					OPTIONAL,
	iE-Extensions					ProtocolExtensionContainer { { Additional-HS-Cell-Information-RL-Reconf-Prep-ItemIEs-ExtIEs} } OPTIONAL,
	...
}

Additional-HS-Cell-Information-RL-Reconf-Prep-ItemIEs-ExtIEs	NBAP-PROTOCOL-EXTENSION ::= {
	...
}

UL-DPCH-Information-RL-ReconfPrepFDD ::= SEQUENCE {
	ul-ScramblingCode								UL-ScramblingCode					OPTIONAL,
	ul-SIR-Target									UL-SIR								OPTIONAL,
	minUL-ChannelisationCodeLength					MinUL-ChannelisationCodeLength		OPTIONAL,
	maxNrOfUL-DPDCHs								MaxNrOfUL-DPDCHs					OPTIONAL,
	-- This IE shall be present if minUL-ChannelisationCodeLength Ie is set to 4 
	ul-PunctureLimit								PunctureLimit						OPTIONAL,
	tFCS											TFCS								OPTIONAL,
	ul-DPCCH-SlotFormat								UL-DPCCH-SlotFormat					OPTIONAL,
	diversityMode									DiversityMode						OPTIONAL,
	not-Used-sSDT-CellIDLength						NULL								OPTIONAL,
	not-Used-s-FieldLength							NULL								OPTIONAL,
	iE-Extensions									ProtocolExtensionContainer { { UL-DPCH-Information-RL-ReconfPrepFDD-ExtIEs} }		OPTIONAL,
	...
}

UL-DPCH-Information-RL-ReconfPrepFDD-ExtIEs  NBAP-PROTOCOL-EXTENSION ::= {
	{ ID id-UL-DPDCH-Indicator-For-E-DCH-Operation	CRITICALITY reject	EXTENSION UL-DPDCH-Indicator-For-E-DCH-Operation			PRESENCE optional },
	...
}

DL-DPCH-Information-RL-ReconfPrepFDD ::= SEQUENCE {
	tFCS											TFCS								OPTIONAL,
	dl-DPCH-SlotFormat								DL-DPCH-SlotFormat					OPTIONAL,
	tFCI-SignallingMode								TFCI-SignallingMode					OPTIONAL,
	tFCI-Presence									TFCI-Presence						OPTIONAL,
	-- This IE shall be present if the DL DPCH Slot Format IE is set to any of the values from 12 to 16
	multiplexingPosition							MultiplexingPosition 				OPTIONAL,
	not-Used-pDSCH-CodeMapping						NULL								OPTIONAL,
	not-Used-pDSCH-RL-ID							NULL								OPTIONAL,
	limitedPowerIncrease							LimitedPowerIncrease				OPTIONAL,
	iE-Extensions									ProtocolExtensionContainer { { DL-DPCH-Information-RL-ReconfPrepFDD-ExtIEs} }		OPTIONAL,
	...
}

DL-DPCH-Information-RL-ReconfPrepFDD-ExtIEs  NBAP-PROTOCOL-EXTENSION ::= {
	{ ID id-DL-DPCH-Power-Information-RL-ReconfPrepFDD	CRITICALITY reject	EXTENSION DL-DPCH-Power-Information-RL-ReconfPrepFDD	PRESENCE optional },
	...
}

DL-DPCH-Power-Information-RL-ReconfPrepFDD ::= SEQUENCE {
	powerOffsetInformation					PowerOffsetInformation-RL-ReconfPrepFDD,
	fdd-TPC-DownlinkStepSize				FDD-TPC-DownlinkStepSize,
	innerLoopDLPCStatus						InnerLoopDLPCStatus,
	iE-Extensions							ProtocolExtensionContainer { { DL-DPCH-Power-Information-RL-ReconfPrepFDD-ExtIEs } }			OPTIONAL,
	...
}

DL-DPCH-Power-Information-RL-ReconfPrepFDD-ExtIEs NBAP-PROTOCOL-EXTENSION ::= {
	...
}

PowerOffsetInformation-RL-ReconfPrepFDD ::= SEQUENCE {
	pO1-ForTFCI-Bits						PowerOffset,
	pO2-ForTPC-Bits							PowerOffset,
	pO3-ForPilotBits						PowerOffset,
	iE-Extensions							ProtocolExtensionContainer { { PowerOffsetInformation-RL-ReconfPrepFDD-ExtIEs} }		OPTIONAL,
	...
}

PowerOffsetInformation-RL-ReconfPrepFDD-ExtIEs NBAP-PROTOCOL-EXTENSION ::= {
	...
}

DCH-DeleteList-RL-ReconfPrepFDD ::= SEQUENCE (SIZE (1..maxNrOfDCHs)) OF DCH-DeleteItem-RL-ReconfPrepFDD

DCH-DeleteItem-RL-ReconfPrepFDD ::= SEQUENCE {
	dCH-ID											DCH-ID,
	iE-Extensions									ProtocolExtensionContainer { { DCH-DeleteItem-RL-ReconfPrepFDD-ExtIEs} }		OPTIONAL,
	...
}

DCH-DeleteItem-RL-ReconfPrepFDD-ExtIEs  NBAP-PROTOCOL-EXTENSION ::= {
	...
}

RL-InformationList-RL-ReconfPrepFDD ::= SEQUENCE (SIZE (1..maxNrOfRLs)) OF ProtocolIE-Single-Container {{ RL-InformationItemIE-RL-ReconfPrepFDD }}

RL-InformationItemIE-RL-ReconfPrepFDD NBAP-PROTOCOL-IES ::= {
	{ ID	id-RL-InformationItem-RL-ReconfPrepFDD			CRITICALITY		reject			TYPE 	RL-InformationItem-RL-ReconfPrepFDD		PRESENCE	mandatory}
}

RL-InformationItem-RL-ReconfPrepFDD ::= SEQUENCE {
	rL-ID											RL-ID,
	dl-CodeInformation								FDD-DL-CodeInformation						OPTIONAL,
	maxDL-Power										DL-Power									OPTIONAL,
	minDL-Power										DL-Power									OPTIONAL,
	not-Used-sSDT-Indication						NULL										OPTIONAL,
	not-Used-sSDT-Cell-Identity						NULL										OPTIONAL,
	transmitDiversityIndicator						TransmitDiversityIndicator					OPTIONAL,
	-- This IE shall be present if Diversity Mode IE is present in UL DPCH Information IE and it is not set to “none”
	iE-Extensions									ProtocolExtensionContainer { { RL-InformationItem-RL-ReconfPrepFDD-ExtIEs} }		OPTIONAL,
	...
}

RL-InformationItem-RL-ReconfPrepFDD-ExtIEs  NBAP-PROTOCOL-EXTENSION ::= {
	{ ID id-DLReferencePower						CRITICALITY ignore	EXTENSION DL-Power						PRESENCE optional }|
	{ ID id-RL-Specific-DCH-Info					CRITICALITY ignore	EXTENSION RL-Specific-DCH-Info				PRESENCE optional }|
	{ ID id-DL-DPCH-TimingAdjustment				CRITICALITY reject	EXTENSION DL-DPCH-TimingAdjustment				PRESENCE optional }|
	{ ID id-Primary-CPICH-Usage-for-Channel-Estimation		CRITICALITY ignore	EXTENSION Primary-CPICH-Usage-for-Channel-Estimation					PRESENCE optional}|
	{ ID id-Secondary-CPICH-Information-Change		CRITICALITY ignore	EXTENSION Secondary-CPICH-Information-Change			PRESENCE optional }|
	{ ID id-E-DCH-RL-Indication						CRITICALITY reject	EXTENSION E-DCH-RL-Indication				PRESENCE optional }|
	{ ID id-RL-Specific-E-DCH-Info					CRITICALITY ignore	EXTENSION RL-Specific-E-DCH-Info				PRESENCE optional }|
	{ ID id-F-DPCH-SlotFormat						CRITICALITY reject	EXTENSION F-DPCH-SlotFormat				PRESENCE optional },
	...
}

E-DPCH-Information-RL-ReconfPrepFDD ::= SEQUENCE {
	maxSet-E-DPDCHs								Max-Set-E-DPDCHs													OPTIONAL,
	ul-PunctureLimit							PunctureLimit														OPTIONAL,
	e-TFCS-Information							E-TFCS-Information													OPTIONAL,
	e-TTI										E-TTI																OPTIONAL,
	e-DPCCH-PO									E-DPCCH-PO															OPTIONAL,
	e-RGCH-2-IndexStepThreshold					E-RGCH-2-IndexStepThreshold											OPTIONAL,
	e-RGCH-3-IndexStepThreshold					E-RGCH-3-IndexStepThreshold																	OPTIONAL,
	hARQ-Info-for-E-DCH							HARQ-Info-for-E-DCH																			OPTIONAL,
	hSDSCH-Configured-Indicator					HSDSCH-Configured-Indicator																	OPTIONAL,
	iE-Extensions								ProtocolExtensionContainer { { E-DPCH-Information-RL-ReconfPrepFDD-ExtIEs} }		OPTIONAL,
	...
}

E-DPCH-Information-RL-ReconfPrepFDD-ExtIEs NBAP-PROTOCOL-EXTENSION ::= {
	{ ID id-MinimumReducedE-DPDCH-GainFactor		CRITICALITY ignore	EXTENSION MinimumReducedE-DPDCH-GainFactor	PRESENCE optional },
	...
}

F-DPCH-Information-RL-ReconfPrepFDD ::= SEQUENCE {
	powerOffsetInformation				PowerOffsetInformation-F-DPCH-RL-ReconfPrepFDD,
	fdd-TPC-DownlinkStepSize			FDD-TPC-DownlinkStepSize,
	limitedPowerIncrease				LimitedPowerIncrease,
	innerLoopDLPCStatus					InnerLoopDLPCStatus,
	iE-Extensions						ProtocolExtensionContainer { { F-DPCH-Information-RL-ReconfPrepFDD-ExtIEs} }					OPTIONAL,
	...
}

F-DPCH-Information-RL-ReconfPrepFDD-ExtIEs NBAP-PROTOCOL-EXTENSION ::= {
	...
}

PowerOffsetInformation-F-DPCH-RL-ReconfPrepFDD ::= SEQUENCE {
	pO2-ForTPC-Bits						PowerOffset,
	-- This IE shall be ignored by Node B
	iE-Extensions						ProtocolExtensionContainer { { PowerOffsetInformation-F-DPCH-RL-ReconfPrepFDD-ExtIEs} }		OPTIONAL,
	...
}

PowerOffsetInformation-F-DPCH-RL-ReconfPrepFDD-ExtIEs NBAP-PROTOCOL-EXTENSION ::= {
	...
}

-- **************************************************************
--
-- RADIO LINK RECONFIGURATION PREPARE TDD
--
-- **************************************************************

RadioLinkReconfigurationPrepareTDD ::= SEQUENCE {
	protocolIEs				ProtocolIE-Container		{{RadioLinkReconfigurationPrepareTDD-IEs}},
	protocolExtensions		ProtocolExtensionContainer	{{RadioLinkReconfigurationPrepareTDD-Extensions}}		OPTIONAL,
	...
}

RadioLinkReconfigurationPrepareTDD-IEs NBAP-PROTOCOL-IES ::= {
	{ ID id-NodeB-CommunicationContextID						CRITICALITY reject	TYPE NodeB-CommunicationContextID				PRESENCE mandatory }|
	{ ID id-UL-CCTrCH-InformationAddList-RL-ReconfPrepTDD		CRITICALITY reject	TYPE UL-CCTrCH-InformationAddList-RL-ReconfPrepTDD			PRESENCE optional }|
	{ ID id-UL-CCTrCH-InformationModifyList-RL-ReconfPrepTDD	CRITICALITY reject	TYPE UL-CCTrCH-InformationModifyList-RL-ReconfPrepTDD			PRESENCE optional }|
	{ ID id-UL-CCTrCH-InformationDeleteList-RL-ReconfPrepTDD	CRITICALITY reject	TYPE UL-CCTrCH-InformationDeleteList-RL-ReconfPrepTDD			PRESENCE optional }|
	{ ID id-DL-CCTrCH-InformationAddList-RL-ReconfPrepTDD		CRITICALITY reject	TYPE DL-CCTrCH-InformationAddList-RL-ReconfPrepTDD			PRESENCE optional }|
	{ ID id-DL-CCTrCH-InformationModifyList-RL-ReconfPrepTDD	CRITICALITY reject	TYPE DL-CCTrCH-InformationModifyList-RL-ReconfPrepTDD			PRESENCE optional }|
	{ ID id-DL-CCTrCH-InformationDeleteList-RL-ReconfPrepTDD	CRITICALITY reject	TYPE DL-CCTrCH-InformationDeleteList-RL-ReconfPrepTDD			PRESENCE optional }|
	{ ID id-TDD-DCHs-to-Modify									CRITICALITY reject	TYPE TDD-DCHs-to-Modify					PRESENCE optional }|
	{ ID id-DCHs-to-Add-TDD										CRITICALITY reject	TYPE DCH-TDD-Information					PRESENCE optional }|
	{ ID id-DCH-DeleteList-RL-ReconfPrepTDD						CRITICALITY reject	TYPE DCH-DeleteList-RL-ReconfPrepTDD			PRESENCE optional }|
	{ ID id-DSCH-Information-ModifyList-RL-ReconfPrepTDD		CRITICALITY reject	TYPE DSCH-Information-ModifyList-RL-ReconfPrepTDD				PRESENCE optional }|
	{ ID id-DSCHs-to-Add-TDD									CRITICALITY reject	TYPE DSCH-TDD-Information					PRESENCE optional }|
	{ ID id-DSCH-Information-DeleteList-RL-ReconfPrepTDD		CRITICALITY reject	TYPE DSCH-Information-DeleteList-RL-ReconfPrepTDD				PRESENCE optional }|
	{ ID id-USCH-Information-ModifyList-RL-ReconfPrepTDD		CRITICALITY reject	TYPE USCH-Information-ModifyList-RL-ReconfPrepTDD				PRESENCE optional }|
	{ ID id-USCH-Information-Add								CRITICALITY reject	TYPE USCH-Information					PRESENCE optional }|
	{ ID id-USCH-Information-DeleteList-RL-ReconfPrepTDD		CRITICALITY reject	TYPE USCH-Information-DeleteList-RL-ReconfPrepTDD				PRESENCE optional }|
	{ ID id-RL-Information-RL-ReconfPrepTDD						CRITICALITY reject	TYPE RL-Information-RL-ReconfPrepTDD			PRESENCE optional },
-- This RL Information is the for the 1st RL IE repetition
	...
}

RadioLinkReconfigurationPrepareTDD-Extensions NBAP-PROTOCOL-EXTENSION ::= {
	{ ID	id-SignallingBearerRequestIndicator		CRITICALITY reject	EXTENSION SignallingBearerRequestIndicator				PRESENCE optional }|
	{ ID	id-HSDSCH-TDD-Information				CRITICALITY reject	EXTENSION HSDSCH-TDD-Information				PRESENCE optional	}|
	{ ID	id-HSDSCH-Information-to-Modify			CRITICALITY reject	EXTENSION HSDSCH-Information-to-Modify				PRESENCE optional }|
	{ ID	id-HSDSCH-MACdFlows-to-Add				CRITICALITY reject	EXTENSION HSDSCH-MACdFlows-Information				PRESENCE optional }|
	{ ID	id-HSDSCH-MACdFlows-to-Delete			CRITICALITY reject	EXTENSION HSDSCH-MACdFlows-to-Delete				PRESENCE optional }|
	{ ID	id-HSDSCH-RNTI							CRITICALITY reject	EXTENSION HSDSCH-RNTI					PRESENCE conditional }|
	-- The IE shall be present if HS-PDSCH RL ID IE is present.
	{ ID	id-HSPDSCH-RL-ID						CRITICALITY reject	EXTENSION RL-ID							PRESENCE optional }|
	{ ID	id-PDSCH-RL-ID							CRITICALITY ignore	EXTENSION RL-ID							PRESENCE optional }|
	{ ID	id-multiple-RL-Information-RL-ReconfPrepTDD		CRITICALITY reject	EXTENSION MultipleRL-Information-RL-ReconfPrepTDD		PRESENCE optional	}|
-- This RL Information is the for the 2nd and beyond repetition of RL information,
	{ ID id-E-DCH-Information-Reconfig				CRITICALITY reject	EXTENSION E-DCH-Information-Reconfig				PRESENCE optional }|
	{ ID id-E-DCH-Serving-RL-ID						CRITICALITY reject	EXTENSION RL-ID							PRESENCE optional }|
	{ ID id-E-DCH-768-Information-Reconfig			CRITICALITY reject	EXTENSION E-DCH-768-Information-Reconfig				PRESENCE optional }|
	{ ID id-E-DCH-LCR-Information-Reconfig			CRITICALITY reject	EXTENSION E-DCH-LCR-Information-Reconfig					PRESENCE optional }|
	{ ID id-PowerControlGAP								CRITICALITY ignore	EXTENSION ControlGAP									PRESENCE optional },
	-- Applicable to 1.28Mcps TDD only
	...
}

UL-CCTrCH-InformationAddList-RL-ReconfPrepTDD ::= SEQUENCE (SIZE (1..maxNrOfCCTrCHs)) OF UL-CCTrCH-InformationAddItem-RL-ReconfPrepTDD

UL-CCTrCH-InformationAddItem-RL-ReconfPrepTDD ::= SEQUENCE {
	cCTrCH-ID									CCTrCH-ID,
	tFCS										TFCS,
	tFCI-Coding									TFCI-Coding,
	punctureLimit								PunctureLimit,
	ul-DPCH-InformationList						UL-DPCH-InformationAddList-RL-ReconfPrepTDD	OPTIONAL,
-- This DPCH Information is the for the first RL repetition, DPCH information for RL repetitions 2 and on, should be defined in MultipleRL-UL-DPCH-InformationAddList-RL-ReconfPrepTDD
	iE-Extensions								ProtocolExtensionContainer { { UL-CCTrCH-InformationAddItem-RL-ReconfPrepTDD-ExtIEs} }		OPTIONAL,
	...
}

UL-CCTrCH-InformationAddItem-RL-ReconfPrepTDD-ExtIEs  NBAP-PROTOCOL-EXTENSION ::= {
	{ ID id-UL-DPCH-LCR-InformationAddListIE-RL-ReconfPrepTDD	CRITICALITY reject	EXTENSION UL-DPCH-LCR-InformationAddList-RL-ReconfPrepTDD		PRESENCE optional }|	-- Applicable to 1.28Mcps TDD only
-- This DPCH Information is the for the first RL repetition, DPCH information for RL repetitions 2 and on, should be defined in MultipleRL-UL-DPCH-InformationAddList-RL-ReconfPrepTDD
	{ ID id-UL-SIRTarget										CRITICALITY reject	EXTENSION UL-SIR	PRESENCE optional }|
	-- Mandatory for 1.28Mcps TDD, Not Applicable to 3.84Mcps TDD or 7.68Mcps TDD.
-- This Information is the for the first RL repetition, SIR Target information for RL repetitions 2 and on, should be defined in MultipleRL-UL-DPCH-InformationAddList-RL-ReconfPrepTDD
	{ ID id-TDD-TPC-UplinkStepSize-InformationAdd-LCR-RL-ReconfPrepTDD	CRITICALITY reject	EXTENSION TDD-TPC-UplinkStepSize-LCR	PRESENCE optional	}|
-- This Information is the for the first RL repetition, TPCinformation for RL repetitions 2 and on, should be defined in MultipleRL-UL-DPCH-InformationAddList-RL-ReconfPrepTDD
	-- Mandatory for 1.28Mcps TDD, Not Applicable to 3.84Mcps TDD or 7.68Mcps TDD.
	{ ID id-RL-ID												CRITICALITY ignore	EXTENSION RL-ID	PRESENCE optional }|
-- This is the RL ID for the first RL repetition
	{ ID id-multipleRL-ul-DPCH-InformationList					CRITICALITY reject	EXTENSION MultipleRL-UL-DPCH-InformationAddList-RL-ReconfPrepTDD	PRESENCE optional }|
-- This Information is the for the 2nd and beyond RL repetition,
	{ ID id-UL-DPCH-768-InformationAddItemIE-RL-ReconfPrepTDD	CRITICALITY reject	EXTENSION UL-DPCH-768-InformationAddList-RL-ReconfPrepTDD		PRESENCE optional },	-- Applicable to 7.68Mcps TDD only, first radio link
	...
}

UL-DPCH-InformationAddList-RL-ReconfPrepTDD ::= ProtocolIE-Single-Container {{ UL-DPCH-InformationAddListIEs-RL-ReconfPrepTDD }}

UL-DPCH-InformationAddListIEs-RL-ReconfPrepTDD NBAP-PROTOCOL-IES ::= {
	{ ID id-UL-DPCH-InformationAddListIE-RL-ReconfPrepTDD   CRITICALITY reject		TYPE UL-DPCH-InformationAddItem-RL-ReconfPrepTDD		PRESENCE mandatory }
}

UL-DPCH-InformationAddItem-RL-ReconfPrepTDD ::= SEQUENCE {
	repetitionPeriod						RepetitionPeriod,
	repetitionLength						RepetitionLength,
	tdd-DPCHOffset							TDD-DPCHOffset,
	uL-Timeslot-Information					UL-Timeslot-Information,
	iE-Extensions							ProtocolExtensionContainer { { UL-DPCH-InformationAddItem-RL-ReconfPrepTDD-ExtIEs} }		OPTIONAL,
	...
}

UL-DPCH-InformationAddItem-RL-ReconfPrepTDD-ExtIEs  NBAP-PROTOCOL-EXTENSION ::= {
	...
}

UL-DPCH-LCR-InformationAddList-RL-ReconfPrepTDD ::= SEQUENCE {
	repetitionPeriod						RepetitionPeriod,
	repetitionLength						RepetitionLength,
	tdd-DPCHOffset							TDD-DPCHOffset,
	uL-Timeslot-InformationLCR				UL-TimeslotLCR-Information,
	iE-Extensions							ProtocolExtensionContainer { { UL-DPCH-LCR-InformationAddItem-RL-ReconfPrepTDD-ExtIEs} }		OPTIONAL,
	...
}

UL-DPCH-LCR-InformationAddItem-RL-ReconfPrepTDD-ExtIEs  NBAP-PROTOCOL-EXTENSION ::= {
	...
}

MultipleRL-UL-DPCH-InformationAddList-RL-ReconfPrepTDD ::= SEQUENCE (SIZE (1..maxNrOfRLs-1)) OF MultipleRL-UL-DPCH-InformationAddListIE-RL-ReconfPrepTDD
--Includes the 2nd through the max number of radio link repetitions.

MultipleRL-UL-DPCH-InformationAddListIE-RL-ReconfPrepTDD ::= SEQUENCE {
	ul-DPCH-InformationList						UL-DPCH-InformationAddList-RL-ReconfPrepTDD		OPTIONAL,
	ul-DPCH-InformationListLCR					UL-DPCH-LCR-InformationAddList-RL-ReconfPrepTDD	OPTIONAL,
	ul-sir-target								UL-SIR											OPTIONAL,
	-- Mandatory for 1.28Mcps TDD, Not Applicable to 3.84Mcps TDD or 7.68Mcps TDD.
	tDD-TPC-UplinkStepSize-LCR 					TDD-TPC-UplinkStepSize-LCR						OPTIONAL,
	-- Mandatory for 1.28Mcps TDD, Not Applicable to 3.84Mcps TDD or 7.68Mcps TDD.
	rL-ID										RL-ID											OPTIONAL,
	iE-Extensions								ProtocolExtensionContainer { { MultipleRL-UL-DPCH-InformationAddListIE-RL-ReconfPrepTDD-ExtIEs} }		OPTIONAL,
	...
}

MultipleRL-UL-DPCH-InformationAddListIE-RL-ReconfPrepTDD-ExtIEs  NBAP-PROTOCOL-EXTENSION ::= {
	{ ID id-UL-DPCH-768-InformationAddListIE-RL-ReconfPrepTDD	CRITICALITY reject	EXTENSION	UL-DPCH-768-InformationAddList-RL-ReconfPrepTDD	PRESENCE optional },
	...
}

UL-DPCH-768-InformationAddList-RL-ReconfPrepTDD ::= SEQUENCE {
	repetitionPeriod						RepetitionPeriod,
	repetitionLength						RepetitionLength,
	tdd-DPCHOffset							TDD-DPCHOffset,
	uL-Timeslot-Information768				UL-Timeslot768-Information,
	iE-Extensions							ProtocolExtensionContainer { { UL-DPCH-768-InformationAddItem-RL-ReconfPrepTDD-ExtIEs} }		OPTIONAL,
	...
}

UL-DPCH-768-InformationAddItem-RL-ReconfPrepTDD-ExtIEs  NBAP-PROTOCOL-EXTENSION ::= {
	...
}

UL-CCTrCH-InformationModifyList-RL-ReconfPrepTDD ::= SEQUENCE (SIZE (1..maxNrOfCCTrCHs)) OF UL-CCTrCH-InformationModifyItem-RL-ReconfPrepTDD

UL-CCTrCH-InformationModifyItem-RL-ReconfPrepTDD ::= SEQUENCE {
	cCTrCH-ID									CCTrCH-ID,
	tFCS										TFCS												OPTIONAL,
	tFCI-Coding									TFCI-Coding											OPTIONAL,
	punctureLimit								PunctureLimit 										OPTIONAL,
	ul-DPCH-InformationAddList					UL-DPCH-InformationModify-AddList-RL-ReconfPrepTDD	OPTIONAL,
-- This DPCH Information is the for the first RL repetition, DPCH information for RL repetitions 2 and on, should be defined in MultipleRL-UL-DPCH-InformationModifyList-RL-ReconfPrepTDD
	ul-DPCH-InformationModifyList				UL-DPCH-InformationModify-ModifyList-RL-ReconfPrepTDD	OPTIONAL,
-- This DPCH Information is the for the first RL repetition, DPCH information for RL repetitions 2 and on, should be defined in MultipleRL-UL-DPCH-InformationModifyList-RL-ReconfPrepTDD
	ul-DPCH-InformationDeleteList				UL-DPCH-InformationModify-DeleteList-RL-ReconfPrepTDD	OPTIONAL,
-- This DPCH Information is the for the first RL repetition, DPCH information for RL repetitions 2 and on, should be defined in MultipleRL-UL-DPCH-InformationModifyList-RL-ReconfPrepTDD
	iE-Extensions								ProtocolExtensionContainer { { UL-CCTrCH-InformationModifyItem-RL-ReconfPrepTDD-ExtIEs} }		OPTIONAL,
	...
}

UL-CCTrCH-InformationModifyItem-RL-ReconfPrepTDD-ExtIEs  NBAP-PROTOCOL-EXTENSION ::= {
	{ ID id-UL-DPCH-LCR-InformationModify-AddList	 CRITICALITY reject		EXTENSION	 UL-DPCH-LCR-InformationModify-AddList-RL-ReconfPrepTDD		PRESENCE optional }|	-- Applicable to 1.28Mcps TDD only
-- This DPCH Information is the for the first RL repetition, DPCH information for RL repetitions 2 and on, should be defined in MultipleRL-UL-DPCH-InformationModifyList-RL-ReconfPrepTDD
	{ ID id-UL-SIRTarget		CRITICALITY reject		EXTENSION		UL-SIR		PRESENCE optional	}|
	-- Applicable to 1.28Mcps TDD only.
-- This Information is the for the first RL repetition, SIR Target information for RL repetitions 2 and on, should be defined in MultipleRL-UL-DPCH-InformationModifyList-RL-ReconfPrepTDD
	{ ID id-TDD-TPC-UplinkStepSize-InformationModify-LCR-RL-ReconfPrepTDD		CRITICALITY reject		EXTENSION	TDD-TPC-UplinkStepSize-LCR	PRESENCE optional	}|
	-- Applicable to 1.28Mcps TDD only
-- This Information is the for the first RL repetition, Step Size information for RL repetitions 2 and on, should be defined in MultipleRL-UL-DPCH-InformationModifyList-RL-ReconfPrepTDD
	{ ID id-RL-ID										CRITICALITY ignore		EXTENSION		RL-ID		PRESENCE optional	}|
-- This is the RL ID for the first RL repetition
	{ ID id-multipleRL-ul-DPCH-InformationModifyList	CRITICALITY reject		EXTENSION		MultipleRL-UL-DPCH-InformationModifyList-RL-ReconfPrepTDD	PRESENCE optional	}|
-- This DPCH Information is the for the 2nd and beyond RL repetition,
	{ ID id-UL-DPCH-768-InformationModify-AddItem	 CRITICALITY reject		EXTENSION	 UL-DPCH-768-InformationModify-AddList-RL-ReconfPrepTDD		PRESENCE optional },	-- Applicable to 7.68Mcps TDD only
-- This DPCH Information is the for the first RL repetition, DPCH information for RL repetitions 2 and on, should be defined in MultipleRL-UL-DPCH-InformationModifyList-RL-ReconfPrepTDD
	...
}

UL-DPCH-InformationModify-AddList-RL-ReconfPrepTDD ::= ProtocolIE-Single-Container {{ UL-DPCH-InformationModify-AddListIEs-RL-ReconfPrepTDD }}

UL-DPCH-InformationModify-AddListIEs-RL-ReconfPrepTDD NBAP-PROTOCOL-IES ::= {
	{ ID id-UL-DPCH-InformationModify-AddListIE-RL-ReconfPrepTDD   CRITICALITY reject		TYPE UL-DPCH-InformationModify-AddItem-RL-ReconfPrepTDD		PRESENCE mandatory }
}

UL-DPCH-InformationModify-AddItem-RL-ReconfPrepTDD ::= SEQUENCE {
	repetitionPeriod						RepetitionPeriod,
	repetitionLength						RepetitionLength,
	tdd-DPCHOffset							TDD-DPCHOffset,
	uL-Timeslot-Information					UL-Timeslot-Information,
	iE-Extensions							ProtocolExtensionContainer { { UL-DPCH-InformationModify-AddItem-RL-ReconfPrepTDD-ExtIEs} }		OPTIONAL,
	...
}

UL-DPCH-InformationModify-AddItem-RL-ReconfPrepTDD-ExtIEs  NBAP-PROTOCOL-EXTENSION ::= {
	...
}

UL-DPCH-InformationModify-ModifyList-RL-ReconfPrepTDD ::= ProtocolIE-Single-Container {{ UL-DPCH-InformationModify-ModifyListIEs-RL-ReconfPrepTDD }}

UL-DPCH-InformationModify-ModifyListIEs-RL-ReconfPrepTDD NBAP-PROTOCOL-IES ::= {
	{ ID id-UL-DPCH-InformationModify-ModifyListIE-RL-ReconfPrepTDD   CRITICALITY reject		TYPE UL-DPCH-InformationModify-ModifyItem-RL-ReconfPrepTDD		PRESENCE mandatory }
}

UL-DPCH-InformationModify-ModifyItem-RL-ReconfPrepTDD ::= SEQUENCE {
	repetitionPeriod						RepetitionPeriod	OPTIONAL,
	repetitionLength						RepetitionLength	OPTIONAL,
	tdd-DPCHOffset							TDD-DPCHOffset		OPTIONAL,
	uL-Timeslot-InformationModify-ModifyList-RL-ReconfPrepTDD				UL-Timeslot-InformationModify-ModifyList-RL-ReconfPrepTDD			OPTIONAL,
	iE-Extensions							ProtocolExtensionContainer { { UL-DPCH-InformationModify-ModifyItem-RL-ReconfPrepTDD-ExtIEs} }		OPTIONAL,
	...
}

UL-DPCH-InformationModify-ModifyItem-RL-ReconfPrepTDD-ExtIEs  NBAP-PROTOCOL-EXTENSION ::= {
	{ ID id-UL-TimeslotLCR-Information-RL-ReconfPrepTDD   	CRITICALITY reject		EXTENSION 	UL-TimeslotLCR-InformationModify-ModifyList-RL-ReconfPrepTDD		PRESENCE optional }|	-- Applicable to 1.28Mcps TDD only
	{ ID id-UL-Timeslot768-Information-RL-ReconfPrepTDD   	CRITICALITY reject		EXTENSION 	UL-Timeslot768-InformationModify-ModifyList-RL-ReconfPrepTDD		PRESENCE optional },	-- Applicable to 7.68Mcps TDD only
	...
}

UL-Timeslot-InformationModify-ModifyList-RL-ReconfPrepTDD ::= SEQUENCE (SIZE (1..maxNrOfULTSs)) OF UL-Timeslot-InformationModify-ModifyItem-RL-ReconfPrepTDD	-- Applicable to 3.84Mcps TDD only

UL-Timeslot-InformationModify-ModifyItem-RL-ReconfPrepTDD ::= SEQUENCE {
	timeSlot								TimeSlot,
	midambleShiftAndBurstType				MidambleShiftAndBurstType		OPTIONAL,
	tFCI-Presence							TFCI-Presence					OPTIONAL,
	uL-Code-InformationModify-ModifyList-RL-ReconfPrepTDD				UL-Code-InformationModify-ModifyList-RL-ReconfPrepTDD		OPTIONAL,
	iE-Extensions							ProtocolExtensionContainer { { UL-Timeslot-InformationModify-ModifyItem-RL-ReconfPrepTDD-ExtIEs} }		OPTIONAL,
	...
}

UL-Timeslot-InformationModify-ModifyItem-RL-ReconfPrepTDD-ExtIEs NBAP-PROTOCOL-EXTENSION ::= {
	...
}

UL-Code-InformationModify-ModifyList-RL-ReconfPrepTDD ::= SEQUENCE (SIZE (1..maxNrOfDPCHs)) OF UL-Code-InformationModify-ModifyItem-RL-ReconfPrepTDD

UL-Code-InformationModify-ModifyItem-RL-ReconfPrepTDD ::= SEQUENCE {
	dPCH-ID									DPCH-ID,
	tdd-ChannelisationCode					TDD-ChannelisationCode		OPTIONAL,
	iE-Extensions							ProtocolExtensionContainer { { UL-Code-InformationModify-ModifyItem-RL-ReconfPrepTDD-ExtIEs} }		OPTIONAL,
	...
}

UL-Code-InformationModify-ModifyItem-RL-ReconfPrepTDD-ExtIEs NBAP-PROTOCOL-EXTENSION ::= {
	...
}

UL-TimeslotLCR-InformationModify-ModifyList-RL-ReconfPrepTDD ::= SEQUENCE (SIZE (1..maxNrOfULTSLCRs)) OF UL-Timeslot-LCR-InformationModify-ModifyItem-RL-ReconfPrepTDD	-- Applicable to 1.28Mcps TDD only

UL-Timeslot-LCR-InformationModify-ModifyItem-RL-ReconfPrepTDD ::= SEQUENCE {
	timeSlotLCR								TimeSlotLCR,
	midambleShiftLCR						MidambleShiftLCR	OPTIONAL,
	tFCI-Presence							TFCI-Presence		OPTIONAL,
	uL-Code-InformationModify-ModifyList-RL-ReconfPrepTDDLCR				UL-Code-InformationModify-ModifyList-RL-ReconfPrepTDDLCR		OPTIONAL,
	iE-Extensions							ProtocolExtensionContainer { { UL-Timeslot-LCR-InformationModify-ModifyItem-RL-ReconfPrepTDD-ExtIEs} }		OPTIONAL,
	...
}

UL-Timeslot-LCR-InformationModify-ModifyItem-RL-ReconfPrepTDD-ExtIEs NBAP-PROTOCOL-EXTENSION ::= {
	{ ID id-PLCCH-Information-RL-ReconfPrepTDDLCR	CRITICALITY reject		EXTENSION PLCCHinformation	PRESENCE optional },
	...
}

UL-Code-InformationModify-ModifyList-RL-ReconfPrepTDDLCR ::= SEQUENCE (SIZE (1..maxNrOfDPCHLCRs)) OF UL-Code-InformationModify-ModifyItem-RL-ReconfPrepTDDLCR

UL-Code-InformationModify-ModifyItem-RL-ReconfPrepTDDLCR ::= SEQUENCE {
	dPCH-ID									DPCH-ID,
	tdd-ChannelisationCodeLCR				TDD-ChannelisationCodeLCR		OPTIONAL,
	iE-Extensions							ProtocolExtensionContainer { { UL-Code-InformationModify-ModifyItem-RL-ReconfPrepTDDLCR-ExtIEs} }		OPTIONAL,
	...
}

UL-Code-InformationModify-ModifyItem-RL-ReconfPrepTDDLCR-ExtIEs NBAP-PROTOCOL-EXTENSION ::= {
{ ID id-UL-DPCH-TimeSlotFormat-LCR-ModifyItem-RL-ReconfPrepTDD  CRITICALITY	reject	 EXTENSION TDD-UL-DPCH-TimeSlotFormat-LCR   PRESENCE  optional},

	...
}

UL-Timeslot768-InformationModify-ModifyList-RL-ReconfPrepTDD ::= SEQUENCE (SIZE (1..maxNrOfULTSs)) OF UL-Timeslot-768-InformationModify-ModifyItem-RL-ReconfPrepTDD	-- Applicable to 7.68Mcps TDD only

UL-Timeslot-768-InformationModify-ModifyItem-RL-ReconfPrepTDD ::= SEQUENCE {
	timeSlot								TimeSlot,
	midambleShiftAndBurstType768			MidambleShiftAndBurstType768	OPTIONAL,
	tFCI-Presence							TFCI-Presence					OPTIONAL,
	uL-Code-InformationModify-ModifyList-RL-ReconfPrepTDD768				UL-Code-InformationModify-ModifyList-RL-ReconfPrepTDD768		OPTIONAL,
	iE-Extensions							ProtocolExtensionContainer { { UL-Timeslot-768-InformationModify-ModifyItem-RL-ReconfPrepTDD-ExtIEs} }		OPTIONAL,
	...
}

UL-Timeslot-768-InformationModify-ModifyItem-RL-ReconfPrepTDD-ExtIEs NBAP-PROTOCOL-EXTENSION ::= {
	...
}

UL-Code-InformationModify-ModifyList-RL-ReconfPrepTDD768 ::= SEQUENCE (SIZE (1..maxNrOfDPCHs)) OF UL-Code-InformationModify-ModifyItem-RL-ReconfPrepTDD768

UL-Code-InformationModify-ModifyItem-RL-ReconfPrepTDD768 ::= SEQUENCE {
	dPCH-ID									DPCH-ID,
	tdd-ChannelisationCode768				TDD-ChannelisationCode768		OPTIONAL,
	iE-Extensions							ProtocolExtensionContainer { { UL-Code-InformationModify-ModifyItem-RL-ReconfPrepTDD768-ExtIEs} }		OPTIONAL,
	...
}

UL-Code-InformationModify-ModifyItem-RL-ReconfPrepTDD768-ExtIEs NBAP-PROTOCOL-EXTENSION ::= {
	...
}

UL-DPCH-InformationModify-DeleteList-RL-ReconfPrepTDD ::= ProtocolIE-Single-Container {{ UL-DPCH-InformationModify-DeleteListIEs-RL-ReconfPrepTDD }}

UL-DPCH-InformationModify-DeleteListIEs-RL-ReconfPrepTDD NBAP-PROTOCOL-IES ::= {
	{ ID id-UL-DPCH-InformationModify-DeleteListIE-RL-ReconfPrepTDD   CRITICALITY reject		TYPE UL-DPCH-InformationModify-DeleteListIE-RL-ReconfPrepTDD		PRESENCE mandatory }
}

UL-DPCH-InformationModify-DeleteListIE-RL-ReconfPrepTDD ::= SEQUENCE (SIZE (1..maxNrOfDPCHs)) OF UL-DPCH-InformationModify-DeleteItem-RL-ReconfPrepTDD

UL-DPCH-InformationModify-DeleteItem-RL-ReconfPrepTDD ::= SEQUENCE {
	dPCH-ID								DPCH-ID,
	iE-Extensions						ProtocolExtensionContainer { { UL-DPCH-InformationModify-DeleteItem-RL-ReconfPrepTDD-ExtIEs} }		OPTIONAL,
	...
}

UL-DPCH-InformationModify-DeleteItem-RL-ReconfPrepTDD-ExtIEs  NBAP-PROTOCOL-EXTENSION ::= {
	...
}

UL-DPCH-LCR-InformationModify-AddList-RL-ReconfPrepTDD ::= SEQUENCE {
	repetitionPeriod						RepetitionPeriod,
	repetitionLength						RepetitionLength,
	tdd-DPCHOffset							TDD-DPCHOffset,
	uL-Timeslot-InformationLCR				UL-TimeslotLCR-Information,
	iE-Extensions							ProtocolExtensionContainer { { UL-DPCH-LCR-InformationModify-AddItem-RL-ReconfPrepTDD-ExtIEs} }		OPTIONAL,
	...
}

UL-DPCH-LCR-InformationModify-AddItem-RL-ReconfPrepTDD-ExtIEs  NBAP-PROTOCOL-EXTENSION ::= {
	...
}

MultipleRL-UL-DPCH-InformationModifyList-RL-ReconfPrepTDD ::= SEQUENCE (SIZE (1..maxNrOfRLs-1)) OF MultipleRL-UL-DPCH-InformationModifyListIE-RL-ReconfPrepTDD
--Includes the 2nd through the max number of radio link information repetitions.

MultipleRL-UL-DPCH-InformationModifyListIE-RL-ReconfPrepTDD ::= SEQUENCE {
	ul-DPCH-InformationAddList					UL-DPCH-InformationModify-AddList-RL-ReconfPrepTDD	OPTIONAL,
	ul-DPCH-InformationModifyList				UL-DPCH-InformationModify-ModifyList-RL-ReconfPrepTDD	OPTIONAL,
	ul-DPCH-InformationDeleteList				UL-DPCH-InformationModify-DeleteList-RL-ReconfPrepTDD	OPTIONAL,
	ul-DPCH-InformationAddListLCR				UL-DPCH-LCR-InformationModify-AddList-RL-ReconfPrepTDD	OPTIONAL,
	ul-sir-target								UL-SIR												OPTIONAL,
	tDD-TPC-UplinkStepSize-LCR					TDD-TPC-UplinkStepSize-LCR							OPTIONAL,
	rL-ID										RL-ID												OPTIONAL,
	-- This DPCH Information is the for the 2nd and beyond RL repetitions, 
	iE-Extensions								ProtocolExtensionContainer { { MultipleRL-UL-DPCH-InformationModifyListIE-RL-ReconfPrepTDD-ExtIEs} }		OPTIONAL,
...
}

MultipleRL-UL-DPCH-InformationModifyListIE-RL-ReconfPrepTDD-ExtIEs  NBAP-PROTOCOL-EXTENSION ::= {
	{ ID id-UL-DPCH-768-InformationModify-AddList	 CRITICALITY reject		EXTENSION UL-DPCH-768-InformationModify-AddList-RL-ReconfPrepTDD		PRESENCE optional },	-- Applicable to 7.68Mcps TDD only
	...
}

UL-DPCH-768-InformationModify-AddList-RL-ReconfPrepTDD ::= SEQUENCE {
	repetitionPeriod						RepetitionPeriod,
	repetitionLength						RepetitionLength,
	tdd-DPCHOffset							TDD-DPCHOffset,
	uL-Timeslot-Information768				UL-Timeslot768-Information,
	iE-Extensions							ProtocolExtensionContainer { { UL-DPCH-768-InformationModify-AddItem-RL-ReconfPrepTDD-ExtIEs} }		OPTIONAL,
	...
}

UL-DPCH-768-InformationModify-AddItem-RL-ReconfPrepTDD-ExtIEs  NBAP-PROTOCOL-EXTENSION ::= {
	...
}

UL-CCTrCH-InformationDeleteList-RL-ReconfPrepTDD ::= SEQUENCE (SIZE (1..maxNrOfCCTrCHs)) OF UL-CCTrCH-InformationDeleteItem-RL-ReconfPrepTDD

UL-CCTrCH-InformationDeleteItem-RL-ReconfPrepTDD ::= SEQUENCE {
	cCTrCH-ID									CCTrCH-ID,
	iE-Extensions								ProtocolExtensionContainer { { UL-CCTrCH-InformationDeleteItem-RL-ReconfPrepTDD-ExtIEs} }		OPTIONAL,
	...
}

UL-CCTrCH-InformationDeleteItem-RL-ReconfPrepTDD-ExtIEs  NBAP-PROTOCOL-EXTENSION ::= {
	...
}

DL-CCTrCH-InformationAddList-RL-ReconfPrepTDD ::= SEQUENCE (SIZE (1..maxNrOfCCTrCHs)) OF DL-CCTrCH-InformationAddItem-RL-ReconfPrepTDD

DL-CCTrCH-InformationAddItem-RL-ReconfPrepTDD ::= SEQUENCE {
	cCTrCH-ID										CCTrCH-ID,
	tFCS											TFCS,
	tFCI-Coding										TFCI-Coding,
	punctureLimit									PunctureLimit,
	cCTrCH-TPCList									CCTrCH-TPCAddList-RL-ReconfPrepTDD				OPTIONAL,
	dl-DPCH-InformationList							DL-DPCH-InformationAddList-RL-ReconfPrepTDD 	OPTIONAL,
-- This DPCH Information is the for the first RL repetition, DPCH information for RL repetitions 2 and on, should be defined in MultipleRL-DL-DPCH-InformationAddList-RL-ReconfPrepTDD
	iE-Extensions									ProtocolExtensionContainer { { DL-CCTrCH-InformationAddItem-RL-ReconfPrepTDD-ExtIEs} }			OPTIONAL,
	...
}

DL-CCTrCH-InformationAddItem-RL-ReconfPrepTDD-ExtIEs  NBAP-PROTOCOL-EXTENSION ::= {
	{ ID id-DL-DPCH-LCR-InformationAddList-RL-ReconfPrepTDD				CRITICALITY reject	EXTENSION DL-DPCH-LCR-InformationAddList-RL-ReconfPrepTDD		PRESENCE optional }|	-- Applicable to 1.28Mcps TDD only
-- This DPCH Information is the for the first RL repetition, DPCH information for RL repetitions 2 and on, should be defined in MultipleRL-DL-DPCH-InformationAddList-RL-ReconfPrepTDD
	{ ID id-CCTrCH-Initial-DL-Power-RL-ReconfPrepTDD					CRITICALITY ignore	EXTENSION DL-Power	PRESENCE optional	}|
-- This DL Power information is the for the first RL repetition, DL power information for RL repetitions 2 and on, should be defined in MultipleRL-DL-DPCH-InformationAddList-RL-ReconfPrepTDD
	{ ID id-TDD-TPC-DownlinkStepSize-InformationAdd-RL-ReconfPrepTDD	CRITICALITY reject	EXTENSION  TDD-TPC-DownlinkStepSize	 PRESENCE optional}|
-- This DL step size is the for the first RL repetition, DL step size information for RL repetitions 2 and on, should be defined in MultipleRL-DL-DPCH-InformationAddList-RL-ReconfPrepTDD
	{ ID id-CCTrCH-Maximum-DL-Power-InformationAdd-RL-ReconfPrepTDD		CRITICALITY ignore	EXTENSION DL-Power	PRESENCE optional	}|
-- This DL Power information is the for the first RL repetition, DL power information for RL repetitions 2 and on, should be defined in MultipleRL-DL-DPCH-InformationAddList-RL-ReconfPrepTDD
	{ ID id-CCTrCH-Minimum-DL-Power-InformationAdd-RL-ReconfPrepTDD		CRITICALITY ignore	EXTENSION DL-Power	PRESENCE optional	}|
-- This DL Power information is the for the first RL repetition, DL power information for RL repetitions 2 and on, should be defined in MultipleRL-DL-DPCH-InformationAddList-RL-ReconfPrepTDD
	{ ID id-RL-ID														CRITICALITY ignore	EXTENSION RL-ID	PRESENCE optional	}|
-- This is the RL ID for the first RL repetition
	{ ID id-multipleRL-dl-DPCH-InformationList							CRITICALITY reject	EXTENSION MultipleRL-DL-DPCH-InformationAddList-RL-ReconfPrepTDD	PRESENCE optional	}|
-- This DPCH Information is the for the 2nd and beyond RL repetition,
	{ ID id-DL-DPCH-768-InformationAddItem-RL-ReconfPrepTDD				CRITICALITY reject	EXTENSION DL-DPCH-768-InformationAddList-RL-ReconfPrepTDD		PRESENCE optional },	-- Applicable to 7.68Mcps TDD only
	...
}

CCTrCH-TPCAddList-RL-ReconfPrepTDD ::= SEQUENCE (SIZE (1..maxNrOfCCTrCHs)) OF CCTrCH-TPCAddItem-RL-ReconfPrepTDD		-- Applicable to 3.84Mcps TDD and 7.68Mcps TDD only

CCTrCH-TPCAddItem-RL-ReconfPrepTDD	 ::= SEQUENCE {
	cCTrCH-ID								CCTrCH-ID,
	iE-Extensions							ProtocolExtensionContainer { { CCTrCH-TPCAddItem-RL-ReconfPrepTDD-ExtIEs} }		OPTIONAL,
	...
}

CCTrCH-TPCAddItem-RL-ReconfPrepTDD-ExtIEs  NBAP-PROTOCOL-EXTENSION ::= {
	...
}

DL-DPCH-InformationAddList-RL-ReconfPrepTDD ::= ProtocolIE-Single-Container {{ DL-DPCH-InformationAddListIEs-RL-ReconfPrepTDD }}

DL-DPCH-InformationAddListIEs-RL-ReconfPrepTDD NBAP-PROTOCOL-IES ::= {
	{ ID id-DL-DPCH-InformationAddListIE-RL-ReconfPrepTDD   CRITICALITY reject		TYPE DL-DPCH-InformationAddItem-RL-ReconfPrepTDD		PRESENCE mandatory }
}

DL-DPCH-InformationAddItem-RL-ReconfPrepTDD ::= SEQUENCE {
	repetitionPeriod						RepetitionPeriod,
	repetitionLength						RepetitionLength,
	tdd-DPCHOffset							TDD-DPCHOffset,
	dL-Timeslot-Information					DL-Timeslot-Information,
	iE-Extensions							ProtocolExtensionContainer { { DL-DPCH-InformationAddItem-RL-ReconfPrepTDD-ExtIEs} }		OPTIONAL,
	...
}

DL-DPCH-InformationAddItem-RL-ReconfPrepTDD-ExtIEs  NBAP-PROTOCOL-EXTENSION ::= {
	...
}

DL-DPCH-LCR-InformationAddList-RL-ReconfPrepTDD ::= SEQUENCE {
	repetitionPeriod						RepetitionPeriod,
	repetitionLength						RepetitionLength,
	tdd-DPCHOffset							TDD-DPCHOffset,
	dL-Timeslot-InformationLCR				DL-TimeslotLCR-Information,
	iE-Extensions							ProtocolExtensionContainer { { DL-DPCH-LCR-InformationAddItem-RL-ReconfPrepTDD-ExtIEs} }		OPTIONAL,
	...
}

DL-DPCH-LCR-InformationAddItem-RL-ReconfPrepTDD-ExtIEs  NBAP-PROTOCOL-EXTENSION ::= {
	...
}

MultipleRL-DL-DPCH-InformationAddList-RL-ReconfPrepTDD ::= SEQUENCE (SIZE (1..maxNrOfRLs-1)) OF MultipleRL-DL-DPCH-InformationAddListIE-RL-ReconfPrepTDD
	--Includes the 2nd through the max number of radio link information repetitions.

MultipleRL-DL-DPCH-InformationAddListIE-RL-ReconfPrepTDD ::= SEQUENCE {
	dl-DPCH-InformationList										DL-DPCH-InformationAddList-RL-ReconfPrepTDD	OPTIONAL,
	dl-DPCH-InformationListLCR									DL-DPCH-LCR-InformationAddList-RL-ReconfPrepTDD	OPTIONAL,
	cCTrCH-Initial-DL-Power										DL-Power							OPTIONAL,
	tDD-TPC-DownlinkStepSize									TDD-TPC-DownlinkStepSize			OPTIONAL,
	cCTrCH-Maximum-DL-Power-InformationAdd-RL-ReconfPrepTDD		DL-Power							OPTIONAL,
	cCTrCH-Minimum-DL-Power-InformationAdd-RL-ReconfPrepTDD		DL-Power							OPTIONAL,
	rL-ID														RL-ID								OPTIONAL,
	iE-Extensions					ProtocolExtensionContainer { { MultipleRL-DL-DPCH-InformationAddListIE-RL-ReconfPrepTDD-ExtIEs} }		OPTIONAL,
	...
}

MultipleRL-DL-DPCH-InformationAddListIE-RL-ReconfPrepTDD-ExtIEs  NBAP-PROTOCOL-EXTENSION ::= {
	{ ID id-DL-DPCH-768-InformationAddList-RL-ReconfPrepTDD		CRITICALITY reject	EXTENSION DL-DPCH-768-InformationAddList-RL-ReconfPrepTDD		PRESENCE optional },	-- Applicable to 7.68Mcps TDD only
	...
}

DL-DPCH-768-InformationAddList-RL-ReconfPrepTDD ::= SEQUENCE {
	repetitionPeriod						RepetitionPeriod,
	repetitionLength						RepetitionLength,
	tdd-DPCHOffset							TDD-DPCHOffset,
	dL-Timeslot-Information768				DL-Timeslot768-Information,
	iE-Extensions							ProtocolExtensionContainer { { DL-DPCH-768-InformationAddItem-RL-ReconfPrepTDD-ExtIEs} }		OPTIONAL,
	...
}

DL-DPCH-768-InformationAddItem-RL-ReconfPrepTDD-ExtIEs  NBAP-PROTOCOL-EXTENSION ::= {
	...
}

DL-CCTrCH-InformationModifyList-RL-ReconfPrepTDD ::= SEQUENCE (SIZE (1..maxNrOfCCTrCHs)) OF DL-CCTrCH-InformationModifyItem-RL-ReconfPrepTDD

DL-CCTrCH-InformationModifyItem-RL-ReconfPrepTDD ::= SEQUENCE {
	cCTrCH-ID										CCTrCH-ID,
	tFCS											TFCS											OPTIONAL,
	tFCI-Coding										TFCI-Coding										OPTIONAL,
	punctureLimit									PunctureLimit 									OPTIONAL,
	cCTrCH-TPCList									CCTrCH-TPCModifyList-RL-ReconfPrepTDD			OPTIONAL,
	dl-DPCH-InformationAddList						DL-DPCH-InformationModify-AddList-RL-ReconfPrepTDD 	OPTIONAL,
-- This DPCH Information is the for the first RL repetition, DPCH information for RL repetitions 2 and on, should be defined in MultipleRL-DL-DPCH-InformationModifyList-RL-ReconfPrepTDD
	dl-DPCH-InformationModifyList					DL-DPCH-InformationModify-ModifyList-RL-ReconfPrepTDD 	OPTIONAL,
-- This DPCH Information is the for the first RL repetition, DPCH information for RL repetitions 2 and on, should be defined in MultipleRL-DL-DPCH-InformationModifyList-RL-ReconfPrepTDD
	dl-DPCH-InformationDeleteList					DL-DPCH-InformationModify-DeleteList-RL-ReconfPrepTDD 	OPTIONAL,
-- This DPCH Information is the for the first RL repetition, DPCH information for RL repetitions 2 and on, should be defined in MultipleRL-DL-DPCH-InformationModifyList-RL-ReconfPrepTDD
	iE-Extensions									ProtocolExtensionContainer { { DL-CCTrCH-InformationModifyItem-RL-ReconfPrepTDD-ExtIEs} }			OPTIONAL,
	...
}

DL-CCTrCH-InformationModifyItem-RL-ReconfPrepTDD-ExtIEs  NBAP-PROTOCOL-EXTENSION ::= {
	{ ID id-DL-DPCH-LCR-InformationModify-AddList-RL-ReconfPrepTDD CRITICALITY reject		EXTENSION 	DL-DPCH-LCR-InformationModify-AddList-RL-ReconfPrepTDD		PRESENCE optional }|  -- Applicable to 1.28Mcps TDD only
-- This DPCH Information is the for the first RL repetition, DPCH information for RL repetitions 2 and on, should be defined in MultipleRL-DL-DPCH-InformationModifyList-RL-ReconfPrepTDD
	{ ID id-TDD-TPC-DownlinkStepSize-InformationModify-RL-ReconfPrepTDD	CRITICALITY reject	EXTENSION TDD-TPC-DownlinkStepSize	PRESENCE optional}|
-- This Step Size Information is the for the first RL repetition, step size information for RL repetitions 2 and on, should be defined in MultipleRL-DL-DPCH-InformationModifyList-RL-ReconfPrepTDD
	{ ID id-CCTrCH-Maximum-DL-Power-InformationModify-RL-ReconfPrepTDD		CRITICALITY ignore	EXTENSION DL-Power		PRESENCE optional	}|
-- This power Information is the for the first RL repetition, power information for RL repetitions 2 and on, should be defined in MultipleRL-DL-DPCH-InformationModifyList-RL-ReconfPrepTDD
	{ ID id-CCTrCH-Minimum-DL-Power-InformationModify-RL-ReconfPrepTDD		CRITICALITY ignore	EXTENSION DL-Power		PRESENCE optional	}|
-- This power Information is the for the first RL repetition, power information for RL repetitions 2 and on, should be defined in MultipleRL-DL-DPCH-InformationModifyList-RL-ReconfPrepTDD
	{ ID id-RL-ID		CRITICALITY ignore		EXTENSION		RL-ID		PRESENCE optional	}|
-- This is the RL ID for the first RL repetition
	{ ID id-multipleRL-dl-DPCH-InformationModifyList	CRITICALITY reject		EXTENSION		MultipleRL-DL-DPCH-InformationModifyList-RL-ReconfPrepTDD	PRESENCE optional	}|
-- This DPCH Information is the for the 2nd and beyond RL repetitions,
	{ ID id-DL-DPCH-768-InformationModify-AddItem-RL-ReconfPrepTDD CRITICALITY reject		EXTENSION 	DL-DPCH-768-InformationModify-AddList-RL-ReconfPrepTDD		PRESENCE optional },  -- Applicable to 7.68Mcps TDD only first radio link
	...
}

CCTrCH-TPCModifyList-RL-ReconfPrepTDD ::= SEQUENCE (SIZE (1..maxNrOfCCTrCHs)) OF CCTrCH-TPCModifyItem-RL-ReconfPrepTDD

CCTrCH-TPCModifyItem-RL-ReconfPrepTDD	 ::= SEQUENCE {
	cCTrCH-ID								CCTrCH-ID,
	iE-Extensions							ProtocolExtensionContainer { { CCTrCH-TPCModifyItem-RL-ReconfPrepTDD-ExtIEs} }		OPTIONAL,
	...
}

CCTrCH-TPCModifyItem-RL-ReconfPrepTDD-ExtIEs  NBAP-PROTOCOL-EXTENSION ::= {
	...
}

DL-DPCH-InformationModify-AddList-RL-ReconfPrepTDD ::= ProtocolIE-Single-Container {{ DL-DPCH-InformationModify-AddListIEs-RL-ReconfPrepTDD }}	
-- Applicable to 3.84Mcps TDD only

DL-DPCH-InformationModify-AddListIEs-RL-ReconfPrepTDD NBAP-PROTOCOL-IES ::= {
	{ ID id-DL-DPCH-InformationModify-AddListIE-RL-ReconfPrepTDD   CRITICALITY reject		TYPE DL-DPCH-InformationModify-AddItem-RL-ReconfPrepTDD		PRESENCE mandatory }
}

DL-DPCH-InformationModify-AddItem-RL-ReconfPrepTDD ::= SEQUENCE {
	repetitionPeriod						RepetitionPeriod,
	repetitionLength						RepetitionLength,
	tdd-DPCHOffset							TDD-DPCHOffset,
	dL-Timeslot-Information					DL-Timeslot-Information,
	iE-Extensions							ProtocolExtensionContainer { { DL-DPCH-InformationModify-AddItem-RL-ReconfPrepTDD-ExtIEs} }		OPTIONAL,
	...
}

DL-DPCH-InformationModify-AddItem-RL-ReconfPrepTDD-ExtIEs  NBAP-PROTOCOL-EXTENSION ::= {
	...
}

DL-DPCH-InformationModify-ModifyList-RL-ReconfPrepTDD ::= ProtocolIE-Single-Container {{ DL-DPCH-InformationModify-ModifyListIEs-RL-ReconfPrepTDD }}

DL-DPCH-InformationModify-ModifyListIEs-RL-ReconfPrepTDD NBAP-PROTOCOL-IES ::= {
	{ ID id-DL-DPCH-InformationModify-ModifyListIE-RL-ReconfPrepTDD   CRITICALITY reject		TYPE DL-DPCH-InformationModify-ModifyItem-RL-ReconfPrepTDD		PRESENCE mandatory }
}

DL-DPCH-InformationModify-ModifyItem-RL-ReconfPrepTDD ::= SEQUENCE {
	repetitionPeriod						RepetitionPeriod			OPTIONAL,
	repetitionLength						RepetitionLength			OPTIONAL,
	tdd-DPCHOffset							TDD-DPCHOffset				OPTIONAL,
	dL-Timeslot-InformationAddModify-ModifyList-RL-ReconfPrepTDD		DL-Timeslot-InformationModify-ModifyList-RL-ReconfPrepTDD			OPTIONAL,
	iE-Extensions							ProtocolExtensionContainer { { DL-DPCH-InformationModify-ModifyItem-RL-ReconfPrepTDD-ExtIEs} }		OPTIONAL,
	...
}

DL-DPCH-InformationModify-ModifyItem-RL-ReconfPrepTDD-ExtIEs  NBAP-PROTOCOL-EXTENSION ::= {
	{ ID id-DL-Timeslot-LCR-InformationModify-ModifyList-RL-ReconfPrepTDD   CRITICALITY reject			EXTENSION		 DL-Timeslot-LCR-InformationModify-ModifyList-RL-ReconfPrepTDD		PRESENCE optional }|
	{ ID id-DL-Timeslot-768-InformationModify-ModifyList-RL-ReconfPrepTDD   CRITICALITY reject			EXTENSION		 DL-Timeslot-768-InformationModify-ModifyList-RL-ReconfPrepTDD		PRESENCE optional },
	...
}

DL-Timeslot-InformationModify-ModifyList-RL-ReconfPrepTDD ::= SEQUENCE (SIZE (1..maxNrOfDLTSs)) OF DL-Timeslot-InformationModify-ModifyItem-RL-ReconfPrepTDD

DL-Timeslot-InformationModify-ModifyItem-RL-ReconfPrepTDD	 ::= SEQUENCE {
	timeSlot								TimeSlot,
	midambleShiftAndBurstType				MidambleShiftAndBurstType			OPTIONAL,
	tFCI-Presence							TFCI-Presence						OPTIONAL,
	dL-Code-InformationModify-ModifyList-RL-ReconfPrepTDD				DL-Code-InformationModify-ModifyList-RL-ReconfPrepTDD			OPTIONAL,
	iE-Extensions							ProtocolExtensionContainer { { DL-Timeslot-InformationModify-ModifyItem-RL-ReconfPrepTDD-ExtIEs} }		OPTIONAL,
	...
}

DL-Timeslot-InformationModify-ModifyItem-RL-ReconfPrepTDD-ExtIEs NBAP-PROTOCOL-EXTENSION ::= {
	...
}

DL-Code-InformationModify-ModifyList-RL-ReconfPrepTDD ::= SEQUENCE (SIZE (0..maxNrOfDPCHs)) OF DL-Code-InformationModify-ModifyItem-RL-ReconfPrepTDD

DL-Code-InformationModify-ModifyItem-RL-ReconfPrepTDD	 ::= SEQUENCE {
	dPCH-ID									DPCH-ID,
	tdd-ChannelisationCode					TDD-ChannelisationCode		OPTIONAL,
	iE-Extensions							ProtocolExtensionContainer { { DL-Code-InformationModify-ModifyItem-RL-ReconfPrepTDD-ExtIEs} }		OPTIONAL,
	...
}

DL-Code-InformationModify-ModifyItem-RL-ReconfPrepTDD-ExtIEs NBAP-PROTOCOL-EXTENSION ::= {
	...
}

DL-Timeslot-LCR-InformationModify-ModifyList-RL-ReconfPrepTDD ::= SEQUENCE (SIZE (1..maxNrOfDLTSLCRs)) OF DL-Timeslot-LCR-InformationModify-ModifyItem-RL-ReconfPrepTDD

DL-Timeslot-LCR-InformationModify-ModifyItem-RL-ReconfPrepTDD	 ::= SEQUENCE {
	timeSlotLCR								TimeSlotLCR,
	midambleShiftLCR						MidambleShiftLCR		OPTIONAL,
	tFCI-Presence							TFCI-Presence			OPTIONAL,
	dL-Code-LCR-InformationModify-ModifyList-RL-ReconfPrepTDD				DL-Code-LCR-InformationModify-ModifyList-RL-ReconfPrepTDD			OPTIONAL,
	iE-Extensions							ProtocolExtensionContainer { { DL-Timeslot-LCR-InformationModify-ModifyItem-RL-ReconfPrepTDD-ExtIEs} }		OPTIONAL,
	...
}

DL-Timeslot-LCR-InformationModify-ModifyItem-RL-ReconfPrepTDD-ExtIEs NBAP-PROTOCOL-EXTENSION ::= {
	{ ID id-Maximum-DL-Power-Modify-LCR-InformationModify-RL-ReconfPrepTDD	CRITICALITY ignore	EXTENSION DL-Power		PRESENCE optional	}|
	-- Applicable to 1.28Mcps TDD only
	{ ID id-Minimum-DL-Power-Modify-LCR-InformationModify-RL-ReconfPrepTDD	CRITICALITY ignore	EXTENSION DL-Power		PRESENCE optional	},
	-- Applicable to 1.28Mcps TDD only
	...
}

DL-Code-LCR-InformationModify-ModifyList-RL-ReconfPrepTDD ::= SEQUENCE (SIZE (1..maxNrOfDPCHLCRs)) OF DL-Code-LCR-InformationModify-ModifyItem-RL-ReconfPrepTDD

DL-Code-LCR-InformationModify-ModifyItem-RL-ReconfPrepTDD	 ::= SEQUENCE {
	dPCH-ID									DPCH-ID,
	tdd-ChannelisationCodeLCR				TDD-ChannelisationCodeLCR		OPTIONAL,
	iE-Extensions							ProtocolExtensionContainer { { DL-Code-LCR-InformationModify-ModifyItem-RL-ReconfPrepTDD-ExtIEs} }		OPTIONAL,
	...
}

DL-Code-LCR-InformationModify-ModifyItem-RL-ReconfPrepTDD-ExtIEs NBAP-PROTOCOL-EXTENSION ::= {
	{ ID id-DL-DPCH-TimeSlotFormat-LCR-ModifyItem-RL-ReconfPrepTDD	 CRITICALITY	reject	 EXTENSION TDD-DL-DPCH-TimeSlotFormat-LCR   PRESENCE  optional},
	...
}

DL-Timeslot-768-InformationModify-ModifyList-RL-ReconfPrepTDD ::= SEQUENCE (SIZE (1..maxNrOfDLTSs)) OF DL-Timeslot-768-InformationModify-ModifyItem-RL-ReconfPrepTDD

DL-Timeslot-768-InformationModify-ModifyItem-RL-ReconfPrepTDD	 ::= SEQUENCE {
	timeSlot								TimeSlot,
	midambleShiftAndBurstType				MidambleShiftAndBurstType			OPTIONAL,
	tFCI-Presence							TFCI-Presence						OPTIONAL,
	dL-Code-768-InformationModify-ModifyList-RL-ReconfPrepTDD				DL-Code-768-InformationModify-ModifyList-RL-ReconfPrepTDD			OPTIONAL,
	iE-Extensions							ProtocolExtensionContainer { { DL-Timeslot-768-InformationModify-ModifyItem-RL-ReconfPrepTDD-ExtIEs} }		OPTIONAL,
	...
}

DL-Timeslot-768-InformationModify-ModifyItem-RL-ReconfPrepTDD-ExtIEs NBAP-PROTOCOL-EXTENSION ::= {
	...
}

DL-Code-768-InformationModify-ModifyList-RL-ReconfPrepTDD ::= SEQUENCE (SIZE (1..maxNrOfDPCHs768)) OF DL-Code-768-InformationModify-ModifyItem-RL-ReconfPrepTDD

DL-Code-768-InformationModify-ModifyItem-RL-ReconfPrepTDD	 ::= SEQUENCE {
	dPCH-ID768								DPCH-ID768,
	tdd-ChannelisationCode768				TDD-ChannelisationCode768		OPTIONAL,
	iE-Extensions							ProtocolExtensionContainer { { DL-Code-768-InformationModify-ModifyItem-RL-ReconfPrepTDD-ExtIEs} }		OPTIONAL,
	...
}

DL-Code-768-InformationModify-ModifyItem-RL-ReconfPrepTDD-ExtIEs NBAP-PROTOCOL-EXTENSION ::= {
	...
}

DL-DPCH-InformationModify-DeleteList-RL-ReconfPrepTDD ::= ProtocolIE-Single-Container {{ DL-DPCH-InformationModify-DeleteListIEs-RL-ReconfPrepTDD }}

DL-DPCH-InformationModify-DeleteListIEs-RL-ReconfPrepTDD NBAP-PROTOCOL-IES ::= {
	{ ID id-DL-DPCH-InformationModify-DeleteListIE-RL-ReconfPrepTDD   CRITICALITY reject		TYPE DL-DPCH-InformationModify-DeleteListIE-RL-ReconfPrepTDD		PRESENCE mandatory }
}

DL-DPCH-InformationModify-DeleteListIE-RL-ReconfPrepTDD ::= SEQUENCE (SIZE (1..maxNrOfDPCHs)) OF DL-DPCH-InformationModify-DeleteItem-RL-ReconfPrepTDD

DL-DPCH-InformationModify-DeleteItem-RL-ReconfPrepTDD ::= SEQUENCE {
	dPCH-ID										DPCH-ID,
	iE-Extensions								ProtocolExtensionContainer { { DL-DPCH-InformationModify-DeleteItem-RL-ReconfPrepTDD-ExtIEs} }		OPTIONAL,
	...
}

DL-DPCH-InformationModify-DeleteItem-RL-ReconfPrepTDD-ExtIEs  NBAP-PROTOCOL-EXTENSION ::= {
	...
}

DL-DPCH-LCR-InformationModify-AddList-RL-ReconfPrepTDD ::= SEQUENCE {
	repetitionPeriod						RepetitionPeriod,
	repetitionLength						RepetitionLength,
	tdd-DPCHOffset							TDD-DPCHOffset,
	dL-Timeslot-InformationLCR				DL-TimeslotLCR-Information,
	iE-Extensions							ProtocolExtensionContainer { { DL-DPCH-LCR-InformationModify-AddItem-RL-ReconfPrepTDD-ExtIEs} }		OPTIONAL,
	...
}

DL-DPCH-LCR-InformationModify-AddItem-RL-ReconfPrepTDD-ExtIEs  NBAP-PROTOCOL-EXTENSION ::= {
	...
}

MultipleRL-DL-DPCH-InformationModifyList-RL-ReconfPrepTDD ::= SEQUENCE (SIZE (1..maxNrOfRLs-1)) OF MultipleRL-DL-DPCH-InformationModifyListIE-RL-ReconfPrepTDD
	--Includes the 2nd through the max number of radio link information repetitions.

MultipleRL-DL-DPCH-InformationModifyListIE-RL-ReconfPrepTDD ::= SEQUENCE {
	dl-DPCH-InformationAddList										DL-DPCH-InformationModify-AddList-RL-ReconfPrepTDD			OPTIONAL,
	dl-DPCH-InformationModifyList									DL-DPCH-InformationModify-ModifyList-RL-ReconfPrepTDD		OPTIONAL,
	dl-DPCH-InformationDeleteList									DL-DPCH-InformationModify-DeleteList-RL-ReconfPrepTDD		OPTIONAL,
	dl-DPCH-InformationAddListLCR									DL-DPCH-LCR-InformationModify-AddList-RL-ReconfPrepTDD	OPTIONAL,
	tDD-TPC-DownlinkStepSize-InformationModify-RL-ReconfPrepTDD		TDD-TPC-DownlinkStepSize											OPTIONAL,
	cCTrCH-Maximum-DL-Power-InformationModify-RL-ReconfPrepTDD		DL-Power									OPTIONAL,
	cCTrCH-Minimum-DL-Power-InformationModify-RL-ReconfPrepTDD		DL-Power									OPTIONAL,
	rL-ID															RL-ID										OPTIONAL,
	iE-Extensions													ProtocolExtensionContainer { { MultipleRL-DL-DPCH-InformationModifyListIE-RL-ReconfPrepTDD-ExtIEs} }		OPTIONAL,
	...
} 

MultipleRL-DL-DPCH-InformationModifyListIE-RL-ReconfPrepTDD-ExtIEs  NBAP-PROTOCOL-EXTENSION ::= {
	{ ID id-DL-DPCH-768-InformationModify-AddList-RL-ReconfPrepTDD CRITICALITY reject		EXTENSION 	DL-DPCH-768-InformationModify-AddList-RL-ReconfPrepTDD		PRESENCE optional },  -- Applicable to 7.68Mcps TDD only
	...
}

DL-DPCH-768-InformationModify-AddList-RL-ReconfPrepTDD ::= SEQUENCE {
	repetitionPeriod						RepetitionPeriod,
	repetitionLength						RepetitionLength,
	tdd-DPCHOffset							TDD-DPCHOffset,
	dL-Timeslot-Information768				DL-Timeslot768-Information,
	iE-Extensions							ProtocolExtensionContainer { { DL-DPCH-768-InformationModify-AddItem-RL-ReconfPrepTDD-ExtIEs} }		OPTIONAL,
	...
}

DL-DPCH-768-InformationModify-AddItem-RL-ReconfPrepTDD-ExtIEs  NBAP-PROTOCOL-EXTENSION ::= {
	...
}

DL-CCTrCH-InformationDeleteList-RL-ReconfPrepTDD ::= SEQUENCE (SIZE (1..maxNrOfCCTrCHs)) OF DL-CCTrCH-InformationDeleteItem-RL-ReconfPrepTDD

DL-CCTrCH-InformationDeleteItem-RL-ReconfPrepTDD ::= SEQUENCE {
	cCTrCH-ID										CCTrCH-ID,
	iE-Extensions									ProtocolExtensionContainer { { DL-CCTrCH-InformationDeleteItem-RL-ReconfPrepTDD-ExtIEs} }			OPTIONAL,
	...
}

DL-CCTrCH-InformationDeleteItem-RL-ReconfPrepTDD-ExtIEs  NBAP-PROTOCOL-EXTENSION ::= {
	...
}

DCH-DeleteList-RL-ReconfPrepTDD ::= SEQUENCE (SIZE (1..maxNrOfDCHs)) OF DCH-DeleteItem-RL-ReconfPrepTDD

DCH-DeleteItem-RL-ReconfPrepTDD ::= SEQUENCE {
	dCH-ID										DCH-ID,
	iE-Extensions								ProtocolExtensionContainer { { DCH-DeleteItem-RL-ReconfPrepTDD-ExtIEs} }		OPTIONAL,
	...
}

DCH-DeleteItem-RL-ReconfPrepTDD-ExtIEs  NBAP-PROTOCOL-EXTENSION ::= {
	...
}

DSCH-Information-ModifyList-RL-ReconfPrepTDD ::= SEQUENCE (SIZE (1..maxNrOfDSCHs)) OF DSCH-Information-ModifyItem-RL-ReconfPrepTDD

DSCH-Information-ModifyItem-RL-ReconfPrepTDD ::= SEQUENCE {
	dSCH-ID										DSCH-ID,
	cCTrCH-ID									CCTrCH-ID					OPTIONAL,
	-- DL CCTrCH in which the DSCH is mapped
	transportFormatSet							TransportFormatSet			OPTIONAL,
	allocationRetentionPriority					AllocationRetentionPriority	OPTIONAL,
	frameHandlingPriority						FrameHandlingPriority		OPTIONAL,
	toAWS										ToAWS						OPTIONAL,
	toAWE										ToAWE						OPTIONAL,
	transportBearerRequestIndicator				TransportBearerRequestIndicator,
	iE-Extensions								ProtocolExtensionContainer { { DSCH-Information-ModifyItem-RL-ReconfPrepTDD-ExtIEs} }		OPTIONAL,
	...
 }

DSCH-Information-ModifyItem-RL-ReconfPrepTDD-ExtIEs  NBAP-PROTOCOL-EXTENSION ::= {
	{ ID id-bindingID					CRITICALITY ignore	EXTENSION BindingID					PRESENCE optional	}|
	-- Shall be ignored if bearer establishment with ALCAP.
	{ ID id-transportlayeraddress		CRITICALITY ignore	EXTENSION TransportLayerAddress		PRESENCE optional	}|
	-- Shall be ignored if bearer establishment with ALCAP.
	{ ID id-TnlQos						CRITICALITY ignore	EXTENSION TnlQos					PRESENCE optional	},
	...
}

DSCH-Information-DeleteList-RL-ReconfPrepTDD ::= SEQUENCE (SIZE (1..maxNrOfDSCHs)) OF DSCH-Information-DeleteItem-RL-ReconfPrepTDD

DSCH-Information-DeleteItem-RL-ReconfPrepTDD ::= SEQUENCE {
	dSCH-ID										DSCH-ID,
	iE-Extensions								ProtocolExtensionContainer { { DSCH-Information-DeleteItem-RL-ReconfPrepTDD-ExtIEs} }		OPTIONAL,
	...
}

DSCH-Information-DeleteItem-RL-ReconfPrepTDD-ExtIEs  NBAP-PROTOCOL-EXTENSION ::= {
	...
}

USCH-Information-ModifyList-RL-ReconfPrepTDD ::= SEQUENCE (SIZE (1..maxNrOfUSCHs)) OF USCH-Information-ModifyItem-RL-ReconfPrepTDD

USCH-Information-ModifyItem-RL-ReconfPrepTDD ::= SEQUENCE {
 	uSCH-ID										USCH-ID,
 	transportFormatSet							TransportFormatSet			OPTIONAL,
	allocationRetentionPriority					AllocationRetentionPriority	OPTIONAL,
	cCTrCH-ID									CCTrCH-ID					OPTIONAL,	-- UL CCTrCH in which the USCH is mapped
	transportBearerRequestIndicator				TransportBearerRequestIndicator,
	iE-Extensions								ProtocolExtensionContainer { { USCH-Information-ModifyItem-RL-ReconfPrepTDD-ExtIEs} }		OPTIONAL,
	...
}

USCH-Information-ModifyItem-RL-ReconfPrepTDD-ExtIEs  NBAP-PROTOCOL-EXTENSION ::= {
	{ ID id-bindingID						CRITICALITY	ignore		EXTENSION BindingID				PRESENCE optional	}|
	-- Shall be ignored if bearer establishment with ALCAP.
	{ ID id-transportlayeraddress			CRITICALITY	ignore		EXTENSION TransportLayerAddress	PRESENCE optional	}|
	-- Shall be ignored if bearer establishment with ALCAP.
	{ ID id-TnlQos							CRITICALITY	ignore		EXTENSION TnlQos				PRESENCE optional	},
	...
}

USCH-Information-DeleteList-RL-ReconfPrepTDD ::= SEQUENCE (SIZE (1..maxNrOfUSCHs)) OF USCH-Information-DeleteItem-RL-ReconfPrepTDD

USCH-Information-DeleteItem-RL-ReconfPrepTDD ::= SEQUENCE {
	uSCH-ID										USCH-ID,
	iE-Extensions								ProtocolExtensionContainer { { USCH-Information-DeleteItem-RL-ReconfPrepTDD-ExtIEs} }		OPTIONAL,
	...

}

USCH-Information-DeleteItem-RL-ReconfPrepTDD-ExtIEs  NBAP-PROTOCOL-EXTENSION ::= {
	...
}

MultipleRL-Information-RL-ReconfPrepTDD ::= SEQUENCE (SIZE (1..maxNrOfRLs-1)) OF RL-Information-RL-ReconfPrepTDD
--Includes the 2nd through the max number of radio link information repetitions.

RL-Information-RL-ReconfPrepTDD ::= SEQUENCE {
	rL-ID										RL-ID,
	maxDL-Power									DL-Power			OPTIONAL,
	minDL-Power									DL-Power			OPTIONAL,
	iE-Extensions								ProtocolExtensionContainer { { RL-Information-RL-ReconfPrepTDD-ExtIEs} }		OPTIONAL,
	...
}

RL-Information-RL-ReconfPrepTDD-ExtIEs  NBAP-PROTOCOL-EXTENSION ::= {
	{ ID id-InitDL-Power								CRITICALITY ignore	EXTENSION DL-Power				PRESENCE optional	}|
	{ ID id-RL-Specific-DCH-Info						CRITICALITY ignore	EXTENSION RL-Specific-DCH-Info			PRESENCE optional	}|
	{ ID id-UL-Synchronisation-Parameters-LCR			CRITICALITY ignore	EXTENSION UL-Synchronisation-Parameters-LCR	PRESENCE optional	}|
	-- Mandatory for 1.28Mcps TDD, Not Applicable to 3.84Mcps TDD or 7.68Mcps TDD
	{ ID id-TimeslotISCP-LCR-InfoList-RL-ReconfPrepTDD	CRITICALITY ignore	EXTENSION DL-TimeslotISCPInfoLCR			PRESENCE optional	}|
	-- Applicable to 1.28Mcps TDD only
	{ ID id-UARFCNforNt									CRITICALITY reject	EXTENSION UARFCN				PRESENCE optional	},
	  -- Applicable to 1.28Mcps TDD when using multiple frequencies
	...
}


-- **************************************************************
--
-- RADIO LINK RECONFIGURATION READY
--
-- **************************************************************

RadioLinkReconfigurationReady ::= SEQUENCE {
	protocolIEs				ProtocolIE-Container		{{RadioLinkReconfigurationReady-IEs}},
	protocolExtensions		ProtocolExtensionContainer	{{RadioLinkReconfigurationReady-Extensions}}		OPTIONAL,
	...
}

RadioLinkReconfigurationReady-IEs NBAP-PROTOCOL-IES ::= {
	{ ID id-CRNC-CommunicationContextID					CRITICALITY ignore	TYPE CRNC-CommunicationContextID				PRESENCE mandatory }|
	{ ID id-RL-InformationResponseList-RL-ReconfReady	CRITICALITY ignore	TYPE RL-InformationResponseList-RL-ReconfReady	PRESENCE optional }|
	{ ID id-CriticalityDiagnostics						CRITICALITY ignore	TYPE CriticalityDiagnostics				PRESENCE optional },
	...
}

RadioLinkReconfigurationReady-Extensions NBAP-PROTOCOL-EXTENSION ::= {
	{ ID id-TargetCommunicationControlPortID	CRITICALITY ignore		EXTENSION CommunicationControlPortID		PRESENCE optional }|
	{ ID id-HSDSCH-FDD-Information-Response		CRITICALITY ignore		EXTENSION HSDSCH-FDD-Information-Response		PRESENCE optional }|
	-- FDD only
	{ ID id-HSDSCH-TDD-Information-Response		CRITICALITY ignore		EXTENSION HSDSCH-TDD-Information-Response		PRESENCE optional }|
	-- TDD only
	{ ID id-E-DCH-Information-Response			CRITICALITY ignore		EXTENSION E-DCH-Information-Response		PRESENCE optional }|
	{ ID id-MAChs-ResetIndicator				CRITICALITY ignore		EXTENSION MAChs-ResetIndicator						PRESENCE optional }|
	{ ID id-Fast-Reconfiguration-Permission		CRITICALITY ignore		EXTENSION Fast-Reconfiguration-Permission		PRESENCE optional }|
	{ ID id-ContinuousPacketConnectivityHS-SCCH-less-Information-Response		CRITICALITY ignore		EXTENSION	ContinuousPacketConnectivityHS-SCCH-less-Information-Response			PRESENCE optional }|
	{ ID id-Additional-HS-Cell-Information-Response		CRITICALITY ignore		EXTENSION	Additional-HS-Cell-Information-Response-List			PRESENCE optional },
	...
}

RL-InformationResponseList-RL-ReconfReady	 ::= SEQUENCE (SIZE (1..maxNrOfRLs)) OF ProtocolIE-Single-Container {{ RL-InformationResponseItemIE-RL-ReconfReady}}

RL-InformationResponseItemIE-RL-ReconfReady NBAP-PROTOCOL-IES ::= {
	{ ID id-RL-InformationResponseItem-RL-ReconfReady	CRITICALITY ignore	TYPE RL-InformationResponseItem-RL-ReconfReady	PRESENCE mandatory }
}

RL-InformationResponseItem-RL-ReconfReady ::= SEQUENCE {
	rL-ID											RL-ID,
	dCH-InformationResponseList-RL-ReconfReady		DCH-InformationResponseList-RL-ReconfReady	OPTIONAL,
	dSCH-InformationResponseList-RL-ReconfReady		DSCH-InformationResponseList-RL-ReconfReady	OPTIONAL, -- TDD only
	uSCH-InformationResponseList-RL-ReconfReady		USCH-InformationResponseList-RL-ReconfReady	OPTIONAL, -- TDD only
	not-Used-tFCI2-BearerInformationResponse		NULL										OPTIONAL,
	iE-Extensions									ProtocolExtensionContainer { { RL-InformationResponseItem-RL-ReconfReady-ExtIEs} }		OPTIONAL,
	...
}

RL-InformationResponseItem-RL-ReconfReady-ExtIEs  NBAP-PROTOCOL-EXTENSION ::= {
	{ ID id-DL-PowerBalancing-UpdatedIndicator			CRITICALITY ignore	EXTENSION DL-PowerBalancing-UpdatedIndicator				PRESENCE optional }|
	{ ID id-E-DCH-RL-Set-ID								CRITICALITY ignore	EXTENSION RL-Set-ID							PRESENCE optional }|
	{ ID id-E-DCH-FDD-DL-Control-Channel-Information	CRITICALITY ignore	EXTENSION E-DCH-FDD-DL-Control-Channel-Information		PRESENCE optional }|
	{ ID id-E-DCH-FDD-Information-Response				CRITICALITY ignore	EXTENSION E-DCH-FDD-Information-Response					PRESENCE optional },
	...
}

DCH-InformationResponseList-RL-ReconfReady ::= ProtocolIE-Single-Container {{ DCH-InformationResponseListIEs-RL-ReconfReady }}

DCH-InformationResponseListIEs-RL-ReconfReady NBAP-PROTOCOL-IES ::= {
	{ ID id-DCH-InformationResponse   CRITICALITY ignore	TYPE DCH-InformationResponse	PRESENCE mandatory }
}

DSCH-InformationResponseList-RL-ReconfReady ::= ProtocolIE-Single-Container {{ DSCH-InformationResponseListIEs-RL-ReconfReady }}

DSCH-InformationResponseListIEs-RL-ReconfReady NBAP-PROTOCOL-IES ::= {
	{ ID id-DSCH-InformationResponse   CRITICALITY ignore	TYPE DSCH-InformationResponse	PRESENCE mandatory }
}

USCH-InformationResponseList-RL-ReconfReady ::= ProtocolIE-Single-Container {{ USCH-InformationResponseListIEs-RL-ReconfReady }}

USCH-InformationResponseListIEs-RL-ReconfReady NBAP-PROTOCOL-IES ::= {
	{ ID id-USCH-InformationResponse   CRITICALITY ignore	TYPE USCH-InformationResponse	PRESENCE mandatory }
}

-- **************************************************************
--
-- RADIO LINK RECONFIGURATION FAILURE
--
-- **************************************************************

RadioLinkReconfigurationFailure ::= SEQUENCE {
	protocolIEs				ProtocolIE-Container		{{RadioLinkReconfigurationFailure-IEs}},
	protocolExtensions		ProtocolExtensionContainer	{{RadioLinkReconfigurationFailure-Extensions}}		OPTIONAL,
	...
}

RadioLinkReconfigurationFailure-IEs NBAP-PROTOCOL-IES ::= {
	{ ID id-CRNC-CommunicationContextID			CRITICALITY ignore	TYPE CRNC-CommunicationContextID		PRESENCE mandatory } |
	{ ID id-CauseLevel-RL-ReconfFailure			CRITICALITY ignore	TYPE CauseLevel-RL-ReconfFailure		PRESENCE mandatory } |
	{ ID id-CriticalityDiagnostics				CRITICALITY ignore	TYPE CriticalityDiagnostics			PRESENCE optional },
	...
}

RadioLinkReconfigurationFailure-Extensions NBAP-PROTOCOL-EXTENSION ::= {
	...
}

CauseLevel-RL-ReconfFailure ::= CHOICE {
	generalCause		GeneralCauseList-RL-ReconfFailure,
	rLSpecificCause		RLSpecificCauseList-RL-ReconfFailure,
	...
}

GeneralCauseList-RL-ReconfFailure ::= SEQUENCE {
	cause										Cause,
	iE-Extensions								ProtocolExtensionContainer { { GeneralCauseItem-RL-ReconfFailure-ExtIEs} }			OPTIONAL,
	...
}

GeneralCauseItem-RL-ReconfFailure-ExtIEs  NBAP-PROTOCOL-EXTENSION ::= {
	...
}

RLSpecificCauseList-RL-ReconfFailure ::= SEQUENCE {
	rL-ReconfigurationFailureList-RL-ReconfFailure		RL-ReconfigurationFailureList-RL-ReconfFailure		OPTIONAL,
	iE-Extensions										ProtocolExtensionContainer { { RLSpecificCauseItem-RL-ReconfFailure-ExtIEs} }			OPTIONAL,
	...
}

RLSpecificCauseItem-RL-ReconfFailure-ExtIEs  NBAP-PROTOCOL-EXTENSION ::= {
	...
}

RL-ReconfigurationFailureList-RL-ReconfFailure ::= SEQUENCE (SIZE (1..maxNrOfRLs)) OF ProtocolIE-Single-Container {{ RL-ReconfigurationFailureItemIE-RL-ReconfFailure}}

RL-ReconfigurationFailureItemIE-RL-ReconfFailure NBAP-PROTOCOL-IES ::= {
	{ ID id-RL-ReconfigurationFailureItem-RL-ReconfFailure	CRITICALITY ignore	TYPE RL-ReconfigurationFailureItem-RL-ReconfFailure	PRESENCE mandatory}
}

RL-ReconfigurationFailureItem-RL-ReconfFailure ::= SEQUENCE {
 	rL-ID										RL-ID,
	cause										Cause,
	iE-Extensions								ProtocolExtensionContainer { { RL-ReconfigurationFailureItem-RL-ReconfFailure-ExtIEs} }			OPTIONAL,
	...
}

RL-ReconfigurationFailureItem-RL-ReconfFailure-ExtIEs  NBAP-PROTOCOL-EXTENSION ::= {
	...
}

-- **************************************************************
--
-- RADIO LINK RECONFIGURATION COMMIT
--
-- **************************************************************

RadioLinkReconfigurationCommit ::= SEQUENCE {
	protocolIEs				ProtocolIE-Container		{{RadioLinkReconfigurationCommit-IEs}},
	protocolExtensions		ProtocolExtensionContainer	{{RadioLinkReconfigurationCommit-Extensions}}		OPTIONAL,
	...
}

RadioLinkReconfigurationCommit-IEs NBAP-PROTOCOL-IES ::= {
	{ ID	id-NodeB-CommunicationContextID			CRITICALITY ignore	TYPE NodeB-CommunicationContextID	PRESENCE mandatory } |
	{ ID	id-CFN									CRITICALITY ignore	TYPE CFN					PRESENCE mandatory }|
	{ ID 	id-Active-Pattern-Sequence-Information	CRITICALITY ignore	TYPE Active-Pattern-Sequence-Information	PRESENCE optional },
	-- FDD only
	...
}

RadioLinkReconfigurationCommit-Extensions NBAP-PROTOCOL-EXTENSION ::= {
	{ ID id-Fast-Reconfiguration-Mode	CRITICALITY reject	EXTENSION Fast-Reconfiguration-Mode		PRESENCE optional },--FDD only
	...
}

-- **************************************************************
--
-- RADIO LINK RECONFIGURATION CANCEL
--
-- **************************************************************

RadioLinkReconfigurationCancel ::= SEQUENCE {
	protocolIEs				ProtocolIE-Container		{{RadioLinkReconfigurationCancel-IEs}},
	protocolExtensions		ProtocolExtensionContainer	{{RadioLinkReconfigurationCancel-Extensions}}		OPTIONAL,
	...
}

RadioLinkReconfigurationCancel-IEs NBAP-PROTOCOL-IES ::= {
	{ ID id-NodeB-CommunicationContextID			CRITICALITY ignore		TYPE NodeB-CommunicationContextID			PRESENCE mandatory	},
	...
}

RadioLinkReconfigurationCancel-Extensions NBAP-PROTOCOL-EXTENSION ::= {
	...
}

-- **************************************************************
--
-- RADIO LINK RECONFIGURATION REQUEST FDD
--
-- **************************************************************

RadioLinkReconfigurationRequestFDD ::= SEQUENCE {
	protocolIEs				ProtocolIE-Container		{{RadioLinkReconfigurationRequestFDD-IEs}},
	protocolExtensions		ProtocolExtensionContainer	{{RadioLinkReconfigurationRequestFDD-Extensions}}		OPTIONAL,
	...
}

RadioLinkReconfigurationRequestFDD-IEs NBAP-PROTOCOL-IES ::= {
	{ ID id-NodeB-CommunicationContextID					CRITICALITY reject	TYPE NodeB-CommunicationContextID					PRESENCE mandatory }|
	{ ID id-UL-DPCH-Information-RL-ReconfRqstFDD			CRITICALITY reject	TYPE UL-DPCH-Information-RL-ReconfRqstFDD			PRESENCE optional }|
	{ ID id-DL-DPCH-Information-RL-ReconfRqstFDD			CRITICALITY reject	TYPE DL-DPCH-Information-RL-ReconfRqstFDD			PRESENCE optional }|
	{ ID id-FDD-DCHs-to-Modify								CRITICALITY reject	TYPE FDD-DCHs-to-Modify					PRESENCE optional }|
	{ ID id-DCHs-to-Add-FDD									CRITICALITY reject	TYPE DCH-FDD-Information					PRESENCE optional }|
	{ ID id-DCH-DeleteList-RL-ReconfRqstFDD					CRITICALITY reject	TYPE DCH-DeleteList-RL-ReconfRqstFDD				PRESENCE optional }|
	{ ID id-RL-InformationList-RL-ReconfRqstFDD				CRITICALITY reject	TYPE RL-InformationList-RL-ReconfRqstFDD			PRESENCE optional }|
	{ ID id-Transmission-Gap-Pattern-Sequence-Information	CRITICALITY reject	TYPE Transmission-Gap-Pattern-Sequence-Information	 PRESENCE optional },
	...
}

RadioLinkReconfigurationRequestFDD-Extensions NBAP-PROTOCOL-EXTENSION ::= {
	{ ID id-SignallingBearerRequestIndicator			CRITICALITY reject	EXTENSION SignallingBearerRequestIndicator			PRESENCE optional }|
	{ ID id-HSDSCH-FDD-Information						CRITICALITY reject	EXTENSION HSDSCH-FDD-Information				PRESENCE optional }|
	{ ID id-HSDSCH-Information-to-Modify-Unsynchronised	CRITICALITY reject	EXTENSION HSDSCH-Information-to-Modify-Unsynchronised		PRESENCE optional }|
	{ ID id-HSDSCH-MACdFlows-to-Add						CRITICALITY reject	EXTENSION HSDSCH-MACdFlows-Information				PRESENCE optional }|
	{ ID id-HSDSCH-MACdFlows-to-Delete					CRITICALITY reject	EXTENSION HSDSCH-MACdFlows-to-Delete				PRESENCE optional }|
	{ ID id-HSDSCH-RNTI									CRITICALITY reject	EXTENSION HSDSCH-RNTI				PRESENCE conditional }|
	-- The IE shall be present if HS-PDSCH RL ID IE is present.
	{ ID id-HSPDSCH-RL-ID								CRITICALITY reject	EXTENSION RL-ID						PRESENCE optional }|
	{ ID id-E-DPCH-Information-RL-ReconfRqstFDD			CRITICALITY reject	EXTENSION E-DPCH-Information-RL-ReconfRqstFDD		PRESENCE optional }|
	{ ID id-E-DCH-FDD-Information						CRITICALITY reject	EXTENSION E-DCH-FDD-Information				PRESENCE optional }|
	{ ID id-E-DCH-FDD-Information-to-Modify				CRITICALITY reject	EXTENSION E-DCH-FDD-Information-to-Modify			PRESENCE optional }|
	{ ID id-E-DCH-MACdFlows-to-Add						CRITICALITY reject	EXTENSION E-DCH-MACdFlows-Information				PRESENCE optional }|
	{ ID id-E-DCH-MACdFlows-to-Delete					CRITICALITY reject	EXTENSION E-DCH-MACdFlows-to-Delete				PRESENCE optional }|
	{ ID id-Serving-E-DCH-RL-ID							CRITICALITY reject	EXTENSION Serving-E-DCH-RL-ID				PRESENCE optional }|
	{ ID id-CPC-Information								CRITICALITY reject	EXTENSION CPC-Information								PRESENCE optional }|
	{ ID id-NoOfTargetCellHS-SCCH-Order					CRITICALITY	ignore		EXTENSION NoOfTargetCellHS-SCCH-Order			PRESENCE optional}|
	{ ID id-Additional-HS-Cell-Information-RL-Reconf-Req	CRITICALITY reject	EXTENSION Additional-HS-Cell-Information-RL-Reconf-Req			PRESENCE optional },
	...
}

Additional-HS-Cell-Information-RL-Reconf-Req	::= SEQUENCE (SIZE (1..maxNrOfHSDSCH-1)) OF Additional-HS-Cell-Information-RL-Reconf-Req-ItemIEs

Additional-HS-Cell-Information-RL-Reconf-Req-ItemIEs	::=SEQUENCE{
	hSPDSCH-RL-ID									RL-ID,
	c-ID											C-ID										OPTIONAL,
	hS-DSCH-FDD-Secondary-Serving-Information		HS-DSCH-FDD-Secondary-Serving-Information	OPTIONAL,
	hS-DSCH-FDD-Secondary-Serving-Information-To-Modify-Unsynchronised		HS-DSCH-FDD-Secondary-Serving-Information-To-Modify-Unsynchronised	OPTIONAL,
	hS-DSCH-Secondary-Serving-Remove				HS-DSCH-Secondary-Serving-Remove			OPTIONAL,
	iE-Extensions					ProtocolExtensionContainer { { Additional-HS-Cell-Information-RL-Reconf-Req-ExtIEs} } OPTIONAL,
	...
}

Additional-HS-Cell-Information-RL-Reconf-Req-ExtIEs	NBAP-PROTOCOL-EXTENSION ::= {
	...
}


UL-DPCH-Information-RL-ReconfRqstFDD ::= SEQUENCE {
	ul-TFCS											TFCS			OPTIONAL,
	iE-Extensions									ProtocolExtensionContainer { { UL-DPCH-Information-RL-ReconfRqstFDD-ExtIEs} }		OPTIONAL,
	...
}

UL-DPCH-Information-RL-ReconfRqstFDD-ExtIEs NBAP-PROTOCOL-EXTENSION ::= {
	{ ID id-UL-DPDCH-Indicator-For-E-DCH-Operation	CRITICALITY reject	EXTENSION UL-DPDCH-Indicator-For-E-DCH-Operation		PRESENCE optional },
	...
}

DL-DPCH-Information-RL-ReconfRqstFDD ::= SEQUENCE {
	dl-TFCS											TFCS									OPTIONAL,
 	tFCI-SignallingMode								TFCI-SignallingMode						OPTIONAL,
	limitedPowerIncrease							LimitedPowerIncrease					OPTIONAL,
	iE-Extensions									ProtocolExtensionContainer { { DL-DPCH-Information-RL-ReconfRqstFDD-ExtIEs} }		OPTIONAL,
	...
 }

DL-DPCH-Information-RL-ReconfRqstFDD-ExtIEs NBAP-PROTOCOL-EXTENSION ::= {
	...
}

DCH-DeleteList-RL-ReconfRqstFDD ::= SEQUENCE (SIZE (1..maxNrOfDCHs)) OF DCH-DeleteItem-RL-ReconfRqstFDD

DCH-DeleteItem-RL-ReconfRqstFDD ::= SEQUENCE {
	dCH-ID											DCH-ID,
	iE-Extensions									ProtocolExtensionContainer { { DCH-DeleteItem-RL-ReconfRqstFDD-ExtIEs} }			OPTIONAL,
	...

}

DCH-DeleteItem-RL-ReconfRqstFDD-ExtIEs  NBAP-PROTOCOL-EXTENSION ::= {
	...
}

RL-InformationList-RL-ReconfRqstFDD ::= SEQUENCE (SIZE (1..maxNrOfRLs)) OF ProtocolIE-Single-Container {{ RL-InformationItemIE-RL-ReconfRqstFDD}}

RL-InformationItemIE-RL-ReconfRqstFDD NBAP-PROTOCOL-IES ::= {
	{ ID id-RL-InformationItem-RL-ReconfRqstFDD			CRITICALITY reject		TYPE RL-InformationItem-RL-ReconfRqstFDD		PRESENCE mandatory }
}

RL-InformationItem-RL-ReconfRqstFDD ::= SEQUENCE {
	rL-ID										RL-ID,
	maxDL-Power									DL-Power					OPTIONAL,
	minDL-Power									DL-Power					OPTIONAL,
	dl-CodeInformation							FDD-DL-CodeInformation		OPTIONAL,
	-- The IE shall be present if the Transmission Gap Pattern Sequence Information IE is included and the indicated Downlink Compressed Mode method for at least one of the included Transmission Gap Pattern Sequence is set to "SF/2".
	iE-Extensions								ProtocolExtensionContainer { { RL-InformationItem-RL-ReconfRqstFDD-ExtIEs} }			OPTIONAL,
	...
}

RL-InformationItem-RL-ReconfRqstFDD-ExtIEs  NBAP-PROTOCOL-EXTENSION ::= {
	{ ID id-DLReferencePower			CRITICALITY ignore		EXTENSION DL-Power							PRESENCE optional }|
	{ ID id-RL-Specific-DCH-Info		CRITICALITY ignore		EXTENSION RL-Specific-DCH-Info				PRESENCE optional }|
	{ ID id-E-DCH-RL-Indication			CRITICALITY reject		EXTENSION E-DCH-RL-Indication				PRESENCE optional }|
	{ ID id-RL-Specific-E-DCH-Info		CRITICALITY ignore		EXTENSION RL-Specific-E-DCH-Info			PRESENCE optional }|
	{ ID id-F-DPCH-SlotFormat			CRITICALITY reject		EXTENSION F-DPCH-SlotFormat					PRESENCE optional },
	...
}

E-DPCH-Information-RL-ReconfRqstFDD ::= SEQUENCE {
	maxSet-E-DPDCHs						Max-Set-E-DPDCHs													OPTIONAL,
	ul-PunctureLimit					PunctureLimit														OPTIONAL,
	e-TFCS-Information					E-TFCS-Information													OPTIONAL,
	e-TTI								E-TTI																OPTIONAL,
	e-DPCCH-PO							E-DPCCH-PO																					OPTIONAL,
	e-RGCH-2-IndexStepThreshold			E-RGCH-2-IndexStepThreshold											OPTIONAL,
	e-RGCH-3-IndexStepThreshold			E-RGCH-3-IndexStepThreshold																	OPTIONAL,
	hARQ-Info-for-E-DCH					HARQ-Info-for-E-DCH													OPTIONAL,
	hSDSCH-Configured-Indicator			HSDSCH-Configured-Indicator											OPTIONAL,
	iE-Extensions					ProtocolExtensionContainer { { E-DPCH-Information-RL-ReconfRqstFDD-ExtIEs} }			OPTIONAL,
	...
}

E-DPCH-Information-RL-ReconfRqstFDD-ExtIEs NBAP-PROTOCOL-EXTENSION ::= {
	{ ID id-MinimumReducedE-DPDCH-GainFactor		CRITICALITY ignore	EXTENSION MinimumReducedE-DPDCH-GainFactor	PRESENCE optional },
	...
}

-- **************************************************************
--
-- RADIO LINK RECONFIGURATION REQUEST TDD
--
-- **************************************************************

RadioLinkReconfigurationRequestTDD ::= SEQUENCE {
	protocolIEs				ProtocolIE-Container		{{RadioLinkReconfigurationRequestTDD-IEs}},
	protocolExtensions		ProtocolExtensionContainer	{{RadioLinkReconfigurationRequestTDD-Extensions}}		OPTIONAL,
	...
}

RadioLinkReconfigurationRequestTDD-IEs NBAP-PROTOCOL-IES ::= {
	{ ID id-NodeB-CommunicationContextID						CRITICALITY reject	TYPE NodeB-CommunicationContextID				PRESENCE mandatory }|
	{ ID id-UL-CCTrCH-InformationModifyList-RL-ReconfRqstTDD	CRITICALITY notify	TYPE UL-CCTrCH-InformationModifyList-RL-ReconfRqstTDD		PRESENCE optional } |
	{ ID id-UL-CCTrCH-InformationDeleteList-RL-ReconfRqstTDD	CRITICALITY notify	TYPE UL-CCTrCH-InformationDeleteList-RL-ReconfRqstTDD		PRESENCE optional } |
	{ ID id-DL-CCTrCH-InformationModifyList-RL-ReconfRqstTDD	CRITICALITY notify	TYPE DL-CCTrCH-InformationModifyList-RL-ReconfRqstTDD		PRESENCE optional } |
	{ ID id-DL-CCTrCH-InformationDeleteList-RL-ReconfRqstTDD	CRITICALITY notify	TYPE DL-CCTrCH-InformationDeleteList-RL-ReconfRqstTDD		PRESENCE optional } |
	{ ID id-TDD-DCHs-to-Modify									CRITICALITY reject	TYPE TDD-DCHs-to-Modify					PRESENCE optional }|
	{ ID	id-DCHs-to-Add-TDD									CRITICALITY reject	TYPE DCH-TDD-Information					PRESENCE optional }|
	{ ID id-DCH-DeleteList-RL-ReconfRqstTDD						CRITICALITY reject	TYPE DCH-DeleteList-RL-ReconfRqstTDD			PRESENCE optional }|
	{ ID id-RL-Information-RL-ReconfRqstTDD						CRITICALITY reject	TYPE RL-Information-RL-ReconfRqstTDD			PRESENCE optional },
-- This RL-Information-RL-ReconfRqstTDD is the first RL information repetition in the RL-Information List. Repetition 2 and on, should be defined in Multiple-RL-Information-RL-ReconfRqstTDD,
	...
}

RadioLinkReconfigurationRequestTDD-Extensions NBAP-PROTOCOL-EXTENSION ::= {
	{ ID id-SignallingBearerRequestIndicator			CRITICALITY reject	EXTENSION SignallingBearerRequestIndicator	PRESENCE optional }|
	{ ID id-multiple-RL-Information-RL-ReconfRqstTDD				CRITICALITY reject	EXTENSION Multiple-RL-Information-RL-ReconfRqstTDD		PRESENCE optional }|
--Includes the 2nd through the max number of radio link information repetitions.
	{ ID id-HSDSCH-TDD-Information						CRITICALITY reject	EXTENSION HSDSCH-TDD-Information			PRESENCE optional }|
	{ ID id-HSDSCH-Information-to-Modify-Unsynchronised	CRITICALITY reject	EXTENSION HSDSCH-Information-to-Modify-Unsynchronised		PRESENCE optional }|
	{ ID id-HSDSCH-MACdFlows-to-Add						CRITICALITY reject	EXTENSION HSDSCH-MACdFlows-Information			PRESENCE optional }|
	{ ID id-HSDSCH-MACdFlows-to-Delete					CRITICALITY reject	EXTENSION HSDSCH-MACdFlows-to-Delete			PRESENCE optional }|
	{ ID id-HSDSCH-RNTI									CRITICALITY reject	EXTENSION HSDSCH-RNTI			PRESENCE conditional }|
	-- The IE shall be present if HS-PDSCH RL ID IE is present.
	{ ID id-HSPDSCH-RL-ID								CRITICALITY reject	EXTENSION RL-ID					PRESENCE optional }|
	{ ID id-E-DCH-Information-Reconfig					CRITICALITY reject	EXTENSION E-DCH-Information-Reconfig			PRESENCE optional }|
	{ ID id-E-DCH-Serving-RL-ID							CRITICALITY reject	EXTENSION RL-ID					PRESENCE optional }|
	{ ID id-E-DCH-768-Information-Reconfig				CRITICALITY reject	EXTENSION E-DCH-768-Information-Reconfig		PRESENCE optional }|
	{ ID id-E-DCH-LCR-Information-Reconfig				CRITICALITY reject	EXTENSION E-DCH-LCR-Information-Reconfig		PRESENCE optional }|
	{ ID id-PowerControlGAP								CRITICALITY ignore	EXTENSION ControlGAP									PRESENCE optional },
	-- Applicable to 1.28Mcps TDD only
	...
}

UL-CCTrCH-InformationModifyList-RL-ReconfRqstTDD ::= SEQUENCE (SIZE (1..maxNrOfCCTrCHs)) OF ProtocolIE-Single-Container {{ UL-CCTrCH-InformationModifyItemIE-RL-ReconfRqstTDD}}

UL-CCTrCH-InformationModifyItemIE-RL-ReconfRqstTDD NBAP-PROTOCOL-IES ::= {
	{ ID id-UL-CCTrCH-InformationModifyItem-RL-ReconfRqstTDD	CRITICALITY notify	TYPE UL-CCTrCH-InformationModifyItem-RL-ReconfRqstTDD		PRESENCE mandatory}
}

UL-CCTrCH-InformationModifyItem-RL-ReconfRqstTDD ::= SEQUENCE {
	cCTrCH-ID										CCTrCH-ID,
	tFCS											TFCS			OPTIONAL,
	punctureLimit									PunctureLimit	OPTIONAL,
	iE-Extensions									ProtocolExtensionContainer { { UL-CCTrCH-InformationModifyItem-RL-ReconfRqstTDD-ExtIEs} }			OPTIONAL,
	...
}

UL-CCTrCH-InformationModifyItem-RL-ReconfRqstTDD-ExtIEs  NBAP-PROTOCOL-EXTENSION ::= {
{ ID id-UL-SIRTarget		CRITICALITY reject		EXTENSION UL-SIR		PRESENCE optional },
	-- Applicable to 1.28Mcps TDD only
	...
}

UL-CCTrCH-InformationDeleteList-RL-ReconfRqstTDD ::= SEQUENCE (SIZE (1..maxNrOfCCTrCHs)) OF ProtocolIE-Single-Container {{ UL-CCTrCH-InformationDeleteItemIE-RL-ReconfRqstTDD}}

UL-CCTrCH-InformationDeleteItemIE-RL-ReconfRqstTDD NBAP-PROTOCOL-IES ::= {
	{ ID id-UL-CCTrCH-InformationDeleteItem-RL-ReconfRqstTDD			CRITICALITY notify	TYPE UL-CCTrCH-InformationDeleteItem-RL-ReconfRqstTDD		PRESENCE mandatory }
}

UL-CCTrCH-InformationDeleteItem-RL-ReconfRqstTDD ::= SEQUENCE {
	cCTrCH-ID										CCTrCH-ID,
	iE-Extensions									ProtocolExtensionContainer { { UL-CCTrCH-InformationDeleteItem-RL-ReconfRqstTDD-ExtIEs} }			OPTIONAL,
	...
}

UL-CCTrCH-InformationDeleteItem-RL-ReconfRqstTDD-ExtIEs  NBAP-PROTOCOL-EXTENSION ::= {
	...
}

DL-CCTrCH-InformationModifyList-RL-ReconfRqstTDD ::= SEQUENCE (SIZE (1..maxNrOfCCTrCHs)) OF ProtocolIE-Single-Container {{ DL-CCTrCH-InformationModifyItemIE-RL-ReconfRqstTDD}}

DL-CCTrCH-InformationModifyItemIE-RL-ReconfRqstTDD NBAP-PROTOCOL-IES ::= {
	{ ID id-DL-CCTrCH-InformationModifyItem-RL-ReconfRqstTDD		CRITICALITY notify		TYPE DL-CCTrCH-InformationModifyItem-RL-ReconfRqstTDD	PRESENCE mandatory }
}

DL-CCTrCH-InformationModifyItem-RL-ReconfRqstTDD ::= SEQUENCE {
	cCTrCH-ID										CCTrCH-ID,
	tFCS											TFCS			OPTIONAL,
	punctureLimit									PunctureLimit	OPTIONAL,
	iE-Extensions									ProtocolExtensionContainer { { DL-CCTrCH-InformationModifyItem-RL-ReconfRqstTDD-ExtIEs} }			OPTIONAL,
	...
}

DL-CCTrCH-InformationModifyItem-RL-ReconfRqstTDD-ExtIEs  NBAP-PROTOCOL-EXTENSION ::= {
	{ ID id-DL-DPCH-LCR-InformationModify-ModifyList-RL-ReconfRqstTDD	CRITICALITY ignore	EXTENSION  DL-DPCH-LCR-InformationModify-ModifyList-RL-ReconfRqstTDD		PRESENCE optional }|	-- Applicable to 1.28Mcps TDD only
-- This DPCH LCR Information is the for the first RL repetition, DPCH LCR information for RL repetitions 2 and on, should be defined in MultipleRL-DL-CCTrCH-InformationModifyList-RL-ReconfRqstTDD.
	{ ID id-CCTrCH-Maximum-DL-Power-InformationModify-RL-ReconfRqstTDD	CRITICALITY ignore	EXTENSION DL-Power		PRESENCE optional	}|
-- This power Information is the for the first RL repetition, power information for RL repetitions 2 and on, should be defined in MultipleRL-DL-CCTrCH-InformationModifyList-RL-ReconfRqstTDD.
	{ ID id-CCTrCH-Minimum-DL-Power-InformationModify-RL-ReconfRqstTDD	CRITICALITY ignore	EXTENSION DL-Power		PRESENCE optional	}|
-- This power Information is the for the first RL repetition, power information for RL repetitions 2 and on, should be defined in MultipleRL-DL-CCTrCH-InformationModifyList-RL-ReconfRqstTDD.
	{ ID id-RL-ID														CRITICALITY ignore	EXTENSION RL-ID		PRESENCE optional	}|
-- This is the RL ID for the first RL repetition.
	{ ID id-multipleRL-dl-CCTrCH-InformationModifyList-RL-ReconfRqstTDD	CRITICALITY reject	EXTENSION	MultipleRL-DL-CCTrCH-InformationModifyList-RL-ReconfRqstTDD	PRESENCE optional	},
-- This CCTrCH Information is the for the 2nd and beyond RL repetitions.
	...
}

MultipleRL-DL-CCTrCH-InformationModifyList-RL-ReconfRqstTDD ::= SEQUENCE (SIZE (1..maxNrOfRLs-1)) OF  MultipleRL-DL-CCTrCH-InformationModifyListIE-RL-ReconfRqstTDD
--Includes the 2nd through the max number of radio link information repetitions.

MultipleRL-DL-CCTrCH-InformationModifyListIE-RL-ReconfRqstTDD ::= SEQUENCE {
	dl-DPCH-LCR-InformationModifyList								DL-DPCH-LCR-InformationModify-ModifyList-RL-ReconfRqstTDD	OPTIONAL,
	cCTrCH-Maximum-DL-Power-InformationModify-RL-ReconfRqstTDD		DL-Power										OPTIONAL,
	cCTrCH-Minimum-DL-Power-InformationModify-RL-ReconfRqstTDD		DL-Power										OPTIONAL,
	rL-ID															RL-ID											OPTIONAL,
	...
}

DL-DPCH-LCR-InformationModify-ModifyList-RL-ReconfRqstTDD ::= SEQUENCE {	
	dL-Timeslot-LCR-InformationModify-ModifyList-RL-ReconfRqstTDD		DL-Timeslot-LCR-InformationModify-ModifyList-RL-ReconfRqstTDD		OPTIONAL,
	iE-Extensions							ProtocolExtensionContainer { { DL-DPCH-LCR-InformationModify-ModifyList-RL-ReconfRqstTDD-ExtIEs} }		OPTIONAL,
	...
}

DL-DPCH-LCR-InformationModify-ModifyList-RL-ReconfRqstTDD-ExtIEs  NBAP-PROTOCOL-EXTENSION ::= {
	...
}

DL-Timeslot-LCR-InformationModify-ModifyList-RL-ReconfRqstTDD	::= SEQUENCE (SIZE (1..maxNrOfDLTSLCRs)) OF DL-Timeslot-LCR-InformationModify-ModifyItem-RL-ReconfRqstTDD	

DL-Timeslot-LCR-InformationModify-ModifyItem-RL-ReconfRqstTDD	 ::= SEQUENCE {
	timeSlotLCR								TimeSlotLCR,
	maxPowerLCR								DL-Power	OPTIONAL,
	minPowerLCR								DL-Power	OPTIONAL,
	iE-Extensions							ProtocolExtensionContainer { { DL-Timeslot-LCR-InformationModify-ModifyItem-RL-ReconfRqstTDD-ExtIEs} }		OPTIONAL,
	...
}

DL-Timeslot-LCR-InformationModify-ModifyItem-RL-ReconfRqstTDD-ExtIEs  NBAP-PROTOCOL-EXTENSION ::= {
	...
}

DL-CCTrCH-InformationDeleteList-RL-ReconfRqstTDD ::= SEQUENCE (SIZE (1..maxNrOfCCTrCHs)) OF ProtocolIE-Single-Container {{ DL-CCTrCH-InformationDeleteItemIE-RL-ReconfRqstTDD}}

DL-CCTrCH-InformationDeleteItemIE-RL-ReconfRqstTDD NBAP-PROTOCOL-IES ::= {
	{ ID id-DL-CCTrCH-InformationDeleteItem-RL-ReconfRqstTDD		CRITICALITY notify	TYPE DL-CCTrCH-InformationDeleteItem-RL-ReconfRqstTDD		PRESENCE mandatory }
}

DL-CCTrCH-InformationDeleteItem-RL-ReconfRqstTDD ::= SEQUENCE {
	cCTrCH-ID										CCTrCH-ID,
	iE-Extensions									ProtocolExtensionContainer { { DL-CCTrCH-InformationDeleteItem-RL-ReconfRqstTDD-ExtIEs} }			OPTIONAL,
	...
}

DL-CCTrCH-InformationDeleteItem-RL-ReconfRqstTDD-ExtIEs  NBAP-PROTOCOL-EXTENSION ::= {
	...
}

DCH-DeleteList-RL-ReconfRqstTDD ::= SEQUENCE (SIZE (1..maxNrOfDCHs)) OF DCH-DeleteItem-RL-ReconfRqstTDD

DCH-DeleteItem-RL-ReconfRqstTDD ::= SEQUENCE {
	dCH-ID											DCH-ID,
	iE-Extensions									ProtocolExtensionContainer { { DCH-DeleteItem-RL-ReconfRqstTDD-ExtIEs} }			OPTIONAL,
	...
}

DCH-DeleteItem-RL-ReconfRqstTDD-ExtIEs  NBAP-PROTOCOL-EXTENSION ::= {
	...
}

Multiple-RL-Information-RL-ReconfRqstTDD ::= SEQUENCE (SIZE (1..maxNrOfRLs-1)) OF RL-Information-RL-ReconfRqstTDD
--Includes the 2nd through the max number of radio link information repetitions.

RL-Information-RL-ReconfRqstTDD ::= SEQUENCE {
	rL-ID										RL-ID,
	maxDL-Power									DL-Power		OPTIONAL,
	minDL-Power									DL-Power		OPTIONAL,
	iE-Extensions								ProtocolExtensionContainer { { RL-InformationItem-RL-ReconfRqstTDD-ExtIEs} }			OPTIONAL,
	...
}

RL-InformationItem-RL-ReconfRqstTDD-ExtIEs  NBAP-PROTOCOL-EXTENSION ::= {
	{ ID id-RL-Specific-DCH-Info				CRITICALITY	ignore		EXTENSION 	RL-Specific-DCH-Info		PRESENCE optional	}|
	{ ID id-UL-Synchronisation-Parameters-LCR	CRITICALITY	ignore		EXTENSION 	UL-Synchronisation-Parameters-LCR	PRESENCE optional	},
	-- Mandatory for 1.28Mcps TDD, Not Applicable to 3.84Mcps TDD or 7.68Mcps TDD
	...
}

-- **************************************************************
--
-- RADIO LINK RECONFIGURATION RESPONSE
--
-- **************************************************************

RadioLinkReconfigurationResponse ::= SEQUENCE {
	protocolIEs				ProtocolIE-Container		{{RadioLinkReconfigurationResponse-IEs}},
	protocolExtensions		ProtocolExtensionContainer	{{RadioLinkReconfigurationResponse-Extensions}}		OPTIONAL,
	...
}

RadioLinkReconfigurationResponse-IEs NBAP-PROTOCOL-IES ::= {
	{ ID	id-CRNC-CommunicationContextID					CRITICALITY	ignore		TYPE	CRNC-CommunicationContextID						PRESENCE	mandatory	} |
	{ ID	id-RL-InformationResponseList-RL-ReconfRsp		CRITICALITY	ignore		TYPE	RL-InformationResponseList-RL-ReconfRsp		PRESENCE	optional	} |
	{ ID	id-CriticalityDiagnostics						CRITICALITY	ignore		TYPE	CriticalityDiagnostics								PRESENCE	optional	},
	...
}

RadioLinkReconfigurationResponse-Extensions NBAP-PROTOCOL-EXTENSION ::= {
	{ ID id-TargetCommunicationControlPortID	CRITICALITY ignore		EXTENSION CommunicationControlPortID		PRESENCE optional }|
	{ ID id-HSDSCH-FDD-Information-Response		CRITICALITY ignore		EXTENSION HSDSCH-FDD-Information-Response		PRESENCE optional }|
	-- FDD only
	{ ID id-HSDSCH-TDD-Information-Response		CRITICALITY ignore		EXTENSION HSDSCH-TDD-Information-Response		PRESENCE optional }|
	-- TDD only
	{ ID id-E-DCH-Information-Response			CRITICALITY ignore		EXTENSION E-DCH-Information-Response		PRESENCE optional	}|
	{ ID id-MAChs-ResetIndicator				CRITICALITY ignore		EXTENSION MAChs-ResetIndicator		PRESENCE optional }|
	{ ID id-ContinuousPacketConnectivityHS-SCCH-less-Information-Response		CRITICALITY ignore		EXTENSION	ContinuousPacketConnectivityHS-SCCH-less-Information-Response			PRESENCE optional }|
	{ ID id-Additional-HS-Cell-Information-Response		CRITICALITY ignore		EXTENSION	Additional-HS-Cell-Information-Response-List			PRESENCE optional },
	...
}

RL-InformationResponseList-RL-ReconfRsp ::= SEQUENCE (SIZE (1..maxNrOfRLs)) OF ProtocolIE-Single-Container {{RL-InformationResponseItemIE-RL-ReconfRsp}}

RL-InformationResponseItemIE-RL-ReconfRsp NBAP-PROTOCOL-IES ::= {
	{ ID id-RL-InformationResponseItem-RL-ReconfRsp	CRITICALITY ignore	TYPE RL-InformationResponseItem-RL-ReconfRsp	PRESENCE mandatory }
}

RL-InformationResponseItem-RL-ReconfRsp ::= SEQUENCE {
	rL-ID										RL-ID,
	dCH-InformationResponseList-RL-ReconfRsp	DCH-InformationResponseList-RL-ReconfRsp									OPTIONAL,
	iE-Extensions								ProtocolExtensionContainer { { RL-InformationResponseItem-RL-ReconfRsp-ExtIEs} }		OPTIONAL,
	...
}

RL-InformationResponseItem-RL-ReconfRsp-ExtIEs  NBAP-PROTOCOL-EXTENSION ::= {
	{ ID id-DL-PowerBalancing-UpdatedIndicator			CRITICALITY ignore	EXTENSION DL-PowerBalancing-UpdatedIndicator				PRESENCE optional }|
	-- FDD only
	{ ID id-E-DCH-RL-Set-ID								CRITICALITY ignore	EXTENSION RL-Set-ID							PRESENCE optional }|
	{ ID id-E-DCH-FDD-DL-Control-Channel-Information	CRITICALITY ignore	EXTENSION E-DCH-FDD-DL-Control-Channel-Information		PRESENCE optional }|
	{ ID id-E-DCH-FDD-Information-Response				CRITICALITY ignore	EXTENSION E-DCH-FDD-Information-Response					PRESENCE optional },
	...
}

DCH-InformationResponseList-RL-ReconfRsp::= ProtocolIE-Single-Container {{ DCH-InformationResponseListIEs-RL-ReconfRsp }}

DCH-InformationResponseListIEs-RL-ReconfRsp NBAP-PROTOCOL-IES ::= {
	{ ID id-DCH-InformationResponse   CRITICALITY ignore	TYPE DCH-InformationResponse	PRESENCE mandatory }
}

-- **************************************************************
--
-- RADIO LINK DELETION REQUEST
--
-- **************************************************************

RadioLinkDeletionRequest ::= SEQUENCE {
	protocolIEs				ProtocolIE-Container		{{RadioLinkDeletionRequest-IEs}},
	protocolExtensions		ProtocolExtensionContainer	{{RadioLinkDeletionRequest-Extensions}}		OPTIONAL,
	...
}

RadioLinkDeletionRequest-IEs NBAP-PROTOCOL-IES ::= {
	{ ID	id-NodeB-CommunicationContextID					CRITICALITY reject	TYPE NodeB-CommunicationContextID				PRESENCE mandatory }|
	{ ID	id-CRNC-CommunicationContextID					CRITICALITY reject	TYPE CRNC-CommunicationContextID				PRESENCE mandatory }|
	{ ID	id-RL-informationList-RL-DeletionRqst			CRITICALITY notify	TYPE RL-informationList-RL-DeletionRqst		PRESENCE mandatory },
	...
}

RadioLinkDeletionRequest-Extensions NBAP-PROTOCOL-EXTENSION ::= {
	...
}

RL-informationList-RL-DeletionRqst ::= SEQUENCE (SIZE (1..maxNrOfRLs)) OF ProtocolIE-Single-Container {{RL-informationItemIE-RL-DeletionRqst}}

RL-informationItemIE-RL-DeletionRqst NBAP-PROTOCOL-IES ::= {
	{ ID id-RL-informationItem-RL-DeletionRqst		CRITICALITY notify			TYPE RL-informationItem-RL-DeletionRqst	PRESENCE mandatory }
}

RL-informationItem-RL-DeletionRqst ::= SEQUENCE {
 	rL-ID										RL-ID,
	iE-Extensions								ProtocolExtensionContainer { { RL-informationItem-RL-DeletionRqst-ExtIEs} }		OPTIONAL,
	...		
 }

RL-informationItem-RL-DeletionRqst-ExtIEs  NBAP-PROTOCOL-EXTENSION ::= {
	...
}

-- **************************************************************
--
-- RADIO LINK DELETION RESPONSE
--
-- **************************************************************

RadioLinkDeletionResponse ::= SEQUENCE {
	protocolIEs				ProtocolIE-Container		{{RadioLinkDeletionResponse-IEs}},
	protocolExtensions		ProtocolExtensionContainer	{{RadioLinkDeletionResponse-Extensions}}		OPTIONAL,
	...
}

RadioLinkDeletionResponse-IEs NBAP-PROTOCOL-IES ::= {
	{ ID	id-CRNC-CommunicationContextID			CRITICALITY ignore	TYPE CRNC-CommunicationContextID				PRESENCE	mandatory	}|
	{ ID	id-CriticalityDiagnostics				CRITICALITY ignore	TYPE CriticalityDiagnostics				PRESENCE	optional	},
	...
}

RadioLinkDeletionResponse-Extensions NBAP-PROTOCOL-EXTENSION ::= {
	...
}

-- **************************************************************
--
-- DL POWER CONTROL REQUEST FDD
--
-- **************************************************************

DL-PowerControlRequest ::= SEQUENCE {
	protocolIEs				ProtocolIE-Container		{{DL-PowerControlRequest-IEs}},
	protocolExtensions		ProtocolExtensionContainer	{{DL-PowerControlRequest-Extensions}}		OPTIONAL,
	...
}

DL-PowerControlRequest-IEs NBAP-PROTOCOL-IES ::= {
	{ ID id-NodeB-CommunicationContextID		CRITICALITY	ignore	TYPE NodeB-CommunicationContextID		PRESENCE	mandatory }|
	{ ID id-PowerAdjustmentType					CRITICALITY ignore	TYPE PowerAdjustmentType			PRESENCE mandatory }|
	{ ID id-DLReferencePower					CRITICALITY ignore	TYPE DL-Power						PRESENCE conditional }|
	-- This IE shall be present if the Adjustment Type IE is set to 'Common'
	{ ID id-InnerLoopDLPCStatus					CRITICALITY	ignore	TYPE InnerLoopDLPCStatus			PRESENCE	optional }|
	{ ID id-DLReferencePowerList-DL-PC-Rqst		CRITICALITY ignore	TYPE DL-ReferencePowerInformationList-DL-PC-Rqst	PRESENCE conditional }|
	-- This IE shall be present if the Adjustment Type IE is set to 'Individual'
	{ ID id-MaxAdjustmentStep					CRITICALITY ignore	TYPE MaxAdjustmentStep				PRESENCE conditional }|
	-- This IE shall be present if the Adjustment Type IE is set to 'Common' or 'Individual'
	{ ID id-AdjustmentPeriod					CRITICALITY ignore	TYPE AdjustmentPeriod				PRESENCE conditional }|
	-- This IE shall be present if the Adjustment Type IE is set to 'Common' or 'Individual'
	{ ID id-AdjustmentRatio						CRITICALITY ignore	TYPE ScaledAdjustmentRatio			PRESENCE conditional },
	-- This IE shall be present if the Adjustment Type IE is set to 'Common' or 'Individual'
	...
}

DL-PowerControlRequest-Extensions NBAP-PROTOCOL-EXTENSION ::= {
	...
}

DL-ReferencePowerInformationList-DL-PC-Rqst ::= SEQUENCE (SIZE (1..maxNrOfRLs)) OF ProtocolIE-Single-Container {{DL-ReferencePowerInformationItemIE-DL-PC-Rqst }}

DL-ReferencePowerInformationItemIE-DL-PC-Rqst NBAP-PROTOCOL-IES ::= {
	{ ID id-DL-ReferencePowerInformationItem-DL-PC-Rqst			CRITICALITY ignore			TYPE DL-ReferencePowerInformationItem-DL-PC-Rqst		PRESENCE mandatory }
}

DL-ReferencePowerInformationItem-DL-PC-Rqst ::= SEQUENCE {
	rL-ID									RL-ID,
	dl-ReferencePower						DL-Power,
	iE-Extensions							ProtocolExtensionContainer { { DL-ReferencePowerInformationItem-DL-PC-Rqst-ExtIEs } }		OPTIONAL,
	...		
}

DL-ReferencePowerInformationItem-DL-PC-Rqst-ExtIEs  NBAP-PROTOCOL-EXTENSION ::= {
	...
}

-- **************************************************************
--
-- DL POWER TIMESLOT CONTROL REQUEST TDD
--
-- **************************************************************

DL-PowerTimeslotControlRequest ::= SEQUENCE {
	protocolIEs				ProtocolIE-Container		{{DL-PowerTimeslotControlRequest-IEs}},
	protocolExtensions		ProtocolExtensionContainer	{{DL-PowerTimeslotControlRequest-Extensions}}		OPTIONAL,
	...
}

DL-PowerTimeslotControlRequest-IEs NBAP-PROTOCOL-IES ::= {
	{ ID id-NodeB-CommunicationContextID	CRITICALITY ignore		TYPE NodeB-CommunicationContextID		PRESENCE mandatory } |
	{ ID id-TimeslotISCPInfo				CRITICALITY	ignore		TYPE DL-TimeslotISCPInfo			PRESENCE optional },
	-- Mandatory for 3.84Mcps TDD and 7.68Mcps TDD, Not Applicable to 1.28Mcps TDD
	...
}

DL-PowerTimeslotControlRequest-Extensions NBAP-PROTOCOL-EXTENSION ::= {
	{ ID id-TimeslotISCPInfoList-LCR-DL-PC-RqstTDD		CRITICALITY	ignore			EXTENSION	DL-TimeslotISCPInfoLCR		PRESENCE optional }|
	-- Mandatory for 1.28Mcps TDD, Not Applicable to 3.84Mcps TDD or 7.68Mcps TDD
	{ ID id-PrimCCPCH-RSCP-DL-PC-RqstTDD				CRITICALITY ignore			EXTENSION PrimaryCCPCH-RSCP			PRESENCE optional	}|
	{ ID id-PrimaryCCPCH-RSCP-Delta						CRITICALITY	ignore			EXTENSION PrimaryCCPCH-RSCP-Delta		PRESENCE optional	},
	...
}

-- **************************************************************
--
-- DEDICATED MEASUREMENT INITIATION REQUEST
--
-- **************************************************************

DedicatedMeasurementInitiationRequest ::= SEQUENCE {
	protocolIEs				ProtocolIE-Container	{{DedicatedMeasurementInitiationRequest-IEs}},
	protocolExtensions		ProtocolExtensionContainer	{{DedicatedMeasurementInitiationRequest-Extensions}}		OPTIONAL,
	...
}

DedicatedMeasurementInitiationRequest-IEs NBAP-PROTOCOL-IES ::= {
	{ ID id-NodeB-CommunicationContextID			CRITICALITY reject	TYPE NodeB-CommunicationContextID			PRESENCE mandatory } |
	{ ID id-MeasurementID							CRITICALITY reject	TYPE MeasurementID					PRESENCE mandatory } |
	{ ID id-DedicatedMeasurementObjectType-DM-Rqst	CRITICALITY reject	TYPE DedicatedMeasurementObjectType-DM-Rqst			PRESENCE mandatory } |
	{ ID id-DedicatedMeasurementType				CRITICALITY reject	TYPE DedicatedMeasurementType			PRESENCE mandatory } |
	{ ID id-MeasurementFilterCoefficient			CRITICALITY reject	TYPE MeasurementFilterCoefficient			PRESENCE optional } |
	{ ID id-ReportCharacteristics					CRITICALITY reject	TYPE ReportCharacteristics			PRESENCE mandatory } |
	{ ID id-CFNReportingIndicator					CRITICALITY reject	TYPE FNReportingIndicator			PRESENCE mandatory } |
	{ ID id-CFN										CRITICALITY reject	TYPE CFN							PRESENCE optional } ,
	...
}

DedicatedMeasurementInitiationRequest-Extensions NBAP-PROTOCOL-EXTENSION ::= {
	{ ID id-NumberOfReportedCellPortions			CRITICALITY reject	EXTENSION NumberOfReportedCellPortions			PRESENCE conditional	}|
	-- The IE shall be present if the Dedicated Measurement Type IE is set to ”Best Cell Portions”, FDD only.
	{ ID id-MeasurementRecoveryBehavior				CRITICALITY ignore	EXTENSION MeasurementRecoveryBehavior					PRESENCE optional	}|
	{ ID id-AlternativeFormatReportingIndicator		CRITICALITY ignore	EXTENSION AlternativeFormatReportingIndicator		PRESENCE optional	},
	...
}

DedicatedMeasurementObjectType-DM-Rqst ::= CHOICE {
	rL							RL-DM-Rqst,
	rLS							RL-Set-DM-Rqst, 		-- for FDD only
	all-RL						AllRL-DM-Rqst,
	all-RLS						AllRL-Set-DM-Rqst, 		-- for FDD only
	...
}

RL-DM-Rqst ::= SEQUENCE {
 	rL-InformationList					RL-InformationList-DM-Rqst,
	iE-Extensions						ProtocolExtensionContainer { { RLItem-DM-Rqst-ExtIEs } }		OPTIONAL,
	...		
}

RLItem-DM-Rqst-ExtIEs  NBAP-PROTOCOL-EXTENSION ::= {
	...
}

RL-InformationList-DM-Rqst ::= SEQUENCE (SIZE (1..maxNrOfRLs)) OF ProtocolIE-Single-Container {{ RL-InformationItemIE-DM-Rqst }}

RL-InformationItemIE-DM-Rqst NBAP-PROTOCOL-IES ::= {
	{ ID id-RL-InformationItem-DM-Rqst   CRITICALITY reject	TYPE RL-InformationItem-DM-Rqst		PRESENCE mandatory }
}

RL-InformationItem-DM-Rqst ::= SEQUENCE {
		rL-ID							RL-ID,	
		dPCH-ID							DPCH-ID				OPTIONAL, -- for TDD only
		iE-Extensions					ProtocolExtensionContainer { { RL-InformationItem-DM-Rqst-ExtIEs } }		OPTIONAL,
		...		
	}

RL-InformationItem-DM-Rqst-ExtIEs  NBAP-PROTOCOL-EXTENSION ::= {
	{ ID id-PUSCH-Info-DM-Rqst		CRITICALITY reject				EXTENSION	PUSCH-Info-DM-Rqst		PRESENCE optional}|
	-- TDD only
	{ ID id-HSSICH-Info-DM-Rqst		CRITICALITY reject				EXTENSION	HSSICH-Info-DM-Rqst		PRESENCE optional}|
	-- TDD only
	{ ID id-DPCH-ID768-DM-Rqst		CRITICALITY reject				EXTENSION	DPCH-ID768				PRESENCE optional}|
	-- 7.68Mcps TDD only
	{ ID id-HSSICH-InfoExt-DM-Rqst	CRITICALITY reject				EXTENSION	HSSICH-InfoExt-DM-Rqst		PRESENCE optional},
	-- 1.28Mcps TDD only, used if the HS-SICH identity has a value larger than 31
	...
}

PUSCH-Info-DM-Rqst ::= SEQUENCE (SIZE (1..maxNrOfPUSCHs)) OF PUSCH-ID

HSSICH-Info-DM-Rqst ::= SEQUENCE (SIZE (1..maxNrOfHSSICHs)) OF HS-SICH-ID

HSSICH-InfoExt-DM-Rqst::= SEQUENCE (SIZE (1..maxNrOfHSSICHs)) OF Extended-HS-SICH-ID
-- 1.28Mcps TDD only, used if the HS-SICH identity has a value larger than 31

RL-Set-DM-Rqst ::= SEQUENCE {
	rL-Set-InformationList-DM-Rqst			RL-Set-InformationList-DM-Rqst,
	iE-Extensions							ProtocolExtensionContainer { { RL-SetItem-DM-Rqst-ExtIEs } }		OPTIONAL,
	...		
}

RL-SetItem-DM-Rqst-ExtIEs  NBAP-PROTOCOL-EXTENSION ::= {
	...
}

RL-Set-InformationList-DM-Rqst					::= SEQUENCE (SIZE(1..maxNrOfRLSets)) OF RL-Set-InformationItem-DM-Rqst

RL-Set-InformationItem-DM-Rqst ::= SEQUENCE {
	rL-Set-ID						RL-Set-ID,
	iE-Extensions					ProtocolExtensionContainer { { RL-Set-InformationItem-DM-Rqst-ExtIEs} } OPTIONAL,
	...
}

RL-Set-InformationItem-DM-Rqst-ExtIEs NBAP-PROTOCOL-EXTENSION ::= {
	...
}

AllRL-DM-Rqst ::= NULL

AllRL-Set-DM-Rqst ::= NULL

-- **************************************************************
--
-- DEDICATED MEASUREMENT INITIATION RESPONSE
--
-- **************************************************************

DedicatedMeasurementInitiationResponse ::= SEQUENCE {
	protocolIEs				ProtocolIE-Container		{{DedicatedMeasurementInitiationResponse-IEs}},
	protocolExtensions		ProtocolExtensionContainer	{{DedicatedMeasurementInitiationResponse-Extensions}}		OPTIONAL,
	...
}

DedicatedMeasurementInitiationResponse-IEs NBAP-PROTOCOL-IES ::= {
	{ ID id-CRNC-CommunicationContextID				CRITICALITY ignore	TYPE CRNC-CommunicationContextID		PRESENCE mandatory } |
	{ ID id-MeasurementID							CRITICALITY ignore	TYPE MeasurementID				PRESENCE mandatory } |
	{ ID id-DedicatedMeasurementObjectType-DM-Rsp	CRITICALITY ignore	TYPE DedicatedMeasurementObjectType-DM-Rsp		PRESENCE optional } |
	{ ID id-CriticalityDiagnostics					CRITICALITY ignore	TYPE CriticalityDiagnostics		PRESENCE optional },
	...
}

DedicatedMeasurementInitiationResponse-Extensions NBAP-PROTOCOL-EXTENSION ::= {
	{ ID id-MeasurementRecoverySupportIndicator		CRITICALITY ignore	EXTENSION MeasurementRecoverySupportIndicator		PRESENCE optional},
	...
}

DedicatedMeasurementObjectType-DM-Rsp ::= CHOICE {
	rL							RL-DM-Rsp,
	rLS							RL-Set-DM-Rsp, 	-- for FDD only
	all-RL						RL-DM-Rsp,
	all-RLS						RL-Set-DM-Rsp, 	-- for FDD only
	...
}

RL-DM-Rsp ::= SEQUENCE {
	rL-InformationList-DM-Rsp			RL-InformationList-DM-Rsp,
	iE-Extensions						ProtocolExtensionContainer { { RLItem-DM-Rsp-ExtIEs } }		OPTIONAL,
	...
}

RLItem-DM-Rsp-ExtIEs  NBAP-PROTOCOL-EXTENSION ::= {
	...
}

RL-InformationList-DM-Rsp ::= SEQUENCE (SIZE (1..maxNrOfRLs)) OF ProtocolIE-Single-Container {{ RL-InformationItemIE-DM-Rsp }}

RL-InformationItemIE-DM-Rsp NBAP-PROTOCOL-IES ::= {
	{ ID id-RL-InformationItem-DM-Rsp   CRITICALITY ignore	TYPE RL-InformationItem-DM-Rsp		PRESENCE mandatory }
}

RL-InformationItem-DM-Rsp ::= SEQUENCE {
	rL-ID								RL-ID,
	dPCH-ID								DPCH-ID			OPTIONAL, 	-- for TDD only
	dedicatedMeasurementValue			DedicatedMeasurementValue,
	cFN									CFN				OPTIONAL,
	iE-Extensions						ProtocolExtensionContainer { { RL-InformationItem-DM-Rsp-ExtIEs } }		OPTIONAL,
	...
}

RL-InformationItem-DM-Rsp-ExtIEs  NBAP-PROTOCOL-EXTENSION ::= {
	{ ID id-PUSCH-Info-DM-Rsp		CRITICALITY reject				EXTENSION	PUSCH-Info-DM-Rsp		PRESENCE optional}|
	-- TDD only
	-- This PUSCH Information is the for the first PUSCH repetition, PUSCH information for PUSCH repetitions 2 and on, should be defined in Multiple-PUSCH-InfoList-DM-Rsp.
	{ ID id-HSSICH-Info-DM-Rsp		CRITICALITY reject				EXTENSION	HS-SICH-ID				PRESENCE optional}|
	-- TDD only
	{ ID id-multiple-DedicatedMeasurementValueList-TDD-DM-Rsp	CRITICALITY ignore	EXTENSION Multiple-DedicatedMeasurementValueList-TDD-DM-Rsp	PRESENCE optional	}|
	-- Applicable to 3.84Mcps TDD only. This list of dedicated measurement values is used for the 2nd and beyond measurements of a RL when multiple dedicated measurement values need to be reported.
	{ ID id-multiple-DedicatedMeasurementValueList-LCR-TDD-DM-Rsp	CRITICALITY ignore	EXTENSION Multiple-DedicatedMeasurementValueList-LCR-TDD-DM-Rsp	PRESENCE optional	}|
	-- Applicable to 1.28Mcps TDD only. This list of dedicated measurement values is used for the 2nd and beyond measurements of a RL when multiple dedicated measurement values need to be reported.
	{ ID id-multiple-PUSCH-InfoList-DM-Rsp	CRITICALITY ignore	EXTENSION Multiple-PUSCH-InfoList-DM-Rsp	PRESENCE optional	}|
	-- TDD only, This PUSCH information is the for the 2nd and beyond PUSCH repetitions.
	{ ID id-multiple-HSSICHMeasurementValueList-TDD-DM-Rsp	CRITICALITY ignore	EXTENSION Multiple-HSSICHMeasurementValueList-TDD-DM-Rsp	PRESENCE optional	}|
	-- TDD only. This list of HS-SICH measurement values is used for the 2nd and beyond measurements of a RL when multiple HS-SICH measurement values need to be reported.
	{ ID id-DPCH-ID768-DM-Rsp		CRITICALITY reject				EXTENSION	DPCH-ID768		PRESENCE optional}| 	-- 7.68Mcps TDD only
	{ ID id-multiple-DedicatedMeasurementValueList-768-TDD-DM-Rsp	CRITICALITY ignore	EXTENSION Multiple-DedicatedMeasurementValueList-768-TDD-DM-Rsp	PRESENCE optional	}|
	-- Applicable to 7.68Mcps TDD only. This list of dedicated measurement values is used for the 2nd and beyond measurements of a RL when multiple dedicated measurement values need to be reported.
	{ID id-Extended-HS-SICH-ID		CRITICALITY reject				EXTENSION	Extended-HS-SICH-ID				PRESENCE optional},
	-- 1.28Mcps TDD only, used if the HS-SICH identity has a value larger than 31
	...
}

PUSCH-Info-DM-Rsp ::= SEQUENCE (SIZE (1..maxNrOfPUSCHs)) OF PUSCH-ID

Multiple-PUSCH-InfoList-DM-Rsp ::= SEQUENCE (SIZE (1.. maxNrOfPUSCHs-1)) OF Multiple-PUSCH-InfoListIE-DM-Rsp
-- Includes the 2nd through the max number of PUSCH information repetitions.

Multiple-PUSCH-InfoListIE-DM-Rsp ::= SEQUENCE {
	pUSCH-ID								PUSCH-ID														OPTIONAL,
	dedicatedMeasurementValue				DedicatedMeasurementValue										OPTIONAL,
	iE-Extensions							ProtocolExtensionContainer { { Multiple-PUSCH-InfoListIE-DM-Rsp-ExtIEs} }		OPTIONAL,
	...
}

Multiple-PUSCH-InfoListIE-DM-Rsp-ExtIEs NBAP-PROTOCOL-EXTENSION ::= {
	...
}

Multiple-DedicatedMeasurementValueList-TDD-DM-Rsp ::= SEQUENCE (SIZE (1.. maxNrOfDPCHsPerRL-1)) OF Multiple-DedicatedMeasurementValueItem-TDD-DM-Rsp

Multiple-DedicatedMeasurementValueItem-TDD-DM-Rsp ::= SEQUENCE {
	dPCH-ID								DPCH-ID, 
	dedicatedMeasurementValue			DedicatedMeasurementValue,
	iE-Extensions						ProtocolExtensionContainer { { Multiple-DedicatedMeasurementValueItem-TDD-DM-Rsp-ExtIEs} }		OPTIONAL,
	...
}

Multiple-DedicatedMeasurementValueItem-TDD-DM-Rsp-ExtIEs NBAP-PROTOCOL-EXTENSION ::= {
	...
}

Multiple-DedicatedMeasurementValueList-LCR-TDD-DM-Rsp ::= SEQUENCE (SIZE (1.. maxNrOfDPCHsLCRPerRL-1)) OF Multiple-DedicatedMeasurementValueItem-LCR-TDD-DM-Rsp

Multiple-DedicatedMeasurementValueItem-LCR-TDD-DM-Rsp ::= SEQUENCE {
	dPCH-ID								DPCH-ID, 
	dedicatedMeasurementValue			DedicatedMeasurementValue,
	iE-Extensions						ProtocolExtensionContainer { { Multiple-DedicatedMeasurementValueItem-LCR-TDD-DM-Rsp-ExtIEs} }		OPTIONAL,
	...
}

Multiple-DedicatedMeasurementValueItem-LCR-TDD-DM-Rsp-ExtIEs NBAP-PROTOCOL-EXTENSION ::= {
	...
}

Multiple-HSSICHMeasurementValueList-TDD-DM-Rsp ::= SEQUENCE (SIZE (1.. maxNrOfHSSICHs-1)) OF Multiple-HSSICHMeasurementValueItem-TDD-DM-Rsp

Multiple-HSSICHMeasurementValueItem-TDD-DM-Rsp ::= SEQUENCE {
	hsSICH-ID							HS-SICH-ID,
	dedicatedMeasurementValue			DedicatedMeasurementValue,
	iE-Extensions						ProtocolExtensionContainer { { Multiple-HSSICHMeasurementValueItem-TDD-DM-Rsp-ExtIEs} }		OPTIONAL,
	...
}

Multiple-HSSICHMeasurementValueItem-TDD-DM-Rsp-ExtIEs NBAP-PROTOCOL-EXTENSION ::= {
	{ ID id-Extended-HS-SICH-ID							CRITICALITY ignore	EXTENSION Extended-HS-SICH-ID	PRESENCE optional},
	 -- 1.28Mcps TDD only, used if the HS-SICH identity has a value larger than 31
	...
}

Multiple-DedicatedMeasurementValueList-768-TDD-DM-Rsp ::= SEQUENCE (SIZE (1.. maxNrOfDPCHs768PerRL-1)) OF Multiple-DedicatedMeasurementValueItem-768-TDD-DM-Rsp

Multiple-DedicatedMeasurementValueItem-768-TDD-DM-Rsp ::= SEQUENCE {
	dPCH-ID768							DPCH-ID768, 
	dedicatedMeasurementValue			DedicatedMeasurementValue,
	iE-Extensions						ProtocolExtensionContainer { { Multiple-DedicatedMeasurementValueItem-768-TDD-DM-Rsp-ExtIEs} }		OPTIONAL,
	...
}

Multiple-DedicatedMeasurementValueItem-768-TDD-DM-Rsp-ExtIEs NBAP-PROTOCOL-EXTENSION ::= {
	...
}

RL-Set-DM-Rsp ::= SEQUENCE {
	rL-Set-InformationList-DM-Rsp		RL-Set-InformationList-DM-Rsp,
	iE-Extensions						ProtocolExtensionContainer { { RL-SetItem-DM-Rsp-ExtIEs } }		OPTIONAL,
	...
}

RL-SetItem-DM-Rsp-ExtIEs  NBAP-PROTOCOL-EXTENSION ::= {
	...
}

RL-Set-InformationList-DM-Rsp ::= SEQUENCE (SIZE (1..maxNrOfRLSets)) OF ProtocolIE-Single-Container {{ RL-Set-InformationItemIE-DM-Rsp }}

RL-Set-InformationItemIE-DM-Rsp NBAP-PROTOCOL-IES ::= {
	{ ID id-RL-Set-InformationItem-DM-Rsp		CRITICALITY ignore		TYPE 	RL-Set-InformationItem-DM-Rsp	PRESENCE mandatory}
}

RL-Set-InformationItem-DM-Rsp ::= SEQUENCE {
	rL-Set-ID						RL-Set-ID,
	dedicatedMeasurementValue		DedicatedMeasurementValue,
	cFN								CFN					OPTIONAL,
	iE-Extensions					ProtocolExtensionContainer { { RL-Set-InformationItem-DM-Rsp-ExtIEs} } OPTIONAL,
	...
}

RL-Set-InformationItem-DM-Rsp-ExtIEs NBAP-PROTOCOL-EXTENSION ::= {
	...
}

-- **************************************************************
--
-- DEDICATED MEASUREMENT INITIATION FAILURE
--
-- **************************************************************

DedicatedMeasurementInitiationFailure ::= SEQUENCE {
	protocolIEs				ProtocolIE-Container		{{DedicatedMeasurementInitiationFailure-IEs}},
	protocolExtensions		ProtocolExtensionContainer	{{DedicatedMeasurementInitiationFailure-Extensions}}		OPTIONAL,
	...
}

DedicatedMeasurementInitiationFailure-IEs NBAP-PROTOCOL-IES ::= {
	{ ID	id-CRNC-CommunicationContextID			CRITICALITY		ignore			TYPE	CRNC-CommunicationContextID		PRESENCE	mandatory	} |
	{ ID	id-MeasurementID						CRITICALITY		ignore			TYPE	MeasurementID				PRESENCE	mandatory	} |
	{ ID	id-Cause								CRITICALITY		ignore			TYPE	Cause				PRESENCE	mandatory	} |
	{ ID	id-CriticalityDiagnostics				CRITICALITY		ignore			TYPE	CriticalityDiagnostics				PRESENCE	optional	},
	...
}

DedicatedMeasurementInitiationFailure-Extensions NBAP-PROTOCOL-EXTENSION ::= {
	...
}

-- **************************************************************
--
-- DEDICATED MEASUREMENT REPORT
--
-- **************************************************************

DedicatedMeasurementReport ::= SEQUENCE {
	protocolIEs				ProtocolIE-Container	{{DedicatedMeasurementReport-IEs}},
	protocolExtensions		ProtocolExtensionContainer	{{DedicatedMeasurementReport-Extensions}}		OPTIONAL,
	...
}

DedicatedMeasurementReport-IEs NBAP-PROTOCOL-IES ::= {
	{ ID id-CRNC-CommunicationContextID				CRITICALITY ignore	TYPE CRNC-CommunicationContextID		PRESENCE	mandatory	} |
	{ ID id-MeasurementID							CRITICALITY ignore	TYPE MeasurementID				PRESENCE	mandatory	} |
	{ ID id-DedicatedMeasurementObjectType-DM-Rprt	CRITICALITY ignore	TYPE DedicatedMeasurementObjectType-DM-Rprt		PRESENCE	mandatory	} ,
	...
}

DedicatedMeasurementReport-Extensions NBAP-PROTOCOL-EXTENSION ::= {
	{ ID id-MeasurementRecoveryReportingIndicator	CRITICALITY ignore	EXTENSION	MeasurementRecoveryReportingIndicator		PRESENCE optional	},
	...
}

DedicatedMeasurementObjectType-DM-Rprt ::= CHOICE {
 	rL									RL-DM-Rprt,
	rLS									RL-Set-DM-Rprt, 		-- for FDD only
 	all-RL								RL-DM-Rprt,
	all-RLS								RL-Set-DM-Rprt, 		-- for FDD only
	...
}

RL-DM-Rprt ::= SEQUENCE {
	rL-InformationList-DM-Rprt			RL-InformationList-DM-Rprt,
	iE-Extensions						ProtocolExtensionContainer { { RLItem-DM-Rprt-ExtIEs } }		OPTIONAL,
	...
}

RLItem-DM-Rprt-ExtIEs  NBAP-PROTOCOL-EXTENSION ::= {
	...
}

RL-InformationList-DM-Rprt ::= SEQUENCE (SIZE (1..maxNrOfRLs)) OF ProtocolIE-Single-Container {{ RL-InformationItemIE-DM-Rprt }}

RL-InformationItemIE-DM-Rprt NBAP-PROTOCOL-IES ::= {
	{ ID id-RL-InformationItem-DM-Rprt   CRITICALITY ignore	TYPE RL-InformationItem-DM-Rprt		PRESENCE mandatory }
}

RL-InformationItem-DM-Rprt ::= SEQUENCE {
	rL-ID							RL-ID,
	dPCH-ID							DPCH-ID		OPTIONAL, 		-- for TDD only
	dedicatedMeasurementValueInformation	DedicatedMeasurementValueInformation,
	iE-Extensions					ProtocolExtensionContainer { { RL-InformationItem-DM-Rprt-ExtIEs } }		OPTIONAL,
	...
}

RL-InformationItem-DM-Rprt-ExtIEs  NBAP-PROTOCOL-EXTENSION ::= {
	{ID id-PUSCH-Info-DM-Rprt		CRITICALITY reject				EXTENSION	PUSCH-Info-DM-Rprt		PRESENCE optional}|
	-- TDD only
	-- This PUSCH Information is the for the first PUSCH repetition, PUSCH information for PUSCH repetitions 2 and on, should be defined in Multiple-PUSCH-InfoList-DM-Rprt.
	{ID id-HSSICH-Info-DM-Rprt		CRITICALITY reject				EXTENSION	HS-SICH-ID				PRESENCE optional}|
	-- TDD only
	{ ID id-multiple-PUSCH-InfoList-DM-Rprt	CRITICALITY ignore		EXTENSION Multiple-PUSCH-InfoList-DM-Rprt		PRESENCE optional	}|
	-- TDD only, This PUSCH information is the for the 2nd and beyond PUSCH repetitions.
	{ ID id-DPCH-ID768-DM-Rprt		CRITICALITY reject				EXTENSION	DPCH-ID768				PRESENCE optional}|
	-- 7.68Mcps TDD only
	{ ID id-Extended-HS-SICH-ID		CRITICALITY ignore				EXTENSION Extended-HS-SICH-ID		PRESENCE optional},
	-- 1.28Mcps TDD only, used if the HS-SICH identity has a value larger than 31
	...
}

PUSCH-Info-DM-Rprt ::= SEQUENCE (SIZE (0..maxNrOfPUSCHs)) OF PUSCH-ID

Multiple-PUSCH-InfoList-DM-Rprt ::= SEQUENCE (SIZE (1.. maxNrOfPUSCHs-1)) OF Multiple-PUSCH-InfoListIE-DM-Rprt
-- Includes the 2nd through the max number of PUSCH information repetitions.

Multiple-PUSCH-InfoListIE-DM-Rprt ::= SEQUENCE {
	pUSCH-ID								PUSCH-ID														OPTIONAL,
	dedicatedMeasurementValue				DedicatedMeasurementValue										OPTIONAL,
	iE-Extensions							ProtocolExtensionContainer { { Multiple-PUSCH-InfoListIE-DM-Rprt-ExtIEs} }		OPTIONAL,
	...
}

Multiple-PUSCH-InfoListIE-DM-Rprt-ExtIEs NBAP-PROTOCOL-EXTENSION ::= {
	...
}

RL-Set-DM-Rprt ::= SEQUENCE {
	rL-Set-InformationList-DM-Rprt		RL-Set-InformationList-DM-Rprt,
	iE-Extensions						ProtocolExtensionContainer { { RL-SetItem-DM-Rprt-ExtIEs } }		OPTIONAL,
	...
}

RL-SetItem-DM-Rprt-ExtIEs  NBAP-PROTOCOL-EXTENSION ::= {
	...
}

RL-Set-InformationList-DM-Rprt ::= SEQUENCE (SIZE (1..maxNrOfRLSets)) OF ProtocolIE-Single-Container {{ RL-Set-InformationItemIE-DM-Rprt }}

RL-Set-InformationItemIE-DM-Rprt NBAP-PROTOCOL-IES ::= {
	{ ID id-RL-Set-InformationItem-DM-Rprt	CRITICALITY ignore	TYPE RL-Set-InformationItem-DM-Rprt		PRESENCE mandatory	}
}

RL-Set-InformationItem-DM-Rprt ::= SEQUENCE {
	rL-Set-ID						RL-Set-ID,
	dedicatedMeasurementValueInformation	DedicatedMeasurementValueInformation,
	iE-Extensions					ProtocolExtensionContainer { { RL-Set-InformationItem-DM-Rprt-ExtIEs} } OPTIONAL,
	...
}

RL-Set-InformationItem-DM-Rprt-ExtIEs NBAP-PROTOCOL-EXTENSION ::= {
	...
}

-- **************************************************************
--
-- DEDICATED MEASUREMENT TERMINATION REQUEST
--
-- **************************************************************

DedicatedMeasurementTerminationRequest ::= SEQUENCE {
	protocolIEs				ProtocolIE-Container		{{DedicatedMeasurementTerminationRequest-IEs}},
	protocolExtensions		ProtocolExtensionContainer	{{DedicatedMeasurementTerminationRequest-Extensions}}		OPTIONAL,
	...
}

DedicatedMeasurementTerminationRequest-IEs NBAP-PROTOCOL-IES ::= {
	{ ID	id-NodeB-CommunicationContextID			CRITICALITY		ignore			TYPE	NodeB-CommunicationContextID		PRESENCE	mandatory	} |
	{ ID	id-MeasurementID						CRITICALITY		ignore			TYPE	MeasurementID				PRESENCE	mandatory	},
	...
}

DedicatedMeasurementTerminationRequest-Extensions NBAP-PROTOCOL-EXTENSION ::= {
	...
}

-- **************************************************************
--
-- DEDICATED MEASUREMENT FAILURE INDICATION
--
-- **************************************************************

DedicatedMeasurementFailureIndication ::= SEQUENCE {
	protocolIEs				ProtocolIE-Container		{{DedicatedMeasurementFailureIndication-IEs}},
	protocolExtensions		ProtocolExtensionContainer	{{DedicatedMeasurementFailureIndication-Extensions}}		OPTIONAL,
	...
}

DedicatedMeasurementFailureIndication-IEs NBAP-PROTOCOL-IES ::= {
	{ ID	id-CRNC-CommunicationContextID		CRITICALITY		ignore		TYPE	CRNC-CommunicationContextID		PRESENCE	mandatory	} |
	{ ID	id-MeasurementID					CRITICALITY		ignore		TYPE	MeasurementID		PRESENCE	mandatory	} |
	{ ID	id-Cause							CRITICALITY		ignore		TYPE	Cause				PRESENCE	mandatory	},
	...
}

DedicatedMeasurementFailureIndication-Extensions NBAP-PROTOCOL-EXTENSION ::= {
	...
}

-- **************************************************************
--
-- RADIO LINK FAILURE INDICATION
--
-- **************************************************************

RadioLinkFailureIndication ::= SEQUENCE {
	protocolIEs				ProtocolIE-Container		{{RadioLinkFailureIndication-IEs}},
	protocolExtensions		ProtocolExtensionContainer	{{RadioLinkFailureIndication-Extensions}}		OPTIONAL,
	...
}

RadioLinkFailureIndication-IEs NBAP-PROTOCOL-IES ::= {
	{ ID	id-CRNC-CommunicationContextID				CRITICALITY ignore			TYPE CRNC-CommunicationContextID			PRESENCE	mandatory	} |
	{ ID	id-Reporting-Object-RL-FailureInd			CRITICALITY ignore			TYPE Reporting-Object-RL-FailureInd		PRESENCE	mandatory	} ,
	...
}

RadioLinkFailureIndication-Extensions NBAP-PROTOCOL-EXTENSION ::= {
	...
}

Reporting-Object-RL-FailureInd ::= CHOICE {
	rL						RL-RL-FailureInd,
	rL-Set					RL-Set-RL-FailureInd, --FDD only
	...,
	cCTrCH					CCTrCH-RL-FailureInd --TDD only
}

RL-RL-FailureInd ::= SEQUENCE {
	rL-InformationList-RL-FailureInd		RL-InformationList-RL-FailureInd,
	iE-Extensions							ProtocolExtensionContainer { { RLItem-RL-FailureInd-ExtIEs } }		OPTIONAL,
	...
}

RLItem-RL-FailureInd-ExtIEs NBAP-PROTOCOL-EXTENSION ::= {
	...
}

RL-InformationList-RL-FailureInd ::= SEQUENCE (SIZE (1..maxNrOfRLs)) OF ProtocolIE-Single-Container {{ RL-InformationItemIE-RL-FailureInd}}

RL-InformationItemIE-RL-FailureInd NBAP-PROTOCOL-IES ::= {
 	{ ID id-RL-InformationItem-RL-FailureInd			CRITICALITY ignore			TYPE RL-InformationItem-RL-FailureInd			PRESENCE mandatory }
}

RL-InformationItem-RL-FailureInd ::= SEQUENCE {
 	rL-ID										RL-ID,
 	cause										Cause,
	iE-Extensions								ProtocolExtensionContainer { { RL-InformationItem-RL-FailureInd-ExtIEs } }		OPTIONAL,
	...
}

RL-InformationItem-RL-FailureInd-ExtIEs NBAP-PROTOCOL-EXTENSION ::= {
	...
}

RL-Set-RL-FailureInd ::= SEQUENCE {
	rL-Set-InformationList-RL-FailureInd	RL-Set-InformationList-RL-FailureInd,
	iE-Extensions							ProtocolExtensionContainer { { RL-SetItem-RL-FailureInd-ExtIEs } }		OPTIONAL,
	...
}

RL-SetItem-RL-FailureInd-ExtIEs NBAP-PROTOCOL-EXTENSION ::= {
	...
}

RL-Set-InformationList-RL-FailureInd ::= SEQUENCE (SIZE (1..maxNrOfRLSets)) OF ProtocolIE-Single-Container {{ RL-Set-InformationItemIE-RL-FailureInd }}

RL-Set-InformationItemIE-RL-FailureInd NBAP-PROTOCOL-IES ::= {
 	{ ID id-RL-Set-InformationItem-RL-FailureInd	CRITICALITY ignore		TYPE RL-Set-InformationItem-RL-FailureInd		PRESENCE mandatory	}
}

RL-Set-InformationItem-RL-FailureInd ::= SEQUENCE {
 	rL-Set-ID				RL-Set-ID,
 	cause					Cause,
	iE-Extensions			ProtocolExtensionContainer { { RL-Set-InformationItem-RL-FailureInd-ExtIEs} } OPTIONAL,
	...
}

RL-Set-InformationItem-RL-FailureInd-ExtIEs NBAP-PROTOCOL-EXTENSION ::= {
	...
}

CCTrCH-RL-FailureInd ::= SEQUENCE {
	rL-ID									RL-ID,
	cCTrCH-InformationList-RL-FailureInd	CCTrCH-InformationList-RL-FailureInd,
	iE-Extensions							ProtocolExtensionContainer { { CCTrCHItem-RL-FailureInd-ExtIEs } }		OPTIONAL,
	...
}

CCTrCHItem-RL-FailureInd-ExtIEs NBAP-PROTOCOL-EXTENSION ::= {
	...
}

CCTrCH-InformationList-RL-FailureInd ::= SEQUENCE (SIZE (1..maxNrOfCCTrCHs)) OF ProtocolIE-Single-Container {{ CCTrCH-InformationItemIE-RL-FailureInd}}

CCTrCH-InformationItemIE-RL-FailureInd NBAP-PROTOCOL-IES ::= {
 	{ ID id-CCTrCH-InformationItem-RL-FailureInd		CRITICALITY ignore		TYPE CCTrCH-InformationItem-RL-FailureInd			PRESENCE mandatory }
}

CCTrCH-InformationItem-RL-FailureInd ::= SEQUENCE {
 	cCTrCH-ID									CCTrCH-ID,
	cause										Cause,
	iE-Extensions								ProtocolExtensionContainer { { CCTrCH-InformationItem-RL-FailureInd-ExtIEs } }		OPTIONAL,
	...
}

CCTrCH-InformationItem-RL-FailureInd-ExtIEs NBAP-PROTOCOL-EXTENSION ::= {
	...
}

-- **************************************************************
--
-- RADIO LINK PREEMPTION REQUIRED INDICATION
--
-- **************************************************************

RadioLinkPreemptionRequiredIndication ::= SEQUENCE {
	protocolIEs                     ProtocolIE-Container       {{RadioLinkPreemptionRequiredIndication-IEs}},
	protocolExtensions              ProtocolExtensionContainer {{RadioLinkPreemptionRequiredIndication-Extensions}}                   OPTIONAL,
	...
}

RadioLinkPreemptionRequiredIndication-IEs NBAP-PROTOCOL-IES ::= {
	{ ID id-CRNC-CommunicationContextID					CRITICALITY ignore	TYPE CRNC-CommunicationContextID				PRESENCE mandatory } |
	{ ID id-RL-InformationList-RL-PreemptRequiredInd	CRITICALITY ignore	TYPE RL-InformationList-RL-PreemptRequiredInd		PRESENCE optional	},
	...
}

RadioLinkPreemptionRequiredIndication-Extensions NBAP-PROTOCOL-EXTENSION ::= {
	...
}

RL-InformationList-RL-PreemptRequiredInd ::= SEQUENCE (SIZE (1..maxNrOfRLs)) OF ProtocolIE-Single-Container { {RL-InformationItemIE-RL-PreemptRequiredInd}}

RL-InformationItemIE-RL-PreemptRequiredInd NBAP-PROTOCOL-IES ::= {
	{ ID id-RL-InformationItem-RL-PreemptRequiredInd	CRITICALITY ignore	TYPE RL-InformationItem-RL-PreemptRequiredInd		PRESENCE mandatory },
	...
}

RL-InformationItem-RL-PreemptRequiredInd::= SEQUENCE {
	rL-ID						RL-ID,
	iE-Extensions				ProtocolExtensionContainer { {RL-InformationItem-RL-PreemptRequiredInd-ExtIEs} } OPTIONAL,
	...
}

RL-InformationItem-RL-PreemptRequiredInd-ExtIEs NBAP-PROTOCOL-EXTENSION ::= {
	...
}

-- **************************************************************
--
-- RADIO LINK RESTORE INDICATION
--
-- **************************************************************

RadioLinkRestoreIndication ::= SEQUENCE {
	protocolIEs				ProtocolIE-Container		{{RadioLinkRestoreIndication-IEs}},
	protocolExtensions		ProtocolExtensionContainer	{{RadioLinkRestoreIndication-Extensions}}		OPTIONAL,
	...
}

RadioLinkRestoreIndication-IEs NBAP-PROTOCOL-IES ::= {
	{ ID	id-CRNC-CommunicationContextID			CRITICALITY ignore	TYPE CRNC-CommunicationContextID		PRESENCE	mandatory	} |
	{ ID	id-Reporting-Object-RL-RestoreInd		CRITICALITY ignore	TYPE Reporting-Object-RL-RestoreInd		PRESENCE	mandatory	},
	...
}

RadioLinkRestoreIndication-Extensions NBAP-PROTOCOL-EXTENSION ::= {
	...
}

Reporting-Object-RL-RestoreInd ::= CHOICE {
	rL						RL-RL-RestoreInd, --TDD only
	rL-Set					RL-Set-RL-RestoreInd, --FDD only
	...,
	cCTrCH					CCTrCH-RL-RestoreInd --TDD only
}

RL-RL-RestoreInd ::= SEQUENCE {
	rL-InformationList-RL-RestoreInd		RL-InformationList-RL-RestoreInd,
	iE-Extensions							ProtocolExtensionContainer { { RLItem-RL-RestoreInd-ExtIEs } }		OPTIONAL,
	...
}

RLItem-RL-RestoreInd-ExtIEs NBAP-PROTOCOL-EXTENSION ::= {
	...
}

RL-InformationList-RL-RestoreInd ::= SEQUENCE (SIZE (1..maxNrOfRLs)) OF ProtocolIE-Single-Container {{RL-InformationItemIE-RL-RestoreInd}}

RL-InformationItemIE-RL-RestoreInd NBAP-PROTOCOL-IES ::= {
 	{ ID	id-RL-InformationItem-RL-RestoreInd		CRITICALITY ignore		TYPE	RL-InformationItem-RL-RestoreInd			PRESENCE	mandatory}
}

RL-InformationItem-RL-RestoreInd ::= SEQUENCE {
 	rL-ID									RL-ID,
	iE-Extensions							ProtocolExtensionContainer { { RL-InformationItem-RL-RestoreInd-ExtIEs } }		OPTIONAL,
	...
}

RL-InformationItem-RL-RestoreInd-ExtIEs NBAP-PROTOCOL-EXTENSION ::= {
	...
}

RL-Set-RL-RestoreInd ::= SEQUENCE {
	rL-Set-InformationList-RL-RestoreInd	RL-Set-InformationList-RL-RestoreInd,
	iE-Extensions							ProtocolExtensionContainer { { RL-SetItem-RL-RestoreInd-ExtIEs } }		OPTIONAL,
	...
}

RL-SetItem-RL-RestoreInd-ExtIEs NBAP-PROTOCOL-EXTENSION ::= {
	...
}

RL-Set-InformationList-RL-RestoreInd ::= SEQUENCE (SIZE (1..maxNrOfRLSets)) OF ProtocolIE-Single-Container {{ RL-Set-InformationItemIE-RL-RestoreInd }}

RL-Set-InformationItemIE-RL-RestoreInd NBAP-PROTOCOL-IES ::= {
 	{ ID id-RL-Set-InformationItem-RL-RestoreInd	CRITICALITY ignore		TYPE RL-Set-InformationItem-RL-RestoreInd	PRESENCE mandatory	}
}

RL-Set-InformationItem-RL-RestoreInd ::= SEQUENCE {
 	rL-Set-ID				RL-Set-ID,
 	iE-Extensions			ProtocolExtensionContainer { { RL-Set-InformationItem-RL-RestoreInd-ExtIEs} } OPTIONAL,
	...
}

RL-Set-InformationItem-RL-RestoreInd-ExtIEs NBAP-PROTOCOL-EXTENSION ::= {
	...
}

CCTrCH-RL-RestoreInd ::= SEQUENCE {
	rL-ID									RL-ID,
	cCTrCH-InformationList-RL-RestoreInd	CCTrCH-InformationList-RL-RestoreInd,
	iE-Extensions							ProtocolExtensionContainer { { CCTrCHItem-RL-RestoreInd-ExtIEs } }		OPTIONAL,
	...
}

CCTrCHItem-RL-RestoreInd-ExtIEs NBAP-PROTOCOL-EXTENSION ::= {
	...
}

CCTrCH-InformationList-RL-RestoreInd ::= SEQUENCE (SIZE (1..maxNrOfCCTrCHs)) OF ProtocolIE-Single-Container {{ CCTrCH-InformationItemIE-RL-RestoreInd}}

CCTrCH-InformationItemIE-RL-RestoreInd NBAP-PROTOCOL-IES ::= {
	{ ID id-CCTrCH-InformationItem-RL-RestoreInd	CRITICALITY ignore	TYPE CCTrCH-InformationItem-RL-RestoreInd		PRESENCE	mandatory }
}

CCTrCH-InformationItem-RL-RestoreInd ::= SEQUENCE {
	cCTrCH-ID									CCTrCH-ID,
	iE-Extensions								ProtocolExtensionContainer { { CCTrCH-InformationItem-RL-RestoreInd-ExtIEs } }		OPTIONAL,
	...
}

CCTrCH-InformationItem-RL-RestoreInd-ExtIEs NBAP-PROTOCOL-EXTENSION ::= {
	...
}

-- **************************************************************
--
-- COMPRESSED MODE COMMAND FDD
--
-- **************************************************************

CompressedModeCommand ::= SEQUENCE {
	protocolIEs				ProtocolIE-Container		{{CompressedModeCommand-IEs}},
	protocolExtensions		ProtocolExtensionContainer	{{CompressedModeCommand-Extensions}}                   OPTIONAL,
	...
}

CompressedModeCommand-IEs NBAP-PROTOCOL-IES ::= {
	{ ID id-NodeB-CommunicationContextID			CRITICALITY ignore		TYPE NodeB-CommunicationContextID			PRESENCE mandatory } |
	{ ID id-Active-Pattern-Sequence-Information		CRITICALITY ignore		TYPE Active-Pattern-Sequence-Information		PRESENCE mandatory },
	...
}

CompressedModeCommand-Extensions NBAP-PROTOCOL-EXTENSION ::= {
	...
}

-- **************************************************************
--
-- ERROR INDICATION
--
-- **************************************************************

ErrorIndication ::= SEQUENCE {
	protocolIEs				ProtocolIE-Container		{{ErrorIndication-IEs}},
	protocolExtensions		ProtocolExtensionContainer	{{ErrorIndication-Extensions}}		OPTIONAL,
	...
}

ErrorIndication-IEs NBAP-PROTOCOL-IES ::= {
	{ ID	id-CRNC-CommunicationContextID		CRITICALITY		ignore			TYPE 	CRNC-CommunicationContextID			PRESENCE	optional	} |
	{ ID	id-NodeB-CommunicationContextID		CRITICALITY		ignore			TYPE 	NodeB-CommunicationContextID		PRESENCE	optional	} |
	{ ID	id-Cause							CRITICALITY		ignore			TYPE	Cause				PRESENCE	optional	} |
	{ ID	id-CriticalityDiagnostics			CRITICALITY		ignore			TYPE	CriticalityDiagnostics			PRESENCE	optional	},
	...
}

ErrorIndication-Extensions NBAP-PROTOCOL-EXTENSION ::= {
	...
}

-- **************************************************************
--
-- PRIVATE MESSAGE
--
-- **************************************************************

PrivateMessage ::= SEQUENCE {
	privateIEs		PrivateIE-Container	{{PrivateMessage-IEs}},
	...
}

PrivateMessage-IEs NBAP-PRIVATE-IES ::= {
	...
}

-- **************************************************************
--
-- PHYSICAL SHARED CHANNEL RECONFIGURATION REQUEST FDD
--
-- **************************************************************

PhysicalSharedChannelReconfigurationRequestFDD ::= SEQUENCE {
	protocolIEs			ProtocolIE-Container		{{PhysicalSharedChannelReconfigurationRequestFDD-IEs}},
	protocolExtensions	ProtocolExtensionContainer	{{PhysicalSharedChannelReconfigurationRequestFDD-Extensions}}	OPTIONAL,
	...
}

PhysicalSharedChannelReconfigurationRequestFDD-IEs NBAP-PROTOCOL-IES ::= {
	{ ID id-C-ID											CRITICALITY reject	TYPE C-ID							PRESENCE mandatory }|
	{ ID id-ConfigurationGenerationID						CRITICALITY reject	TYPE ConfigurationGenerationID					PRESENCE mandatory }|
	{ ID id-SFN												CRITICALITY reject	TYPE SFN							PRESENCE optional }|
	{ ID id-HS-PDSCH-HS-SCCH-E-AGCH-E-RGCH-E-HICH-MaxPower-PSCH-ReconfRqst		CRITICALITY reject	TYPE MaximumTransmissionPower					PRESENCE optional }|
	{ ID id-HS-PDSCH-HS-SCCH-ScramblingCode-PSCH-ReconfRqst	CRITICALITY reject	TYPE DL-ScramblingCode					PRESENCE optional }|
	{ ID id-HS-PDSCH-FDD-Code-Information-PSCH-ReconfRqst	CRITICALITY reject	TYPE HS-PDSCH-FDD-Code-Information					PRESENCE optional }|
	{ ID id-HS-SCCH-FDD-Code-Information-PSCH-ReconfRqst	CRITICALITY reject	TYPE HS-SCCH-FDD-Code-Information					PRESENCE optional },
	...
}

PhysicalSharedChannelReconfigurationRequestFDD-Extensions NBAP-PROTOCOL-EXTENSION ::= {
	{ ID id-E-AGCH-And-E-RGCH-E-HICH-FDD-Scrambling-Code		CRITICALITY reject	EXTENSION DL-ScramblingCode										PRESENCE optional }|
	{ ID id-E-AGCH-FDD-Code-Information								CRITICALITY reject	EXTENSION E-AGCH-FDD-Code-Information								PRESENCE optional }|
	{ ID id-E-RGCH-E-HICH-FDD-Code-Information						CRITICALITY reject	EXTENSION E-RGCH-E-HICH-FDD-Code-Information					PRESENCE optional }|
	{ID id-HSDPA-And-EDCH-CellPortion-Information-PSCH-ReconfRqst	CRITICALITY reject	EXTENSION HSDPA-And-EDCH-CellPortion-InformationList-PSCH-ReconfRqst		PRESENCE optional }|
	{ID id-Maximum-Target-ReceivedTotalWideBandPower				CRITICALITY reject	EXTENSION Maximum-Target-ReceivedTotalWideBandPower		 	PRESENCE optional }|
	{ID id-Reference-ReceivedTotalWideBandPower						CRITICALITY ignore	EXTENSION Reference-ReceivedTotalWideBandPower						 PRESENCE optional }|
	{ID id-Target-NonServing-EDCH-To-Total-EDCH-Power-Ratio			CRITICALITY	reject	EXTENSION Target-NonServing-EDCH-To-Total-EDCH-Power-Ratio		PRESENCE optional }|
	{ ID id-HSDSCH-Common-System-InformationFDD						CRITICALITY reject	EXTENSION HSDSCH-Common-System-InformationFDD				PRESENCE optional }|
	{ ID id-Common-MACFlows-to-DeleteFDD				CRITICALITY reject	EXTENSION Common-MACFlows-to-DeleteFDD										PRESENCE optional }|
	{ ID id-HSDSCH-Paging-System-InformationFDD				CRITICALITY reject	EXTENSION HSDSCH-Paging-System-InformationFDD						PRESENCE optional }|
	{ ID id-Paging-MACFlows-to-DeleteFDD				CRITICALITY reject	EXTENSION Paging-MACFlows-to-DeleteFDD										PRESENCE optional }|
	{ ID id-Common-EDCH-System-InformationFDD				CRITICALITY reject	EXTENSION Common-EDCH-System-InformationFDD										PRESENCE optional }|
	{ ID id-Common-UL-MACFlows-to-DeleteFDD				CRITICALITY reject	EXTENSION Common-MACFlows-to-DeleteFDD											PRESENCE optional }|
	{ ID id-Common-EDCH-MACdFlows-to-DeleteFDD					CRITICALITY reject	EXTENSION E-DCH-MACdFlows-to-Delete										PRESENCE optional }|
	{ ID id-Enhanced-UE-DRX-InformationFDD				CRITICALITY reject	EXTENSION Enhanced-UE-DRX-InformationFDD										PRESENCE optional },
	...
}

HSDPA-And-EDCH-CellPortion-InformationList-PSCH-ReconfRqst ::= SEQUENCE (SIZE (1..maxNrOfCellPortionsPerCell)) OF HSDPA-And-EDCH-CellPortion-InformationItem-PSCH-ReconfRqst

HSDPA-And-EDCH-CellPortion-InformationItem-PSCH-ReconfRqst::= SEQUENCE {
	cellPortionID														CellPortionID,
	hS-PDSCH-HS-SCCH-ScramblingCode-PSCH-ReconfRqst						DL-ScramblingCode				OPTIONAL,
	hS-PDSCH-FDD-Code-Information-PSCH-ReconfRqst						HS-PDSCH-FDD-Code-Information		OPTIONAL,
	hS-SCCH-FDD-Code-Information-PSCH-ReconfRqst						HS-SCCH-FDD-Code-Information		OPTIONAL,
	hS-PDSCH-HS-SCCH-E-AGCH-E-RGCH-E-HICH-MaxPower-PSCH-ReconfRqst		MaximumTransmissionPower		OPTIONAL,
	e-AGCH-And-E-RGCH-E-HICH-FDD-Scrambling-Code						DL-ScramblingCode				OPTIONAL,
	e-AGCH-FDD-Code-Information											E-AGCH-FDD-Code-Information		OPTIONAL,
	e-RGCH-E-HICH-FDD-Code-Information									E-RGCH-E-HICH-FDD-Code-Information		OPTIONAL,
	iE-Extensions														ProtocolExtensionContainer { { HSDPA-And-EDCH-CellPortion-InformationItem-PSCH-ReconfRqst-ExtIEs} }	OPTIONAL,
	...
}

HSDPA-And-EDCH-CellPortion-InformationItem-PSCH-ReconfRqst-ExtIEs NBAP-PROTOCOL-EXTENSION ::= {
...
}

-- **************************************************************
--
-- PHYSICAL SHARED CHANNEL RECONFIGURATION REQUEST TDD
--
-- **************************************************************

PhysicalSharedChannelReconfigurationRequestTDD ::= SEQUENCE {
	protocolIEs			ProtocolIE-Container		{{PhysicalSharedChannelReconfigurationRequestTDD-IEs}},
	protocolExtensions	ProtocolExtensionContainer	{{PhysicalSharedChannelReconfigurationRequestTDD-Extensions}}	OPTIONAL,
	...
}

PhysicalSharedChannelReconfigurationRequestTDD-IEs NBAP-PROTOCOL-IES ::= {
	{ ID id-C-ID									CRITICALITY reject	TYPE C-ID						PRESENCE mandatory }|
	{ ID id-SFN										CRITICALITY reject	TYPE SFN						PRESENCE optional }|
	{ ID id-PDSCHSets-AddList-PSCH-ReconfRqst		CRITICALITY reject	TYPE PDSCHSets-AddList-PSCH-ReconfRqst		PRESENCE optional }|
	{ ID id-PDSCHSets-ModifyList-PSCH-ReconfRqst	CRITICALITY reject	TYPE PDSCHSets-ModifyList-PSCH-ReconfRqst		PRESENCE optional }|
	{ ID id-PDSCHSets-DeleteList-PSCH-ReconfRqst	CRITICALITY reject	TYPE PDSCHSets-DeleteList-PSCH-ReconfRqst		PRESENCE optional }|
	{ ID id-PUSCHSets-AddList-PSCH-ReconfRqst		CRITICALITY reject	TYPE PUSCHSets-AddList-PSCH-ReconfRqst		PRESENCE optional }|
	{ ID id-PUSCHSets-ModifyList-PSCH-ReconfRqst	CRITICALITY reject	TYPE PUSCHSets-ModifyList-PSCH-ReconfRqst		PRESENCE optional }|
	{ ID id-PUSCHSets-DeleteList-PSCH-ReconfRqst	CRITICALITY reject	TYPE PUSCHSets-DeleteList-PSCH-ReconfRqst		PRESENCE optional },
	...
}

PhysicalSharedChannelReconfigurationRequestTDD-Extensions NBAP-PROTOCOL-EXTENSION ::= {
	{ ID id-HS-PDSCH-TDD-Information-PSCH-ReconfRqst			CRITICALITY reject	EXTENSION HS-PDSCH-TDD-Information-PSCH-ReconfRqst			PRESENCE optional } |
	{ ID id-Add-To-HS-SCCH-Resource-Pool-PSCH-ReconfRqst		CRITICALITY reject	EXTENSION Add-To-HS-SCCH-Resource-Pool-PSCH-ReconfRqst			PRESENCE optional } |
	{ ID id-Modify-HS-SCCH-Resource-Pool-PSCH-ReconfRqst		CRITICALITY reject	EXTENSION Modify-HS-SCCH-Resource-Pool-PSCH-ReconfRqst			PRESENCE optional } |
	{ ID id-Delete-From-HS-SCCH-Resource-Pool-PSCH-ReconfRqst	CRITICALITY reject	EXTENSION Delete-From-HS-SCCH-Resource-Pool-PSCH-ReconfRqst		PRESENCE optional } |
	{ ID id-ConfigurationGenerationID						CRITICALITY reject	EXTENSION ConfigurationGenerationID				PRESENCE optional }|
	{ ID id-E-PUCH-Information-PSCH-ReconfRqst								CRITICALITY reject	EXTENSION E-PUCH-Information-PSCH-ReconfRqst														PRESENCE optional }|
	{ ID id-Add-To-E-AGCH-Resource-Pool-PSCH-ReconfRqst						CRITICALITY reject	EXTENSION Add-To-E-AGCH-Resource-Pool-PSCH-ReconfRqst					PRESENCE optional } |
	{ ID id-Modify-E-AGCH-Resource-Pool-PSCH-ReconfRqst						CRITICALITY reject	EXTENSION Modify-E-AGCH-Resource-Pool-PSCH-ReconfRqst									PRESENCE optional } |
	{ ID id-Delete-From-E-AGCH-Resource-Pool-PSCH-ReconfRqst				CRITICALITY reject	EXTENSION Delete-From-E-AGCH-Resource-Pool-PSCH-ReconfRqst									PRESENCE optional } |
	{ ID id-E-HICH-Information-PSCH-ReconfRqst								CRITICALITY reject	EXTENSION E-HICH-Information-PSCH-ReconfRqst				PRESENCE optional }|
	{ ID id-Maximum-Generated-ReceivedTotalWideBandPowerInOtherCells		CRITICALITY reject	EXTENSION Maximum-Generated-ReceivedTotalWideBandPowerInOtherCells		PRESENCE optional }|-- Applicable to 3.84Mcps TDD or 7.68Mcps TDD.
	{ ID id-E-PUCH-Information-768-PSCH-ReconfRqst							CRITICALITY reject	EXTENSION E-PUCH-Information-768-PSCH-ReconfRqst													PRESENCE optional }|
	{ ID id-Add-To-E-AGCH-Resource-Pool-768-PSCH-ReconfRqst					CRITICALITY reject	EXTENSION Add-To-E-AGCH-Resource-Pool-768-PSCH-ReconfRqst			PRESENCE optional } |
	{ ID id-Modify-E-AGCH-Resource-Pool-768-PSCH-ReconfRqst						CRITICALITY reject	EXTENSION Modify-E-AGCH-Resource-Pool-768-PSCH-ReconfRqst									PRESENCE optional } |
	{ ID id-E-HICH-Information-768-PSCH-ReconfRqst							CRITICALITY reject	EXTENSION E-HICH-Information-768-PSCH-ReconfRqst				PRESENCE optional }|
	{ ID id-E-PUCH-Information-LCR-PSCH-ReconfRqst							CRITICALITY reject	EXTENSION E-PUCH-Information-LCR-PSCH-ReconfRqst													PRESENCE optional }|
	{ ID id-Add-To-E-AGCH-Resource-Pool-LCR-PSCH-ReconfRqst					CRITICALITY reject	EXTENSION Add-To-E-AGCH-Resource-Pool-LCR-PSCH-ReconfRqst			PRESENCE optional }|
	{ ID id-Modify-E-AGCH-Resource-Pool-LCR-PSCH-ReconfRqst					CRITICALITY reject	EXTENSION Modify-E-AGCH-Resource-Pool-LCR-PSCH-ReconfRqst									PRESENCE optional }|
	{ ID id-Add-To-E-HICH-Resource-Pool-LCR-PSCH-ReconfRqst	    CRITICALITY reject	EXTENSION Add-To-E-HICH-Resource-Pool-LCR-PSCH-ReconfRqst				PRESENCE optional }|
	{ ID id-Modify-E-HICH-Resource-Pool-LCR-PSCH-ReconfRqst		CRITICALITY reject	EXTENSION Modify-E-HICH-Resource-Pool-LCR-PSCH-ReconfRqst				PRESENCE optional }|
	{ ID id-Delete-From-E-HICH-Resource-Pool-PSCH-ReconfRqst		CRITICALITY reject	EXTENSION Delete-From-E-HICH-Resource-Pool-PSCH-ReconfRqst									PRESENCE optional }|
	{ ID id-SYNC-UL-Partition-LCR											CRITICALITY reject	EXTENSION SYNC-UL-Partition-LCR															PRESENCE optional }|
	 -- Applicable to 1.28Mcps TDD, Not Applicable to 3.84Mcps TDD or 7.68Mcps TDD.
	{ ID id-Maximum-Target-ReceivedTotalWideBandPower-LCR					CRITICALITY reject	EXTENSION Maximum-Target-ReceivedTotalWideBandPower-LCR						PRESENCE optional }|
	-- Applicable to 1.28Mcps TDD only.
	{ ID id-Delete-From-HS-SCCH-Resource-PoolExt-PSCH-ReconfRqst	CRITICALITY reject		EXTENSION Delete-From-HS-SCCH-Resource-PoolExt-PSCH-ReconfRqst		PRESENCE optional }|
	-- Applicable to 1.28Mcps TDD only, used when there are more than maxNrOfHSSCCHs HS-SCCHs in the message.
	{ ID id-HSDSCH-Common-System-InformationLCR						CRITICALITY reject	EXTENSION HSDSCH-Common-System-InformationLCR				PRESENCE optional }|
	{ ID id-Common-MACFlows-to-DeleteLCR							CRITICALITY reject	EXTENSION Common-MACFlows-to-DeleteLCR									PRESENCE optional }|
	{ ID id-HSDSCH-Paging-System-InformationLCR						CRITICALITY reject	EXTENSION HSDSCH-Paging-System-InformationLCR						PRESENCE optional }|
	{ ID id-Paging-MACFlows-to-DeleteLCR							CRITICALITY reject	EXTENSION Paging-MACFlows-to-DeleteLCR									PRESENCE optional }|
	{ ID id-Common-EDCH-System-InformationLCR						CRITICALITY reject	EXTENSION Common-EDCH-System-InformationLCR							PRESENCE optional }|
	{ ID id-Common-UL-MACFlows-to-DeleteLCR							CRITICALITY reject	EXTENSION Common-MACFlows-to-DeleteLCR									PRESENCE optional }|
	{ ID id-Common-EDCH-MACdFlows-to-DeleteLCR						CRITICALITY reject	EXTENSION E-DCH-MACdFlows-to-DeleteLCR									PRESENCE optional }|
	{ ID id-Enhanced-UE-DRX-InformationLCR							CRITICALITY reject	EXTENSION Enhanced-UE-DRX-InformationLCR								PRESENCE optional },
	...
}

PDSCHSets-AddList-PSCH-ReconfRqst ::= SEQUENCE (SIZE (1..maxNrOfPDSCHSets)) OF PDSCHSets-AddItem-PSCH-ReconfRqst

PDSCHSets-AddItem-PSCH-ReconfRqst	 ::= SEQUENCE {
	pDSCHSet-ID									PDSCHSet-ID,
	pDSCH-InformationList						PDSCH-Information-AddList-PSCH-ReconfRqst 	OPTIONAL,	-- Mandatory for 3.84Mcps TDD. Not Applicable to 1.28Mcps TDD or 7.68Mcps TDD
	iE-Extensions								ProtocolExtensionContainer { {PDSCHSets-AddItem-PSCH-ReconfRqst-ExtIEs} }		OPTIONAL,
	...
}

PDSCHSets-AddItem-PSCH-ReconfRqst-ExtIEs  NBAP-PROTOCOL-EXTENSION ::= {
	{ID id-PDSCH-AddInformation-LCR-PSCH-ReconfRqst 	CRITICALITY	reject		EXTENSION 	PDSCH-AddInformation-LCR-AddItem-PSCH-ReconfRqst			PRESENCE	optional}| -- Mandatory for 1.28Mcps TDD. Not Applicable to 3.84Mcps TDD or 7.68Mcps TDD.
	{ID id-PDSCH-AddInformation-768-PSCH-ReconfRqst 	CRITICALITY	reject		EXTENSION 	PDSCH-AddInformation-768-AddItem-PSCH-ReconfRqst			PRESENCE	optional}, -- Mandatory for 7.68 Mcps TDD. Not Applicable to 3.84Mcps TDD or 1.28 Mcps TDD.
	...
}

PDSCH-Information-AddList-PSCH-ReconfRqst ::= ProtocolIE-Single-Container {{ PDSCH-Information-AddListIEs-PSCH-ReconfRqst }}
-- Mandatory for 3.84Mcps TDD, Not Applicable to 1.28Mcps TDD or 7.68Mcps TDD

PDSCH-Information-AddListIEs-PSCH-ReconfRqst	NBAP-PROTOCOL-IES ::= { 
	{ID id-PDSCH-Information-AddListIE-PSCH-ReconfRqst 	CRITICALITY	reject		TYPE 	PDSCH-Information-AddItem-PSCH-ReconfRqst			PRESENCE	mandatory}
}

PDSCH-Information-AddItem-PSCH-ReconfRqst ::= SEQUENCE {
	repetitionPeriod						RepetitionPeriod,
	repetitionLength						RepetitionLength,
	tdd-PhysicalChannelOffset				TDD-PhysicalChannelOffset,
	dL-Timeslot-InformationAddList-PSCH-ReconfRqst				DL-Timeslot-InformationAddList-PSCH-ReconfRqst,
	iE-Extensions							ProtocolExtensionContainer { {PDSCH-Information-AddItem-PSCH-ReconfRqst-ExtIEs} }		OPTIONAL,
	...
	}

PDSCH-Information-AddItem-PSCH-ReconfRqst-ExtIEs  NBAP-PROTOCOL-EXTENSION ::= {
	...
}

DL-Timeslot-InformationAddList-PSCH-ReconfRqst ::= SEQUENCE (SIZE (1.. maxNrOfDLTSs)) OF DL-Timeslot-InformationAddItem-PSCH-ReconfRqst

DL-Timeslot-InformationAddItem-PSCH-ReconfRqst ::= SEQUENCE {
	timeSlot								TimeSlot,
	midambleShiftAndBurstType				MidambleShiftAndBurstType,
	tFCI-Presence							TFCI-Presence,
	dL-Code-InformationAddList-PSCH-ReconfRqst				DL-Code-InformationAddList-PSCH-ReconfRqst,
	iE-Extensions							ProtocolExtensionContainer { { DL-Timeslot-InformationAddItem-PSCH-ReconfRqst-ExtIEs} }		OPTIONAL,
	...
}

DL-Timeslot-InformationAddItem-PSCH-ReconfRqst-ExtIEs NBAP-PROTOCOL-EXTENSION ::= {
	...
}

DL-Code-InformationAddList-PSCH-ReconfRqst ::= SEQUENCE (SIZE (1..maxNrOfPDSCHs)) OF DL-Code-InformationAddItem-PSCH-ReconfRqst

DL-Code-InformationAddItem-PSCH-ReconfRqst ::= SEQUENCE {
	pDSCH-ID								PDSCH-ID,
	tdd-ChannelisationCode					TDD-ChannelisationCode,
	iE-Extensions							ProtocolExtensionContainer { { DL-Code-InformationAddItem-PSCH-ReconfRqst-ExtIEs} }		OPTIONAL,
	...
}

DL-Code-InformationAddItem-PSCH-ReconfRqst-ExtIEs NBAP-PROTOCOL-EXTENSION ::= {
	...
}

PDSCH-AddInformation-LCR-AddItem-PSCH-ReconfRqst ::= SEQUENCE {
	repetitionPeriod						RepetitionPeriod,
	repetitionLength						RepetitionLength,
	tdd-PhysicalChannelOffset				TDD-PhysicalChannelOffset,
	dL-Timeslot-InformationAddList-LCR-PSCH-ReconfRqst				DL-Timeslot-InformationAddList-LCR-PSCH-ReconfRqst,
	iE-Extensions								ProtocolExtensionContainer { {PDSCH-AddInformation-LCR-AddItem-PSCH-ReconfRqst-ExtIEs} }		OPTIONAL,
	...
	}

PDSCH-AddInformation-LCR-AddItem-PSCH-ReconfRqst-ExtIEs  NBAP-PROTOCOL-EXTENSION ::= {
{ID	id-Tstd-indicator			CRITICALITY	reject		EXTENSION 	TSTD-Indicator		PRESENCE 	optional	},
	-- Applicable to 1.28Mcps TDD only
	...
}

DL-Timeslot-InformationAddList-LCR-PSCH-ReconfRqst ::= SEQUENCE (SIZE (1.. maxNrOfDLTSLCRs)) OF DL-Timeslot-InformationAddItem-LCR-PSCH-ReconfRqst

DL-Timeslot-InformationAddItem-LCR-PSCH-ReconfRqst ::= SEQUENCE {
	timeSlotLCR								TimeSlotLCR,
	midambleShiftLCR						MidambleShiftLCR,
	tFCI-Presence							TFCI-Presence,
	dL-Code-InformationAddList-LCR-PSCH-ReconfRqst				DL-Code-InformationAddList-LCR-PSCH-ReconfRqst,
	iE-Extensions							ProtocolExtensionContainer { { DL-Timeslot-InformationAddItem-LCR-PSCH-ReconfRqst-ExtIEs} }		OPTIONAL,
	...
}

DL-Timeslot-InformationAddItem-LCR-PSCH-ReconfRqst-ExtIEs NBAP-PROTOCOL-EXTENSION ::= {
	...
}

DL-Code-InformationAddList-LCR-PSCH-ReconfRqst ::= SEQUENCE (SIZE (1..maxNrOfPDSCHs)) OF DL-Code-InformationAddItem-LCR-PSCH-ReconfRqst

DL-Code-InformationAddItem-LCR-PSCH-ReconfRqst ::= SEQUENCE {
	pDSCH-ID								PDSCH-ID,
	tdd-ChannelisationCodeLCR				TDD-ChannelisationCodeLCR,
	iE-Extensions							ProtocolExtensionContainer { { DL-Code-InformationAddItem-LCR-PSCH-ReconfRqst-ExtIEs} }		OPTIONAL,
	...
}

DL-Code-InformationAddItem-LCR-PSCH-ReconfRqst-ExtIEs NBAP-PROTOCOL-EXTENSION ::= {
	{ID id-PDSCH-Timeslot-Format-PSCH-ReconfRqst-LCR	CRITICALITY reject		EXTENSION TDD-DL-DPCH-TimeSlotFormat-LCR		PRESENCE optional},
	...
}

PDSCH-AddInformation-768-AddItem-PSCH-ReconfRqst ::= SEQUENCE {
	repetitionPeriod						RepetitionPeriod,
	repetitionLength						RepetitionLength,
	tdd-PhysicalChannelOffset				TDD-PhysicalChannelOffset,
	dL-Timeslot-InformationAddList-768-PSCH-ReconfRqst				DL-Timeslot-InformationAddList-768-PSCH-ReconfRqst,
	iE-Extensions								ProtocolExtensionContainer { {PDSCH-AddInformation-768-AddItem-PSCH-ReconfRqst-ExtIEs} }		OPTIONAL,
	...
	}

PDSCH-AddInformation-768-AddItem-PSCH-ReconfRqst-ExtIEs  NBAP-PROTOCOL-EXTENSION ::= {
	...
}

DL-Timeslot-InformationAddList-768-PSCH-ReconfRqst ::= SEQUENCE (SIZE (1.. maxNrOfDLTSs)) OF DL-Timeslot-InformationAddItem-768-PSCH-ReconfRqst

DL-Timeslot-InformationAddItem-768-PSCH-ReconfRqst ::= SEQUENCE {
	timeSlot								TimeSlot,
	midambleShiftAndBurstType768			MidambleShiftAndBurstType768,
	tFCI-Presence							TFCI-Presence,
	dL-Code-InformationAddList-768-PSCH-ReconfRqst				DL-Code-InformationAddList-768-PSCH-ReconfRqst,
	iE-Extensions							ProtocolExtensionContainer { { DL-Timeslot-InformationAddItem-768-PSCH-ReconfRqst-ExtIEs} }		OPTIONAL,
	...
}

DL-Timeslot-InformationAddItem-768-PSCH-ReconfRqst-ExtIEs NBAP-PROTOCOL-EXTENSION ::= {
	...
}

DL-Code-InformationAddList-768-PSCH-ReconfRqst ::= SEQUENCE (SIZE (1..maxNrOfPDSCHs)) OF DL-Code-InformationAddItem-768-PSCH-ReconfRqst

DL-Code-InformationAddItem-768-PSCH-ReconfRqst ::= SEQUENCE {
	pDSCH-ID768								PDSCH-ID768,
	tdd-ChannelisationCode768				TDD-ChannelisationCode768,
	iE-Extensions							ProtocolExtensionContainer { { DL-Code-InformationAddItem-768-PSCH-ReconfRqst-ExtIEs} }		OPTIONAL,
	...
}

DL-Code-InformationAddItem-768-PSCH-ReconfRqst-ExtIEs NBAP-PROTOCOL-EXTENSION ::= {
	...
}

PDSCHSets-ModifyList-PSCH-ReconfRqst ::= SEQUENCE (SIZE (1..maxNrOfPDSCHSets)) OF PDSCHSets-ModifyItem-PSCH-ReconfRqst

PDSCHSets-ModifyItem-PSCH-ReconfRqst	 ::= SEQUENCE {
	pDSCHSet-ID									PDSCHSet-ID,
	pDSCH-InformationList						PDSCH-Information-ModifyList-PSCH-ReconfRqst,
	iE-Extensions								ProtocolExtensionContainer { {PDSCHSets-ModifyItem-PSCH-ReconfRqst-ExtIEs} }		OPTIONAL,
	...
}

PDSCHSets-ModifyItem-PSCH-ReconfRqst-ExtIEs  NBAP-PROTOCOL-EXTENSION ::= {
	{ID id-PDSCH-ModifyInformation-768-PSCH-ReconfRqst 	CRITICALITY	reject		EXTENSION 	PDSCH-ModifyInformation-768-ModifyItem-PSCH-ReconfRqst			PRESENCE	optional}, -- For 7.68 Mcps TDD. Not Applicable to 3.84Mcps TDD or 1.28 Mcps TDD.
	...
}

PDSCH-Information-ModifyList-PSCH-ReconfRqst ::= ProtocolIE-Single-Container {{ PDSCH-Information-ModifyListIEs-PSCH-ReconfRqst }}

PDSCH-Information-ModifyListIEs-PSCH-ReconfRqst NBAP-PROTOCOL-IES ::= {
	{ID id-PDSCH-Information-ModifyListIE-PSCH-ReconfRqst	CRITICALITY reject	TYPE PDSCH-Information-ModifyItem-PSCH-ReconfRqst			PRESENCE	optional}|
	{ID id-PDSCH-ModifyInformation-LCR-PSCH-ReconfRqst		CRITICALITY reject	TYPE PDSCH-ModifyInformation-LCR-ModifyItem-PSCH-ReconfRqst			PRESENCE	optional}
}

PDSCH-Information-ModifyItem-PSCH-ReconfRqst ::= SEQUENCE {
	repetitionPeriod									RepetitionPeriod								OPTIONAL,
	repetitionLength									RepetitionLength								OPTIONAL,
	tdd-PhysicalChannelOffset							TDD-PhysicalChannelOffset						OPTIONAL,
	dL-Timeslot-InformationModifyList-PSCH-ReconfRqst	DL-Timeslot-InformationModifyList-PSCH-ReconfRqst		OPTIONAL,
	iE-Extensions								ProtocolExtensionContainer { {PDSCH-Information-ModifyItem-PSCH-ReconfRqst-ExtIEs} }		OPTIONAL,
	...
}

PDSCH-Information-ModifyItem-PSCH-ReconfRqst-ExtIEs  NBAP-PROTOCOL-EXTENSION ::= {
	...
}

DL-Timeslot-InformationModifyList-PSCH-ReconfRqst ::= SEQUENCE (SIZE (1.. maxNrOfDLTSs)) OF DL-Timeslot-InformationModifyItem-PSCH-ReconfRqst

DL-Timeslot-InformationModifyItem-PSCH-ReconfRqst ::= SEQUENCE {
	timeSlot										TimeSlot,
	midambleShiftAndBurstType						MidambleShiftAndBurstType							OPTIONAL,
	tFCI-Presence									TFCI-Presence										OPTIONAL,
	dL-Code-InformationModifyList-PSCH-ReconfRqst				DL-Code-InformationModifyList-PSCH-ReconfRqst		OPTIONAL,
	iE-Extensions							ProtocolExtensionContainer { { DL-Timeslot-InformationModifyItem-PSCH-ReconfRqst-ExtIEs} }		OPTIONAL,
	...
}

DL-Timeslot-InformationModifyItem-PSCH-ReconfRqst-ExtIEs NBAP-PROTOCOL-EXTENSION ::= {
	...
}

DL-Code-InformationModifyList-PSCH-ReconfRqst ::= SEQUENCE (SIZE (1..maxNrOfPDSCHs)) OF DL-Code-InformationModifyItem-PSCH-ReconfRqst

DL-Code-InformationModifyItem-PSCH-ReconfRqst ::= SEQUENCE {
	pDSCH-ID								PDSCH-ID,
	tdd-ChannelisationCode					TDD-ChannelisationCode,
	iE-Extensions							ProtocolExtensionContainer { { DL-Code-InformationModifyItem-PSCH-ReconfRqst-ExtIEs} }		OPTIONAL,
	...
}

DL-Code-InformationModifyItem-PSCH-ReconfRqst-ExtIEs NBAP-PROTOCOL-EXTENSION ::= {
	...
}

PDSCH-ModifyInformation-LCR-ModifyItem-PSCH-ReconfRqst ::= SEQUENCE {
	repetitionPeriod											RepetitionPeriod							OPTIONAL,
	repetitionLength											RepetitionLength							OPTIONAL,
	tdd-PhysicalChannelOffset									TDD-PhysicalChannelOffset					OPTIONAL,
	dL-Timeslot-LCR-InformationModifyList-PSCH-ReconfRqst		DL-Timeslot-LCR-InformationModifyList-PSCH-ReconfRqst		OPTIONAL,
	iE-Extensions								ProtocolExtensionContainer { {PDSCH-ModifyInformation-LCR-ModifyListIE-PSCH-ReconfRqst-ExtIEs} }		OPTIONAL,
	...
}

PDSCH-ModifyInformation-LCR-ModifyListIE-PSCH-ReconfRqst-ExtIEs NBAP-PROTOCOL-EXTENSION ::= {
	...
}

DL-Timeslot-LCR-InformationModifyList-PSCH-ReconfRqst ::= SEQUENCE (SIZE (1.. maxNrOfDLTSLCRs)) OF DL-Timeslot-LCR-InformationModifyItem-PSCH-ReconfRqst

DL-Timeslot-LCR-InformationModifyItem-PSCH-ReconfRqst ::= SEQUENCE {
	timeSlotLCR												TimeSlotLCR,
	midambleShiftLCR										MidambleShiftLCR							OPTIONAL,
	tFCI-Presence											TFCI-Presence								OPTIONAL,
	dL-Code-LCR-InformationModifyList-PSCH-ReconfRqst		DL-Code-LCR-InformationModifyList-PSCH-ReconfRqst		OPTIONAL,
	iE-Extensions							ProtocolExtensionContainer { { DL-Timeslot-LCR-InformationModifyItem-PSCH-ReconfRqst-ExtIEs} }		OPTIONAL,
	...
}

DL-Timeslot-LCR-InformationModifyItem-PSCH-ReconfRqst-ExtIEs NBAP-PROTOCOL-EXTENSION ::= {
	...
}

DL-Code-LCR-InformationModifyList-PSCH-ReconfRqst ::= SEQUENCE (SIZE (1..maxNrOfPDSCHs)) OF DL-Code-LCR-InformationModifyItem-PSCH-ReconfRqst

DL-Code-LCR-InformationModifyItem-PSCH-ReconfRqst ::= SEQUENCE {
	pDSCH-ID								PDSCH-ID,
	tdd-ChannelisationCodeLCR				TDD-ChannelisationCodeLCR,
	iE-Extensions							ProtocolExtensionContainer { { DL-Code-LCR-InformationModifyItem-PSCH-ReconfRqst-ExtIEs} }		OPTIONAL,
	...
}

DL-Code-LCR-InformationModifyItem-PSCH-ReconfRqst-ExtIEs NBAP-PROTOCOL-EXTENSION ::= {
	{ID id-PDSCH-Timeslot-Format-PSCH-ReconfRqst-LCR	CRITICALITY reject		EXTENSION TDD-DL-DPCH-TimeSlotFormat-LCR		PRESENCE optional},
	...
}


PDSCH-ModifyInformation-768-ModifyItem-PSCH-ReconfRqst ::= SEQUENCE {
	repetitionPeriod											RepetitionPeriod							OPTIONAL,
	repetitionLength											RepetitionLength							OPTIONAL,
	tdd-PhysicalChannelOffset									TDD-PhysicalChannelOffset					OPTIONAL,
	dL-Timeslot-768-InformationModifyList-PSCH-ReconfRqst		DL-Timeslot-768-InformationModifyList-PSCH-ReconfRqst		OPTIONAL,
	iE-Extensions								ProtocolExtensionContainer { {PDSCH-ModifyInformation-768-ModifyListIE-PSCH-ReconfRqst-ExtIEs} }		OPTIONAL,
	...
	}

PDSCH-ModifyInformation-768-ModifyListIE-PSCH-ReconfRqst-ExtIEs NBAP-PROTOCOL-EXTENSION ::= {
	...
}

DL-Timeslot-768-InformationModifyList-PSCH-ReconfRqst ::= SEQUENCE (SIZE (1.. maxNrOfDLTSs)) OF DL-Timeslot-768-InformationModifyItem-PSCH-ReconfRqst

DL-Timeslot-768-InformationModifyItem-PSCH-ReconfRqst ::= SEQUENCE {
	timeSlot												TimeSlot,
	midambleShiftAndBurstType768							MidambleShiftAndBurstType768										OPTIONAL,
	tFCI-Presence											TFCI-Presence														OPTIONAL,
	dL-Code-768-InformationModifyList-PSCH-ReconfRqst		DL-Code-768-InformationModifyList-PSCH-ReconfRqst							OPTIONAL,
	iE-Extensions							ProtocolExtensionContainer { { DL-Timeslot-768-InformationModifyItem-PSCH-ReconfRqst-ExtIEs} }		OPTIONAL,
	...
}

DL-Timeslot-768-InformationModifyItem-PSCH-ReconfRqst-ExtIEs NBAP-PROTOCOL-EXTENSION ::= {
	...
}

DL-Code-768-InformationModifyList-PSCH-ReconfRqst ::= SEQUENCE (SIZE (1..maxNrOfPDSCHs)) OF DL-Code-768-InformationModifyItem-PSCH-ReconfRqst

DL-Code-768-InformationModifyItem-PSCH-ReconfRqst ::= SEQUENCE {
	pDSCH-ID768								PDSCH-ID768,
	tdd-ChannelisationCode768				TDD-ChannelisationCode768,
	iE-Extensions							ProtocolExtensionContainer { { DL-Code-768-InformationModifyItem-PSCH-ReconfRqst-ExtIEs} }		OPTIONAL,
	...
}

DL-Code-768-InformationModifyItem-PSCH-ReconfRqst-ExtIEs NBAP-PROTOCOL-EXTENSION ::= {
	...
}

PDSCHSets-DeleteList-PSCH-ReconfRqst ::= SEQUENCE (SIZE (1..maxNrOfPDSCHSets)) OF PDSCHSets-DeleteItem-PSCH-ReconfRqst

PDSCHSets-DeleteItem-PSCH-ReconfRqst	 ::= SEQUENCE {
	pDSCHSet-ID									PDSCHSet-ID,
	iE-Extensions								ProtocolExtensionContainer { {PDSCHSets-DeleteItem-PSCH-ReconfRqst-ExtIEs} }		OPTIONAL,
	...
}

PDSCHSets-DeleteItem-PSCH-ReconfRqst-ExtIEs  NBAP-PROTOCOL-EXTENSION ::= {
	...
}

PUSCHSets-AddList-PSCH-ReconfRqst ::= SEQUENCE (SIZE (1..maxNrOfPUSCHSets)) OF PUSCHSets-AddItem-PSCH-ReconfRqst

PUSCHSets-AddItem-PSCH-ReconfRqst	 ::= SEQUENCE {
	pUSCHSet-ID									PUSCHSet-ID,
	pUSCH-InformationList						PUSCH-Information-AddList-PSCH-ReconfRqst 	OPTIONAL,
	-- Mandatory for 3.84Mcps TDD, Not Applicable to 1.28Mcps TDD or 7.68Mcps TDD
	iE-Extensions								ProtocolExtensionContainer { {PUSCHSets-AddItem-PSCH-ReconfRqst-ExtIEs} }		OPTIONAL,
	...
}

PUSCHSets-AddItem-PSCH-ReconfRqst-ExtIEs  NBAP-PROTOCOL-EXTENSION ::= {
	{ ID id-PUSCH-AddInformation-LCR-PSCH-ReconfRqst	CRITICALITY	reject		EXTENSION 	PUSCH-AddInformation-LCR-AddItem-PSCH-ReconfRqst			PRESENCE	optional}|	-- Mandatory for 1.28Mcps TDD, Not Applicable to 3.84Mcps TDD or 7.68Mcps TDD
	{ ID id-PUSCH-AddInformation-768-PSCH-ReconfRqst 	CRITICALITY reject		EXTENSION PUSCH-AddInformation-768-AddItem-PSCH-ReconfRqst			PRESENCE optional}, -- Mandatory for 7.68 Mcps TDD. Not Applicable to 3.84Mcps TDD or 1.28 Mcps TDD.
	...
}

PUSCH-Information-AddList-PSCH-ReconfRqst ::=  ProtocolIE-Single-Container {{ PUSCH-Information-AddListIEs-PSCH-ReconfRqst }}

PUSCH-Information-AddListIEs-PSCH-ReconfRqst NBAP-PROTOCOL-IES ::= {
	{ ID id-PUSCH-Information-AddListIE-PSCH-ReconfRqst	CRITICALITY	reject	TYPE PUSCH-Information-AddItem-PSCH-ReconfRqst		PRESENCE mandatory }
}

PUSCH-Information-AddItem-PSCH-ReconfRqst ::= SEQUENCE {
	repetitionPeriod								RepetitionPeriod,
	repetitionLength								RepetitionLength,
	tdd-PhysicalChannelOffset						TDD-PhysicalChannelOffset,
	uL-Timeslot-InformationAddList-PSCH-ReconfRqst	UL-Timeslot-InformationAddList-PSCH-ReconfRqst,
	iE-Extensions									ProtocolExtensionContainer { {PUSCH-Information-AddItem-PSCH-ReconfRqst-ExtIEs} }		OPTIONAL,
	...
}

PUSCH-Information-AddItem-PSCH-ReconfRqst-ExtIEs  NBAP-PROTOCOL-EXTENSION ::= {
	...
}

UL-Timeslot-InformationAddList-PSCH-ReconfRqst ::= SEQUENCE (SIZE (1..maxNrOfULTSs)) OF UL-Timeslot-InformationAddItem-PSCH-ReconfRqst

UL-Timeslot-InformationAddItem-PSCH-ReconfRqst ::= SEQUENCE {
	timeSlot									TimeSlot,
	midambleShiftAndBurstType					MidambleShiftAndBurstType,
	tFCI-Presence								TFCI-Presence,
	uL-Code-InformationAddList-PSCH-ReconfRqst	UL-Code-InformationAddList-PSCH-ReconfRqst,
	iE-Extensions								ProtocolExtensionContainer { { UL-Timeslot-InformationAddItem-PSCH-ReconfRqst-ExtIEs} }		OPTIONAL,
	...
}

UL-Timeslot-InformationAddItem-PSCH-ReconfRqst-ExtIEs NBAP-PROTOCOL-EXTENSION ::= {
	...
}

UL-Code-InformationAddList-PSCH-ReconfRqst ::= SEQUENCE (SIZE (1..maxNrOfPUSCHs)) OF UL-Code-InformationAddItem-PSCH-ReconfRqst

UL-Code-InformationAddItem-PSCH-ReconfRqst ::= SEQUENCE {
	pUSCH-ID								PUSCH-ID,
	tdd-ChannelisationCode					TDD-ChannelisationCode,
	iE-Extensions							ProtocolExtensionContainer { { UL-Code-InformationAddItem-PSCH-ReconfRqst-ExtIEs} }		OPTIONAL,
	...
}

UL-Code-InformationAddItem-PSCH-ReconfRqst-ExtIEs NBAP-PROTOCOL-EXTENSION ::= {
	...
}

PUSCH-AddInformation-LCR-AddItem-PSCH-ReconfRqst ::= SEQUENCE {
	repetitionPeriod									RepetitionPeriod,
	repetitionLength									RepetitionLength,
	tdd-PhysicalChannelOffset							TDD-PhysicalChannelOffset,
	uL-Timeslot-InformationAddList-LCR-PSCH-ReconfRqst	UL-Timeslot-InformationAddList-LCR-PSCH-ReconfRqst,
	iE-Extensions								ProtocolExtensionContainer { {PUSCH-AddInformation-LCR-AddItem-PSCH-ReconfRqst-ExtIEs} }		OPTIONAL,
	...
}

PUSCH-AddInformation-LCR-AddItem-PSCH-ReconfRqst-ExtIEs  NBAP-PROTOCOL-EXTENSION ::= {
	...
}

UL-Timeslot-InformationAddList-LCR-PSCH-ReconfRqst ::= SEQUENCE (SIZE (1.. maxNrOfULTSLCRs)) OF UL-Timeslot-InformationAddItem-LCR-PSCH-ReconfRqst

UL-Timeslot-InformationAddItem-LCR-PSCH-ReconfRqst ::= SEQUENCE {
	timeSlotLCR										TimeSlotLCR,
	midambleShiftLCR								MidambleShiftLCR,
	tFCI-Presence									TFCI-Presence,
	uL-Code-InformationAddList-LCR-PSCH-ReconfRqst	UL-Code-InformationAddList-LCR-PSCH-ReconfRqst,
	iE-Extensions							ProtocolExtensionContainer { { UL-Timeslot-InformationAddItem-LCR-PSCH-ReconfRqst-ExtIEs} }		OPTIONAL,
	...
}

UL-Timeslot-InformationAddItem-LCR-PSCH-ReconfRqst-ExtIEs NBAP-PROTOCOL-EXTENSION ::= {
	...
}

UL-Code-InformationAddList-LCR-PSCH-ReconfRqst ::= SEQUENCE (SIZE (1..maxNrOfPUSCHs)) OF UL-Code-InformationAddItem-LCR-PSCH-ReconfRqst

UL-Code-InformationAddItem-LCR-PSCH-ReconfRqst ::= SEQUENCE {
	pUSCH-ID								PUSCH-ID,
	tdd-ChannelisationCodeLCR				TDD-ChannelisationCodeLCR,
	iE-Extensions							ProtocolExtensionContainer { { UL-Code-InformationAddItem-LCR-PSCH-ReconfRqst-ExtIEs} }		OPTIONAL,
	...
}

UL-Code-InformationAddItem-LCR-PSCH-ReconfRqst-ExtIEs NBAP-PROTOCOL-EXTENSION ::= {
	{ID id-PUSCH-Timeslot-Format-PSCH-ReconfRqst-LCR	CRITICALITY reject		EXTENSION TDD-UL-DPCH-TimeSlotFormat-LCR		PRESENCE optional},
	...
}

PUSCH-AddInformation-768-AddItem-PSCH-ReconfRqst ::= SEQUENCE {
	repetitionPeriod									RepetitionPeriod,
	repetitionLength									RepetitionLength,
	tdd-PhysicalChannelOffset							TDD-PhysicalChannelOffset,
	uL-Timeslot-InformationAddList-768-PSCH-ReconfRqst	UL-Timeslot-InformationAddList-768-PSCH-ReconfRqst,
	iE-Extensions								ProtocolExtensionContainer { {PUSCH-AddInformation-768-AddItem-PSCH-ReconfRqst-ExtIEs} }		OPTIONAL,
	...
}

PUSCH-AddInformation-768-AddItem-PSCH-ReconfRqst-ExtIEs  NBAP-PROTOCOL-EXTENSION ::= {
	...
}

UL-Timeslot-InformationAddList-768-PSCH-ReconfRqst ::= SEQUENCE (SIZE (1.. maxNrOfULTSs)) OF UL-Timeslot-InformationAddItem-768-PSCH-ReconfRqst

UL-Timeslot-InformationAddItem-768-PSCH-ReconfRqst ::= SEQUENCE {
	timeSlot										TimeSlot,
	midambleShiftAndBurstType768					MidambleShiftAndBurstType768,
	tFCI-Presence									TFCI-Presence,
	uL-Code-InformationAddList-768-PSCH-ReconfRqst	UL-Code-InformationAddList-768-PSCH-ReconfRqst,
	iE-Extensions							ProtocolExtensionContainer { { UL-Timeslot-InformationAddItem-768-PSCH-ReconfRqst-ExtIEs} }		OPTIONAL,
	...
}

UL-Timeslot-InformationAddItem-768-PSCH-ReconfRqst-ExtIEs NBAP-PROTOCOL-EXTENSION ::= {
	...
}

UL-Code-InformationAddList-768-PSCH-ReconfRqst ::= SEQUENCE (SIZE (1..maxNrOfPUSCHs)) OF UL-Code-InformationAddItem-768-PSCH-ReconfRqst

UL-Code-InformationAddItem-768-PSCH-ReconfRqst ::= SEQUENCE {
	pUSCH-ID								PUSCH-ID,
	tdd-ChannelisationCode768				TDD-ChannelisationCode768,
	iE-Extensions							ProtocolExtensionContainer { { UL-Code-InformationAddItem-768-PSCH-ReconfRqst-ExtIEs} }		OPTIONAL,
	...
}

UL-Code-InformationAddItem-768-PSCH-ReconfRqst-ExtIEs NBAP-PROTOCOL-EXTENSION ::= {
	...
}

PUSCHSets-ModifyList-PSCH-ReconfRqst ::= SEQUENCE (SIZE (1..maxNrOfPUSCHSets)) OF PUSCHSets-ModifyItem-PSCH-ReconfRqst

PUSCHSets-ModifyItem-PSCH-ReconfRqst	 ::= SEQUENCE {
	pUSCHSet-ID									PUSCHSet-ID,
	pUSCH-InformationList						PUSCH-Information-ModifyList-PSCH-ReconfRqst,
	iE-Extensions								ProtocolExtensionContainer { {PUSCHSets-ModifyItem-PSCH-ReconfRqst-ExtIEs} }		OPTIONAL,
	...
}

PUSCHSets-ModifyItem-PSCH-ReconfRqst-ExtIEs  NBAP-PROTOCOL-EXTENSION ::= {
	{ID id-PUSCH-ModifyInformation-768-PSCH-ReconfRqst 	CRITICALITY	reject		EXTENSION 	PUSCH-ModifyInformation-768-ModifyItem-PSCH-ReconfRqst			PRESENCE	optional}, -- For 7.68 Mcps TDD. Not Applicable to 3.84Mcps TDD or 1.28 Mcps TDD.
	...
}

PUSCH-Information-ModifyList-PSCH-ReconfRqst ::= ProtocolIE-Single-Container {{ PUSCH-Information-ModifyListIEs-PSCH-ReconfRqst }}	

PUSCH-Information-ModifyListIEs-PSCH-ReconfRqst NBAP-PROTOCOL-IES ::= {
	{ID id-PUSCH-Information-ModifyListIE-PSCH-ReconfRqst	CRITICALITY reject		TYPE PUSCH-Information-ModifyItem-PSCH-ReconfRqst			PRESENCE	optional}|
	{ID id-PUSCH-ModifyInformation-LCR-PSCH-ReconfRqst		CRITICALITY reject		TYPE PUSCH-ModifyInformation-LCR-ModifyItem-PSCH-ReconfRqst			PRESENCE	optional}
}

PUSCH-Information-ModifyItem-PSCH-ReconfRqst ::= SEQUENCE {
	repetitionPeriod									RepetitionPeriod							OPTIONAL,
	repetitionLength									RepetitionLength							OPTIONAL,
	tdd-PhysicalChannelOffset							TDD-PhysicalChannelOffset			OPTIONAL,
	uL-Timeslot-InformationModifyList-PSCH-ReconfRqst	UL-Timeslot-InformationModifyList-PSCH-ReconfRqst		OPTIONAL,
	iE-Extensions								ProtocolExtensionContainer { {PUSCH-Information-ModifyItem-PSCH-ReconfRqst-ExtIEs} }		OPTIONAL,
	...
}

PUSCH-Information-ModifyItem-PSCH-ReconfRqst-ExtIEs  NBAP-PROTOCOL-EXTENSION ::= {
	...
}

UL-Timeslot-InformationModifyList-PSCH-ReconfRqst ::= SEQUENCE (SIZE (1..maxNrOfULTSs)) OF UL-Timeslot-InformationModifyItem-PSCH-ReconfRqst

UL-Timeslot-InformationModifyItem-PSCH-ReconfRqst ::= SEQUENCE {
	timeSlot										TimeSlot,
	midambleShiftAndBurstType						MidambleShiftAndBurstType						OPTIONAL,
	tFCI-Presence									TFCI-Presence									OPTIONAL,
	uL-Code-InformationModifyList-PSCH-ReconfRqst	UL-Code-InformationModifyList-PSCH-ReconfRqst		OPTIONAL,
	iE-Extensions							ProtocolExtensionContainer { { UL-Timeslot-InformationModifyItem-PSCH-ReconfRqst-ExtIEs} }		OPTIONAL,
	...
}

UL-Timeslot-InformationModifyItem-PSCH-ReconfRqst-ExtIEs NBAP-PROTOCOL-EXTENSION ::= {
	...
}

UL-Code-InformationModifyList-PSCH-ReconfRqst ::= SEQUENCE (SIZE (1..maxNrOfPUSCHs)) OF UL-Code-InformationModifyItem-PSCH-ReconfRqst

UL-Code-InformationModifyItem-PSCH-ReconfRqst ::= SEQUENCE {
	pUSCH-ID								PUSCH-ID,
	tdd-ChannelisationCode					TDD-ChannelisationCode,
	iE-Extensions							ProtocolExtensionContainer { { UL-Code-InformationModifyItem-PSCH-ReconfRqst-ExtIEs} }		OPTIONAL,
	...
}

UL-Code-InformationModifyItem-PSCH-ReconfRqst-ExtIEs NBAP-PROTOCOL-EXTENSION ::= {
	...
}

PUSCH-ModifyInformation-LCR-ModifyItem-PSCH-ReconfRqst ::= SEQUENCE {
	repetitionPeriod										RepetitionPeriod						OPTIONAL,
	repetitionLength										RepetitionLength						OPTIONAL,
	tdd-PhysicalChannelOffset								TDD-PhysicalChannelOffset				OPTIONAL,
	uL-Timeslot-InformationModifyList-LCR-PSCH-ReconfRqst	UL-Timeslot-LCR-InformationModifyList-PSCH-ReconfRqst	OPTIONAL,
	iE-Extensions								ProtocolExtensionContainer { {PUSCH-ModifyInformation-LCR-ModifyItem-PSCH-ReconfRqst-ExtIEs} }		OPTIONAL,
	...
}

PUSCH-ModifyInformation-LCR-ModifyItem-PSCH-ReconfRqst-ExtIEs  NBAP-PROTOCOL-EXTENSION ::= {
	...
}

UL-Timeslot-LCR-InformationModifyList-PSCH-ReconfRqst ::= SEQUENCE (SIZE (1..maxNrOfULTSLCRs)) OF UL-Timeslot-LCR-InformationModifyItem-PSCH-ReconfRqst

UL-Timeslot-LCR-InformationModifyItem-PSCH-ReconfRqst ::= SEQUENCE {
	timeSlotLCR											TimeSlotLCR,
	midambleShiftLCR									MidambleShiftLCR 							OPTIONAL,
	tFCI-Presence										TFCI-Presence								OPTIONAL,
	uL-Code-LCR-InformationModifyList-PSCH-ReconfRqst	UL-Code-LCR-InformationModifyList-PSCH-ReconfRqst	OPTIONAL,
	iE-Extensions							ProtocolExtensionContainer { { UL-Timeslot-LCR-InformationModifyItem-PSCH-ReconfRqst-ExtIEs} }		OPTIONAL,
	...
}

UL-Timeslot-LCR-InformationModifyItem-PSCH-ReconfRqst-ExtIEs NBAP-PROTOCOL-EXTENSION ::= {
	...
}

UL-Code-LCR-InformationModifyList-PSCH-ReconfRqst ::= SEQUENCE (SIZE (1..maxNrOfPUSCHs)) OF UL-Code-LCR-InformationModifyItem-PSCH-ReconfRqst

UL-Code-LCR-InformationModifyItem-PSCH-ReconfRqst ::= SEQUENCE {
	pUSCH-ID								PUSCH-ID,
	tdd-ChannelisationCodeLCR				TDD-ChannelisationCodeLCR,
	iE-Extensions							ProtocolExtensionContainer { { UL-Code-LCR-InformationModifyItem-PSCH-ReconfRqst-ExtIEs} }		OPTIONAL,
	...
}

UL-Code-LCR-InformationModifyItem-PSCH-ReconfRqst-ExtIEs NBAP-PROTOCOL-EXTENSION ::= {
	{ ID id-PUSCH-Timeslot-Format-PSCH-ReconfRqst-LCR	CRITICALITY reject		EXTENSION TDD-UL-DPCH-TimeSlotFormat-LCR		PRESENCE optional},
	...
}

PUSCH-ModifyInformation-768-ModifyItem-PSCH-ReconfRqst ::= SEQUENCE {
	repetitionPeriod										RepetitionPeriod						OPTIONAL,
	repetitionLength										RepetitionLength						OPTIONAL,
	tdd-PhysicalChannelOffset								TDD-PhysicalChannelOffset				OPTIONAL,
	uL-Timeslot-InformationModifyList-768-PSCH-ReconfRqst	UL-Timeslot-768-InformationModifyList-PSCH-ReconfRqst	OPTIONAL,
	iE-Extensions								ProtocolExtensionContainer { {PUSCH-ModifyInformation-768-ModifyItem-PSCH-ReconfRqst-ExtIEs} }		OPTIONAL,
	...
}

PUSCH-ModifyInformation-768-ModifyItem-PSCH-ReconfRqst-ExtIEs  NBAP-PROTOCOL-EXTENSION ::= {
	...
}

UL-Timeslot-768-InformationModifyList-PSCH-ReconfRqst ::= SEQUENCE (SIZE (1..maxNrOfULTSs)) OF UL-Timeslot-768-InformationModifyItem-PSCH-ReconfRqst

UL-Timeslot-768-InformationModifyItem-PSCH-ReconfRqst ::= SEQUENCE {
	timeSlot											TimeSlot,
	midambleShiftAndBurstType768						MidambleShiftAndBurstType768								OPTIONAL,
	tFCI-Presence										TFCI-Presence																		OPTIONAL,
	uL-Code-768-InformationModifyList-PSCH-ReconfRqst	UL-Code-768-InformationModifyList-PSCH-ReconfRqst	OPTIONAL,
	iE-Extensions							ProtocolExtensionContainer { { UL-Timeslot-768-InformationModifyItem-PSCH-ReconfRqst-ExtIEs} }		OPTIONAL,
	...
}

UL-Timeslot-768-InformationModifyItem-PSCH-ReconfRqst-ExtIEs NBAP-PROTOCOL-EXTENSION ::= {
	...
}

UL-Code-768-InformationModifyList-PSCH-ReconfRqst ::= SEQUENCE (SIZE (1..maxNrOfPUSCHs)) OF UL-Code-768-InformationModifyItem-PSCH-ReconfRqst

UL-Code-768-InformationModifyItem-PSCH-ReconfRqst ::= SEQUENCE {
	pUSCH-ID								PUSCH-ID,
	tdd-ChannelisationCode768				TDD-ChannelisationCode768,
	iE-Extensions							ProtocolExtensionContainer { { UL-Code-768-InformationModifyItem-PSCH-ReconfRqst-ExtIEs} }		OPTIONAL,
	...
}

UL-Code-768-InformationModifyItem-PSCH-ReconfRqst-ExtIEs NBAP-PROTOCOL-EXTENSION ::= {
	...
}

PUSCHSets-DeleteList-PSCH-ReconfRqst ::= SEQUENCE (SIZE (1..maxNrOfPUSCHSets)) OF PUSCHSets-DeleteItem-PSCH-ReconfRqst

PUSCHSets-DeleteItem-PSCH-ReconfRqst	 ::= SEQUENCE {
	pUSCHSet-ID									PUSCHSet-ID,
	iE-Extensions								ProtocolExtensionContainer { {PUSCHSets-DeleteItem-PSCH-ReconfRqst-ExtIEs} }		OPTIONAL,
	...
}

PUSCHSets-DeleteItem-PSCH-ReconfRqst-ExtIEs  NBAP-PROTOCOL-EXTENSION ::= {
	...
}

HS-PDSCH-TDD-Information-PSCH-ReconfRqst ::= SEQUENCE {
	dL-HS-PDSCH-Timeslot-Information-PSCH-ReconfRqst					DL-HS-PDSCH-Timeslot-Information-PSCH-ReconfRqst			OPTIONAL,
	dL-HS-PDSCH-Timeslot-Information-LCR-PSCH-ReconfRqst				DL-HS-PDSCH-Timeslot-Information-LCR-PSCH-ReconfRqst		OPTIONAL,
	-- This HS-PDSCH Timeslot Information is for the first Frequency repetition, HS-PDSCH Timeslot information for Frequency repetitions 2 and on, should be defined in MultipleFreq-DL-HS-PDSCH-Timeslot-Information-LCR-PSCH-ReconfRqst
	iE-Extensions								ProtocolExtensionContainer { { HS-PDSCH-TDD-Information-PSCH-ReconfRqst-ExtIEs} }		OPTIONAL,
	...
}

HS-PDSCH-TDD-Information-PSCH-ReconfRqst-ExtIEs  NBAP-PROTOCOL-EXTENSION ::= {
	{ ID id-dL-HS-PDSCH-Timeslot-Information-768-PSCH-ReconfRqst 								CRITICALITY reject		EXTENSION  DL-HS-PDSCH-Timeslot-Information-768-PSCH-ReconfRqst			PRESENCE	optional }| -- For 7.68 Mcps TDD. Not Applicable to 3.84Mcps TDD or 1.28 Mcps TDD.
	{ ID id-UARFCNforNt																			CRITICALITY ignore		EXTENSION UARFCN																		PRESENCE optional }|
	-- This is the UARFCN for the first Frequency repetition. Mandatory for 1.28Mcps TDD when using multiple frequencies.
	{ ID id-multipleFreq-dL-HS-PDSCH-Timeslot-Information-LCR-PSCH-ReconfRqst					CRITICALITY reject		EXTENSION MultipleFreq-DL-HS-PDSCH-Timeslot-Information-LCR-PSCH-ReconfRqst		PRESENCE optional },
	-- Applicable to 1.28Mcps TDD when using multiple frequencies, This Information is for the 2nd and beyond Frequency repetition
	...
}


DL-HS-PDSCH-Timeslot-Information-PSCH-ReconfRqst ::= SEQUENCE (SIZE (1..maxNrOfDLTSs)) OF DL-HS-PDSCH-Timeslot-InformationItem-PSCH-ReconfRqst

DL-HS-PDSCH-Timeslot-InformationItem-PSCH-ReconfRqst::= SEQUENCE {
	timeSlot								TimeSlot,
	midambleShiftAndBurstType				MidambleShiftAndBurstType,
	dl-HS-PDSCH-Codelist-PSCH-ReconfRqst	DL-HS-PDSCH-Codelist-PSCH-ReconfRqst,
	maxHSDSCH-HSSCCH-Power					MaximumTransmissionPower				OPTIONAL,
	iE-Extensions							ProtocolExtensionContainer { { DL-HS-PDSCH-Timeslot-InformationItem-PSCH-ReconfRqst-ExtIEs} }		OPTIONAL,
	...
}

DL-HS-PDSCH-Timeslot-InformationItem-PSCH-ReconfRqst-ExtIEs NBAP-PROTOCOL-EXTENSION ::= {
	...
}

DL-HS-PDSCH-Codelist-PSCH-ReconfRqst ::= SEQUENCE (SIZE (1..maxNrOfHSPDSCHs)) OF TDD-ChannelisationCode


DL-HS-PDSCH-Timeslot-Information-768-PSCH-ReconfRqst ::= SEQUENCE (SIZE (1..maxNrOfDLTSs)) OF DL-HS-PDSCH-Timeslot-InformationItem-768-PSCH-ReconfRqst

DL-HS-PDSCH-Timeslot-InformationItem-768-PSCH-ReconfRqst::= SEQUENCE {
	timeSlot									TimeSlot,
	midambleShiftAndBurstType768				MidambleShiftAndBurstType768,
	dl-HS-PDSCH-Codelist-768-PSCH-ReconfRqst	DL-HS-PDSCH-Codelist-768-PSCH-ReconfRqst,
	maxHSDSCH-HSSCCH-Power						MaximumTransmissionPower					OPTIONAL,
	iE-Extensions							ProtocolExtensionContainer { { DL-HS-PDSCH-Timeslot-InformationItem-768-PSCH-ReconfRqst-ExtIEs} }		OPTIONAL,
	...
}

DL-HS-PDSCH-Timeslot-InformationItem-768-PSCH-ReconfRqst-ExtIEs NBAP-PROTOCOL-EXTENSION ::= {
	...
}

DL-HS-PDSCH-Codelist-768-PSCH-ReconfRqst ::= SEQUENCE (SIZE (1..maxNrOfHSPDSCHs768)) OF TDD-ChannelisationCode768

MultipleFreq-DL-HS-PDSCH-Timeslot-Information-LCR-PSCH-ReconfRqst ::= SEQUENCE (SIZE (1..maxFrequencyinCell-1)) OF ProtocolIE-Single-Container{{ MultipleFreq-DL-HS-PDSCH-Timeslot-Information-LCRItemIE-PSCH-ReconfRqst}}
	-- Includes the 2nd through the max number of frequency repetitions.

MultipleFreq-DL-HS-PDSCH-Timeslot-Information-LCRItemIE-PSCH-ReconfRqst NBAP-PROTOCOL-IES ::= {
	{ ID id-MultipleFreq-DL-HS-PDSCH-Timeslot-Information-LCRItem-PSCH-ReconfRqst	CRITICALITY  reject	TYPE	MultipleFreq-DL-HS-PDSCH-Timeslot-Information-LCRItem-PSCH-ReconfRqst PRESENCE optional }
}

MultipleFreq-DL-HS-PDSCH-Timeslot-Information-LCRItem-PSCH-ReconfRqst ::= SEQUENCE {
	dL-HS-PDSCH-Timeslot-Information-LCR-PSCH-ReconfRqst	DL-HS-PDSCH-Timeslot-Information-LCR-PSCH-ReconfRqst 	OPTIONAL,
	uARFCN													UARFCN,
	iE-Extensions											ProtocolExtensionContainer { { MultipleFreq-DL-HS-PDSCH-Timeslot-Information-LCRItem-PSCH-ReconfRqst-ExtIEs} }		OPTIONAL,
	...
}

MultipleFreq-DL-HS-PDSCH-Timeslot-Information-LCRItem-PSCH-ReconfRqst-ExtIEs  NBAP-PROTOCOL-EXTENSION ::= {
	...
}

Add-To-HS-SCCH-Resource-Pool-PSCH-ReconfRqst::= SEQUENCE {
	hS-SCCH-Information-PSCH-ReconfRqst		HS-SCCH-Information-PSCH-ReconfRqst			OPTIONAL,
	hS-SCCH-Information-LCR-PSCH-ReconfRqst	HS-SCCH-Information-LCR-PSCH-ReconfRqst		OPTIONAL,
	iE-Extensions							ProtocolExtensionContainer { { Add-To-HS-SCCH-Resource-Pool-PSCH-ReconfRqst-ExtIEs} }		OPTIONAL,
	...
}

Add-To-HS-SCCH-Resource-Pool-PSCH-ReconfRqst-ExtIEs NBAP-PROTOCOL-EXTENSION ::= {
	{ ID id-hS-SCCH-Information-768-PSCH-ReconfRqst CRITICALITY	reject		EXTENSION HS-SCCH-Information-768-PSCH-ReconfRqst			PRESENCE optional }|
	-- 7.68 Mcps TDD. Not Applicable to 3.84Mcps TDD or 1.28 Mcps TDD.
	{ ID id-HS-SCCH-InformationExt-LCR-PSCH-ReconfRqst	CRITICALITY ignore	EXTENSION HS-SCCH-InformationExt-LCR-PSCH-ReconfRqst		PRESENCE optional },
	-- Applicable to 1.28Mcps TDD only, used when there are more than maxNrOfHSSCCHs HS-SCCHs in the message.
	...
}

HS-SCCH-Information-PSCH-ReconfRqst::= SEQUENCE (SIZE (1..maxNrOfHSSCCHs)) OF HS-SCCH-InformationItem-PSCH-ReconfRqst

HS-SCCH-InformationItem-PSCH-ReconfRqst	 ::= SEQUENCE {
	hS-SCCH-ID								HS-SCCH-ID,
	timeSlot								TimeSlot,
	midambleShiftAndBurstType				MidambleShiftAndBurstType,
	tdd-ChannelisationCode					TDD-ChannelisationCode,
	hS-SCCH-MaxPower						DL-Power,
	hS-SICH-Information						HS-SICH-Information-PSCH-ReconfRqst,
	iE-Extensions							ProtocolExtensionContainer { { HS-SCCH-InformationItem-PSCH-ReconfRqst-ExtIEs} }		OPTIONAL,
	...
}

HS-SCCH-InformationItem-PSCH-ReconfRqst-ExtIEs  NBAP-PROTOCOL-EXTENSION ::= {
	...
}

HS-SICH-Information-PSCH-ReconfRqst	 ::= SEQUENCE {
	hsSICH-ID								HS-SICH-ID,
	timeSlot								TimeSlot,
	midambleShiftAndBurstType				MidambleShiftAndBurstType,
	tdd-ChannelisationCode					TDD-ChannelisationCode,
	iE-Extensions							ProtocolExtensionContainer { { HS-SICH-Information-PSCH-ReconfRqst-ExtIEs} }		OPTIONAL,
	...
}

HS-SICH-Information-PSCH-ReconfRqst-ExtIEs  NBAP-PROTOCOL-EXTENSION ::= {
	...
}

HS-SCCH-Information-LCR-PSCH-ReconfRqst::= SEQUENCE (SIZE (1..maxNrOfHSSCCHs)) OF HS-SCCH-InformationItem-LCR-PSCH-ReconfRqst

HS-SCCH-InformationItem-LCR-PSCH-ReconfRqst	 ::= SEQUENCE {
	hS-SCCH-ID								HS-SCCH-ID,
	timeSlotLCR								TimeSlotLCR,
	midambleShiftLCR						MidambleShiftLCR,
	first-TDD-ChannelisationCode			TDD-ChannelisationCode,
	second-TDD-ChannelisationCode			TDD-ChannelisationCode,
	hS-SCCH-MaxPower						DL-Power,
	hS-SICH-Information-LCR					HS-SICH-Information-LCR-PSCH-ReconfRqst,
	iE-Extensions							ProtocolExtensionContainer { { HS-SCCH-InformationItem-LCR-PSCH-ReconfRqst-ExtIEs} }		OPTIONAL,
	...
}

HS-SCCH-InformationItem-LCR-PSCH-ReconfRqst-ExtIEs  NBAP-PROTOCOL-EXTENSION ::= {
	{ ID id-Extended-HS-SCCH-ID							CRITICALITY ignore		EXTENSION Extended-HS-SCCH-ID	PRESENCE optional}|
	-- used if the HS-SCCH identity has a value larger than 31
	{ ID id-UARFCNforNt								 CRITICALITY ignore		EXTENSION UARFCN		PRESENCE optional},
	-- Mandatory for 1.28Mcps TDD when using multiple frequencies
	...
}

HS-SICH-Information-LCR-PSCH-ReconfRqst	 ::= SEQUENCE {
	hsSICH-ID								HS-SICH-ID,
	timeSlotLCR								TimeSlotLCR,
	midambleShiftLCR						MidambleShiftLCR,
	tdd-ChannelisationCode					TDD-ChannelisationCode,
	iE-Extensions							ProtocolExtensionContainer { { HS-SICH-Information-LCR-PSCH-ReconfRqst-ExtIEs} }		OPTIONAL,
	...
}

HS-SICH-Information-LCR-PSCH-ReconfRqst-ExtIEs  NBAP-PROTOCOL-EXTENSION ::= {
	{ ID id-Extended-HS-SICH-ID							CRITICALITY ignore	EXTENSION Extended-HS-SICH-ID	PRESENCE optional},
	-- used if the HS-SICH identity has a value larger than 31
	...
}

HS-SCCH-Information-768-PSCH-ReconfRqst::= SEQUENCE (SIZE (1..maxNrOfHSSCCHs)) OF HS-SCCH-InformationItem-768-PSCH-ReconfRqst

HS-SCCH-InformationItem-768-PSCH-ReconfRqst	 ::= SEQUENCE {
	hS-SCCH-ID								HS-SCCH-ID,
	timeSlot								TimeSlot,
	midambleShiftAndBurstType768			MidambleShiftAndBurstType768,
	tdd-ChannelisationCode768				TDD-ChannelisationCode768,
	hS-SCCH-MaxPower						DL-Power,
	hS-SICH-Information-768					HS-SICH-Information-768-PSCH-ReconfRqst,
	iE-Extensions							ProtocolExtensionContainer { { HS-SCCH-InformationItem-768-PSCH-ReconfRqst-ExtIEs} }		OPTIONAL,
	...
}

HS-SCCH-InformationItem-768-PSCH-ReconfRqst-ExtIEs  NBAP-PROTOCOL-EXTENSION ::= {
	...
}

HS-SICH-Information-768-PSCH-ReconfRqst	 ::= SEQUENCE {
	hsSICH-ID								HS-SICH-ID,
	timeSlot								TimeSlot,
	midambleShiftAndBurstType768			MidambleShiftAndBurstType768,
	tdd-ChannelisationCode768				TDD-ChannelisationCode768,
	iE-Extensions							ProtocolExtensionContainer { { HS-SICH-Information-768-PSCH-ReconfRqst-ExtIEs} }		OPTIONAL,
	...
}

HS-SICH-Information-768-PSCH-ReconfRqst-ExtIEs  NBAP-PROTOCOL-EXTENSION ::= {
	...
}

HS-SCCH-InformationExt-LCR-PSCH-ReconfRqst ::= SEQUENCE (SIZE (1.. maxNrOfHSSCCHsinExt)) OF HS-SCCH-InformationItem-LCR-PSCH-ReconfRqst

Modify-HS-SCCH-Resource-Pool-PSCH-ReconfRqst::= SEQUENCE {
	hS-SCCH-InformationModify-PSCH-ReconfRqst		HS-SCCH-InformationModify-PSCH-ReconfRqst		OPTIONAL,
	hS-SCCH-InformationModify-LCR-PSCH-ReconfRqst	HS-SCCH-InformationModify-LCR-PSCH-ReconfRqst	OPTIONAL,
	iE-Extensions									ProtocolExtensionContainer { { Modify-HS-SCCH-Resource-Pool-PSCH-ReconfRqst-ExtIEs} }		OPTIONAL,
	...
}

Modify-HS-SCCH-Resource-Pool-PSCH-ReconfRqst-ExtIEs NBAP-PROTOCOL-EXTENSION ::= {
	{ ID id-hS-SCCH-InformationModify-768-PSCH-ReconfRqst		CRITICALITY reject	EXTENSION HS-SCCH-InformationModify-768-PSCH-ReconfRqst 	PRESENCE	optional }|
	-- 7.68 Mcps TDD. Not Applicable to 3.84Mcps TDD or 1.28 Mcps TDD.
	{ ID id-HS-SCCH-InformationModifyExt-LCR-PSCH-ReconfRqst	CRITICALITY ignore	EXTENSION HS-SCCH-InformationModifyExt-LCR-PSCH-ReconfRqst		PRESENCE optional },
	-- Applicable to 1.28Mcps TDD only, used when there are more than maxNrOfHSSCCHs HS-SCCHs in the message.
	...
}

HS-SCCH-InformationModifyItem-PSCH-ReconfRqst	 ::= SEQUENCE {
	hS-SCCH-ID								HS-SCCH-ID,
	timeSlot								TimeSlot 									OPTIONAL,
	midambleShiftAndBurstType				MidambleShiftAndBurstType 					OPTIONAL,
	tdd-ChannelisationCode					TDD-ChannelisationCode 						OPTIONAL,
	hS-SCCH-MaxPower						DL-Power 									OPTIONAL,
	hS-SICH-Information						HS-SICH-InformationModify-PSCH-ReconfRqst 	OPTIONAL,
	iE-Extensions							ProtocolExtensionContainer { { HS-SCCH-InformationModifyItem-PSCH-ReconfRqst-ExtIEs} }		OPTIONAL,
	...
}

HS-SCCH-InformationModifyItem-PSCH-ReconfRqst-ExtIEs  NBAP-PROTOCOL-EXTENSION ::= {
	...
}

HS-SICH-InformationModify-PSCH-ReconfRqst	 ::= SEQUENCE {
	hsSICH-ID								HS-SICH-ID,
	timeSlot								TimeSlot 					OPTIONAL,
	midambleShiftAndBurstType				MidambleShiftAndBurstType 	OPTIONAL,
	tdd-ChannelisationCode					TDD-ChannelisationCode 		OPTIONAL,
	iE-Extensions							ProtocolExtensionContainer { { HS-SICH-InformationModify-PSCH-ReconfRqst-ExtIEs} }		OPTIONAL,
	...
}

HS-SICH-InformationModify-PSCH-ReconfRqst-ExtIEs  NBAP-PROTOCOL-EXTENSION ::= {
	...
}

HS-SCCH-InformationModify-LCR-PSCH-ReconfRqst::= SEQUENCE (SIZE (1..maxNrOfHSSCCHs)) OF HS-SCCH-InformationModifyItem-LCR-PSCH-ReconfRqst

HS-SCCH-InformationModifyItem-LCR-PSCH-ReconfRqst	 ::= SEQUENCE {
	hS-SCCH-ID								HS-SCCH-ID,
	timeSlotLCR								TimeSlotLCR 									OPTIONAL,
	midambleShiftLCR						MidambleShiftLCR 								OPTIONAL,
	first-TDD-ChannelisationCode			TDD-ChannelisationCode							OPTIONAL,
	second-TDD-ChannelisationCode			TDD-ChannelisationCode							OPTIONAL,
	hS-SCCH-MaxPower						DL-Power										OPTIONAL,
	hS-SICH-Information-LCR					HS-SICH-InformationModify-LCR-PSCH-ReconfRqst 	OPTIONAL,
	iE-Extensions							ProtocolExtensionContainer { { HS-SCCH-InformationModifyItem-LCR-PSCH-ReconfRqst-ExtIEs} }		OPTIONAL,
	...
}

HS-SCCH-InformationModifyItem-LCR-PSCH-ReconfRqst-ExtIEs  NBAP-PROTOCOL-EXTENSION ::= {
	{ ID id-Extended-HS-SCCH-ID							CRITICALITY ignore	EXTENSION Extended-HS-SCCH-ID	PRESENCE optional}|
	-- used if the HS-SCCH identity has a value larger than 31
	{ ID id-UARFCNforNt									CRITICALITY ignore	EXTENSION UARFCN		PRESENCE optional},
	-- Applicable to 1.28Mcps TDD when using multiple frequencies
	...
}

HS-SCCH-InformationModifyExt-LCR-PSCH-ReconfRqst ::= SEQUENCE (SIZE (1.. maxNrOfHSSCCHsinExt)) OF HS-SCCH-InformationModifyItem-LCR-PSCH-ReconfRqst

HS-SICH-InformationModify-LCR-PSCH-ReconfRqst	 ::= SEQUENCE {
	hsSICH-ID								HS-SICH-ID,
	timeSlotLCR								TimeSlotLCR 			OPTIONAL,
	midambleShiftLCR						MidambleShiftLCR 		OPTIONAL,
	tdd-ChannelisationCode					TDD-ChannelisationCode	OPTIONAL,
	iE-Extensions							ProtocolExtensionContainer { { HS-SICH-InformationModify-LCR-PSCH-ReconfRqst-ExtIEs} }		OPTIONAL,
	...
}

HS-SICH-InformationModify-LCR-PSCH-ReconfRqst-ExtIEs  NBAP-PROTOCOL-EXTENSION ::= {
	{ ID id-Extended-HS-SICH-ID							CRITICALITY ignore	EXTENSION Extended-HS-SICH-ID	PRESENCE optional },
	-- used if the HS-SICH identity has a value larger than 31
	...
}

HS-SCCH-InformationModify-768-PSCH-ReconfRqst::= SEQUENCE (SIZE (1..maxNrOfHSSCCHs)) OF HS-SCCH-InformationModifyItem-768-PSCH-ReconfRqst

HS-SCCH-InformationModifyItem-768-PSCH-ReconfRqst	 ::= SEQUENCE {
	hS-SCCH-ID								HS-SCCH-ID,
	timeSlot								TimeSlot										OPTIONAL,
	midambleShiftAndBurstType768			MidambleShiftAndBurstType768,
	tdd-ChannelisationCode768				TDD-ChannelisationCode768,
	hS-SCCH-MaxPower						DL-Power 																			OPTIONAL,
	hS-SICH-Information-768					HS-SICH-InformationModify-768-PSCH-ReconfRqst 	OPTIONAL,
	iE-Extensions							ProtocolExtensionContainer { { HS-SCCH-InformationModifyItem-768-PSCH-ReconfRqst-ExtIEs} }		OPTIONAL,
	...
}

HS-SCCH-InformationModifyItem-768-PSCH-ReconfRqst-ExtIEs  NBAP-PROTOCOL-EXTENSION ::= {
	...
}

HS-SICH-InformationModify-768-PSCH-ReconfRqst	 ::= SEQUENCE {
	hsSICH-ID								HS-SICH-ID,
	timeSlot								TimeSlot										OPTIONAL,
	midambleShiftAndBurstType768			MidambleShiftAndBurstType768,
	tdd-ChannelisationCode768				TDD-ChannelisationCode768,
	iE-Extensions							ProtocolExtensionContainer { { HS-SICH-InformationModify-768-PSCH-ReconfRqst-ExtIEs} }		OPTIONAL,
	...
}

HS-SICH-InformationModify-768-PSCH-ReconfRqst-ExtIEs  NBAP-PROTOCOL-EXTENSION ::= {
	...
}

HS-SCCH-InformationModify-PSCH-ReconfRqst::= SEQUENCE (SIZE (1..maxNrOfHSSCCHs)) OF HS-SCCH-InformationModifyItem-PSCH-ReconfRqst

Delete-From-HS-SCCH-Resource-Pool-PSCH-ReconfRqst ::= SEQUENCE (SIZE (1..maxNrOfHSSCCHs)) OF Delete-From-HS-SCCH-Resource-PoolItem-PSCH-ReconfRqst

Delete-From-HS-SCCH-Resource-PoolItem-PSCH-ReconfRqst	 ::= SEQUENCE {
	hS-SCCH-ID					HS-SCCH-ID,
	iE-Extensions				ProtocolExtensionContainer { { Delete-From-HS-SCCH-Resource-PoolItem-PSCH-ReconfRqst-ExtIEs} }		OPTIONAL,
	...
}

Delete-From-HS-SCCH-Resource-PoolItem-PSCH-ReconfRqst-ExtIEs  NBAP-PROTOCOL-EXTENSION ::= {
	{ ID id-Extended-HS-SCCH-ID							CRITICALITY ignore	EXTENSION Extended-HS-SCCH-ID	PRESENCE optional },
	-- used if the HS-SCCH identity has a value larger than 31
	...
}

E-PUCH-Information-PSCH-ReconfRqst ::= SEQUENCE {
	lTGI-Presence							LTGI-Presence,
	sNPL-Reporting-Type						SNPL-Reporting-Type,
	midambleShiftAndBurstType				MidambleShiftAndBurstType,
	e-PUCH-Timeslot-Info					E-PUCH-Timeslot-Info,
	iE-Extensions							ProtocolExtensionContainer { { E-PUCH-Information-PSCH-ReconfRqst-ExtIEs} }		OPTIONAL,
	...
}

E-PUCH-Information-PSCH-ReconfRqst-ExtIEs  NBAP-PROTOCOL-EXTENSION ::= {
	...
}

E-PUCH-Timeslot-Info ::= SEQUENCE (SIZE (1..maxNrOfE-PUCHSlots)) OF TimeSlot

Add-To-E-AGCH-Resource-Pool-PSCH-ReconfRqst::= SEQUENCE {
	e-AGCH-Information-PSCH-ReconfRqst		E-AGCH-Information-PSCH-ReconfRqst		OPTIONAL,
	iE-Extensions							ProtocolExtensionContainer { { Add-To-E-AGCH-Resource-Pool-PSCH-ReconfRqst-ExtIEs} }		OPTIONAL,
	...
}

Add-To-E-AGCH-Resource-Pool-PSCH-ReconfRqst-ExtIEs NBAP-PROTOCOL-EXTENSION ::= {
	...
}

E-AGCH-Information-PSCH-ReconfRqst::= SEQUENCE (SIZE (1..maxNrOfEAGCHs)) OF E-AGCH-InformationItem-PSCH-ReconfRqst

E-AGCH-InformationItem-PSCH-ReconfRqst	 ::= SEQUENCE {
	e-AGCH-ID								E-AGCH-Id,
	timeSlot								TimeSlot,
	midambleShiftAndBurstType				MidambleShiftAndBurstType,
	tdd-ChannelisationCode					TDD-ChannelisationCode,
	e-AGCH-MaxPower							DL-Power,
	iE-Extensions							ProtocolExtensionContainer { { E-AGCH-InformationItem-PSCH-ReconfRqst-ExtIEs} }		OPTIONAL,
	...
}

E-AGCH-InformationItem-PSCH-ReconfRqst-ExtIEs  NBAP-PROTOCOL-EXTENSION ::= {
	...
}

Modify-E-AGCH-Resource-Pool-PSCH-ReconfRqst::= SEQUENCE {
	e-AGCH-InformationModify-PSCH-ReconfRqst		E-AGCH-InformationModify-PSCH-ReconfRqst	OPTIONAL,
	iE-Extensions									ProtocolExtensionContainer { { Modify-E-AGCH-Resource-Pool-PSCH-ReconfRqst-ExtIEs} }		OPTIONAL,
	...
}

Modify-E-AGCH-Resource-Pool-PSCH-ReconfRqst-ExtIEs NBAP-PROTOCOL-EXTENSION ::= {
	...
}

E-AGCH-InformationModify-PSCH-ReconfRqst::= SEQUENCE (SIZE (1..maxNrOfEAGCHs)) OF E-AGCH-InformationModifyItem-PSCH-ReconfRqst

E-AGCH-InformationModifyItem-PSCH-ReconfRqst	 ::= SEQUENCE {
	e-AGCH-ID								E-AGCH-Id,
	timeSlot								TimeSlot 					OPTIONAL,
	midambleShiftAndBurstType				MidambleShiftAndBurstType 	OPTIONAL,
	tdd-ChannelisationCode					TDD-ChannelisationCode 		OPTIONAL,
	e-AGCH-MaxPower							DL-Power 					OPTIONAL,
	iE-Extensions							ProtocolExtensionContainer { { E-AGCH-InformationModifyItem-PSCH-ReconfRqst-ExtIEs} }		OPTIONAL,
	...
}

E-AGCH-InformationModifyItem-PSCH-ReconfRqst-ExtIEs  NBAP-PROTOCOL-EXTENSION ::= {
	...
}

Delete-From-E-AGCH-Resource-Pool-PSCH-ReconfRqst ::= SEQUENCE (SIZE (1..maxNrOfEAGCHs)) OF Delete-From-E-AGCH-Resource-PoolItem-PSCH-ReconfRqst

Delete-From-E-AGCH-Resource-PoolItem-PSCH-ReconfRqst	 ::= SEQUENCE {
	e-AGCH-ID							E-AGCH-Id,
	iE-Extensions						ProtocolExtensionContainer { { Delete-From-E-AGCH-Resource-PoolItem-PSCH-ReconfRqst-ExtIEs} }		OPTIONAL,
	...
}

Delete-From-E-AGCH-Resource-PoolItem-PSCH-ReconfRqst-ExtIEs  NBAP-PROTOCOL-EXTENSION ::= {
	...
}

E-HICH-Information-PSCH-ReconfRqst	 ::= SEQUENCE {
	midambleShiftAndBurstType				MidambleShiftAndBurstType,
	tdd-ChannelisationCode					TDD-ChannelisationCode,
	e-HICH-MaxPower							DL-Power,
	iE-Extensions							ProtocolExtensionContainer { { E-HICH-Information-PSCH-ReconfRqst-ExtIEs} }		OPTIONAL,
	...
}
E-HICH-Information-PSCH-ReconfRqst-ExtIEs  NBAP-PROTOCOL-EXTENSION ::= {
	...
}

E-PUCH-Information-768-PSCH-ReconfRqst ::= SEQUENCE {
	lTGI-Presence							LTGI-Presence,
	sNPL-Reporting-Type						SNPL-Reporting-Type,
	midambleShiftAndBurstType768			MidambleShiftAndBurstType768,
	e-PUCH-Timeslot-Info					E-PUCH-Timeslot-Info,
	iE-Extensions							ProtocolExtensionContainer { { E-PUCH-Information-768-PSCH-ReconfRqst-ExtIEs} }		OPTIONAL,
	...
}

E-PUCH-Information-768-PSCH-ReconfRqst-ExtIEs  NBAP-PROTOCOL-EXTENSION ::= {
	...
}

Add-To-E-AGCH-Resource-Pool-768-PSCH-ReconfRqst::= SEQUENCE {
	e-AGCH-Information-768-PSCH-ReconfRqst		E-AGCH-Information-768-PSCH-ReconfRqst		OPTIONAL,
	iE-Extensions							ProtocolExtensionContainer { { Add-To-E-AGCH-Resource-Pool-768-PSCH-ReconfRqst-ExtIEs} }		OPTIONAL,
	...
}

Add-To-E-AGCH-Resource-Pool-768-PSCH-ReconfRqst-ExtIEs NBAP-PROTOCOL-EXTENSION ::= {
	...
}

E-AGCH-Information-768-PSCH-ReconfRqst::= SEQUENCE (SIZE (1..maxNrOfEAGCHs)) OF E-AGCH-InformationItem-768-PSCH-ReconfRqst

E-AGCH-InformationItem-768-PSCH-ReconfRqst	 ::= SEQUENCE {
	e-AGCH-ID								E-AGCH-Id,
	timeSlot								TimeSlot,
	midambleShiftAndBurstType768			MidambleShiftAndBurstType768,
	tdd-ChannelisationCode768				TDD-ChannelisationCode768,
	e-AGCH-MaxPower							DL-Power,
	iE-Extensions							ProtocolExtensionContainer { { E-AGCH-InformationItem-768-PSCH-ReconfRqst-ExtIEs} }		OPTIONAL,
	...
}

E-AGCH-InformationItem-768-PSCH-ReconfRqst-ExtIEs  NBAP-PROTOCOL-EXTENSION ::= {
	...
}

Modify-E-AGCH-Resource-Pool-768-PSCH-ReconfRqst::= SEQUENCE {
	e-AGCH-InformationModify-768-PSCH-ReconfRqst		E-AGCH-InformationModify-768-PSCH-ReconfRqst	OPTIONAL,
	iE-Extensions									ProtocolExtensionContainer { { Modify-E-AGCH-Resource-Pool-768-PSCH-ReconfRqst-ExtIEs} }		OPTIONAL,
	...
}

Modify-E-AGCH-Resource-Pool-768-PSCH-ReconfRqst-ExtIEs NBAP-PROTOCOL-EXTENSION ::= {
	...
}

E-AGCH-InformationModify-768-PSCH-ReconfRqst::= SEQUENCE (SIZE (1..maxNrOfEAGCHs)) OF E-AGCH-InformationModifyItem-768-PSCH-ReconfRqst

E-AGCH-InformationModifyItem-768-PSCH-ReconfRqst	 ::= SEQUENCE {
	e-AGCH-ID								E-AGCH-Id,
	timeSlot								TimeSlot 						OPTIONAL,
	midambleShiftAndBurstType768			MidambleShiftAndBurstType768	OPTIONAL,
	tdd-ChannelisationCode768				TDD-ChannelisationCode768		OPTIONAL,
	e-AGCH-MaxPower							DL-Power 						OPTIONAL,
	iE-Extensions							ProtocolExtensionContainer { { E-AGCH-InformationModifyItem-768-PSCH-ReconfRqst-ExtIEs} }		OPTIONAL,
	...
}

E-AGCH-InformationModifyItem-768-PSCH-ReconfRqst-ExtIEs  NBAP-PROTOCOL-EXTENSION ::= {
	...
}

E-HICH-Information-768-PSCH-ReconfRqst	 ::= SEQUENCE {
	midambleShiftAndBurstType768			MidambleShiftAndBurstType768,
	tdd-ChannelisationCode768				TDD-ChannelisationCode768,
	e-HICH-MaxPower							DL-Power,
	iE-Extensions							ProtocolExtensionContainer { { E-HICH-Information-768-PSCH-ReconfRqst-ExtIEs} }		OPTIONAL,
	...
}
E-HICH-Information-768-PSCH-ReconfRqst-ExtIEs  NBAP-PROTOCOL-EXTENSION ::= {
	...
}

E-PUCH-Information-LCR-PSCH-ReconfRqst ::= SEQUENCE {
	lTGI-Presence							LTGI-Presence,
	sNPL-Reporting-Type						SNPL-Reporting-Type,
	e-PUCH-Timeslot-InfoLCR					E-PUCH-Timeslot-InfoLCR		OPTIONAL,
	-- This E-PUCH Timeslot Information is for the first Frequency repetition, E-PUCH timeslot information for Frequency repetitions 2 and on, should be defined in MultipleFreq-E-PUCH-Timeslot-InformationList-LCR-PSCH-ReconfRqst.
	iE-Extensions							ProtocolExtensionContainer { { E-PUCH-Information-LCR-PSCH-ReconfRqst-ExtIEs} }		OPTIONAL,
	...
}

E-PUCH-Information-LCR-PSCH-ReconfRqst-ExtIEs  NBAP-PROTOCOL-EXTENSION ::= {
	{ ID id-UARFCNforNt															CRITICALITY ignore										EXTENSION UARFCN															PRESENCE optional}|
	-- This is the UARFCN for the first Frequency repetition. Mandatory for 1.28Mcps TDD when using multiple frequencies.
	{ ID id-MultipleFreq-E-PUCH-Timeslot-InformationList-LCR-PSCH-ReconfRqst	CRITICALITY reject										EXTENSION MultipleFreq-E-PUCH-Timeslot-InformationList-LCR-PSCH-ReconfRqst	PRESENCE optional },
	-- Applicable to 1.28Mcps TDD when using multiple frequencies.This E-PUCH Information is for the 2nd and beyond frequencies.
	...
}

E-PUCH-Timeslot-InfoLCR ::= SEQUENCE (SIZE (1..maxNrOfE-PUCHSlotsLCR)) OF E-PUCH-Timeslot-Item-InfoLCR

E-PUCH-Timeslot-Item-InfoLCR ::= SEQUENCE {
	timeSlot								TimeSlotLCR,
	midambleShiftAndBurstType				MidambleShiftLCR,
	e-PUCH-Codelist-LCR						E-PUCH-Codelist-LCR,
	iE-Extensions							ProtocolExtensionContainer { { E-PUCH-Timeslot-Item-InfoLCR-ExtIEs} }		OPTIONAL,
	...
}

E-PUCH-Timeslot-Item-InfoLCR-ExtIEs NBAP-PROTOCOL-EXTENSION ::= {
	...
}

E-PUCH-Codelist-LCR ::= SEQUENCE (SIZE (1..maxNrOfEPUCHcodes)) OF TDD-ChannelisationCode

Add-To-E-AGCH-Resource-Pool-LCR-PSCH-ReconfRqst ::= SEQUENCE {
	e-AGCH-Information-LCR-PSCH-ReconfRqst	E-AGCH-Information-LCR-PSCH-ReconfRqst,
	iE-Extensions							ProtocolExtensionContainer { { Add-To-E-AGCH-Resource-Pool-LCR-PSCH-ReconfRqst-ExtIEs} }		OPTIONAL,
	...
}

Add-To-E-AGCH-Resource-Pool-LCR-PSCH-ReconfRqst-ExtIEs NBAP-PROTOCOL-EXTENSION ::= {
	...
}

E-AGCH-Information-LCR-PSCH-ReconfRqst::= SEQUENCE (SIZE (1..maxNrOfEAGCHs)) OF E-AGCH-InformationItem-LCR-PSCH-ReconfRqst

E-AGCH-InformationItem-LCR-PSCH-ReconfRqst	 ::= SEQUENCE {
	e-AGCH-ID								E-AGCH-Id,
	timeSlotLCR								TimeSlotLCR,
	midambleShiftLCR						MidambleShiftLCR,
	first-TDD-ChannelisationCode			TDD-ChannelisationCode,
	second-TDD-ChannelisationCode			TDD-ChannelisationCode,
	e-AGCH-MaxPower							DL-Power,
	iE-Extensions							ProtocolExtensionContainer { { E-AGCH-InformationItem-LCR-PSCH-ReconfRqst-ExtIEs} }		OPTIONAL,
	...
}

E-AGCH-InformationItem-LCR-PSCH-ReconfRqst-ExtIEs  NBAP-PROTOCOL-EXTENSION ::= {
	{ ID id-UARFCNforNt						CRITICALITY ignore		EXTENSION UARFCN		PRESENCE optional},
	-- Mandatory for 1.28Mcps TDD when using multiple frequencies
	...
}

Modify-E-AGCH-Resource-Pool-LCR-PSCH-ReconfRqst::= SEQUENCE {
	e-AGCH-InformationModify-LCR-PSCH-ReconfRqst	E-AGCH-InformationModify-LCR-PSCH-ReconfRqst,
	iE-Extensions									ProtocolExtensionContainer { { Modify-E-AGCH-Resource-Pool-LCR-PSCH-ReconfRqst-ExtIEs} }		OPTIONAL,
	...
}

Modify-E-AGCH-Resource-Pool-LCR-PSCH-ReconfRqst-ExtIEs NBAP-PROTOCOL-EXTENSION ::= {
	...
}

E-AGCH-InformationModify-LCR-PSCH-ReconfRqst::= SEQUENCE (SIZE (1..maxNrOfEAGCHs)) OF E-AGCH-InformationModifyItem-LCR-PSCH-ReconfRqst

E-AGCH-InformationModifyItem-LCR-PSCH-ReconfRqst	 ::= SEQUENCE {
	e-AGCH-ID								E-AGCH-Id,
	timeSlotLCR								TimeSlotLCR				OPTIONAL,
	midambleShiftLCR						MidambleShiftLCR		OPTIONAL,
	first-TDD-ChannelisationCode			TDD-ChannelisationCode	OPTIONAL,
	second-TDD-ChannelisationCode			TDD-ChannelisationCode	OPTIONAL,
	e-AGCH-MaxPower							DL-Power				OPTIONAL,
	iE-Extensions							ProtocolExtensionContainer { { E-AGCH-InformationModifyItem-LCR-PSCH-ReconfRqst-ExtIEs} }		OPTIONAL,
	...
}

E-AGCH-InformationModifyItem-LCR-PSCH-ReconfRqst-ExtIEs  NBAP-PROTOCOL-EXTENSION ::= {
	{ ID id-UARFCNforNt						CRITICALITY ignore		EXTENSION UARFCN		PRESENCE optional},
	-- Mandatory for 1.28Mcps TDD when using multiple frequencies
	...
}

Add-To-E-HICH-Resource-Pool-LCR-PSCH-ReconfRqst ::= SEQUENCE {
	e-HICH-Information-LCR-PSCH-ReconfRqst	E-HICH-Information-LCR-PSCH-ReconfRqst,
	iE-Extensions							ProtocolExtensionContainer { { Add-To-E-HICH-Resource-Pool-LCR-PSCH-ReconfRqst-ExtIEs} }		OPTIONAL,
	...
}

Add-To-E-HICH-Resource-Pool-LCR-PSCH-ReconfRqst-ExtIEs  NBAP-PROTOCOL-EXTENSION ::= {
	...
}

E-HICH-Information-LCR-PSCH-ReconfRqst ::= SEQUENCE (SIZE (1..maxNrOfEHICHs)) OF E-HICH-InformationItem-LCR-PSCH-ReconfRqst

E-HICH-InformationItem-LCR-PSCH-ReconfRqst	::= SEQUENCE {
	e-HICH-ID-TDD							E-HICH-ID-TDD,
	e-HICH-Type								E-HICH-Type,
	tdd-ChannelisationCode					TDD-ChannelisationCode,
	timeSlotLCR								TimeSlotLCR,
	midambleShiftLCR						MidambleShiftLCR,
	e-HICH-MaxPower							DL-Power,
	iE-Extensions							ProtocolExtensionContainer { { E-HICH-InformationItem-LCR-PSCH-ReconfRqst-ExtIEs} }		OPTIONAL,
	...
}

E-HICH-InformationItem-LCR-PSCH-ReconfRqst-ExtIEs  NBAP-PROTOCOL-EXTENSION ::= {
	{ ID id-Extended-E-HICH-ID-TDD			CRITICALITY ignore EXTENSION Extended-E-HICH-ID-TDD PRESENCE optional}|
	-- Applicable to 1.28Mcps TDD only when the E-HICH identity has a value larger than 31.
	{ ID id-UARFCNforNt						CRITICALITY ignore		EXTENSION UARFCN			PRESENCE optional},
	-- Mandatory for 1.28Mcps TDD when using multiple frequencies
	...
}

Modify-E-HICH-Resource-Pool-LCR-PSCH-ReconfRqst ::= SEQUENCE {
	e-HICH-InformationModify-LCR-PSCH-ReconfRqst	E-HICH-InformationModify-LCR-PSCH-ReconfRqst,
	iE-Extensions									ProtocolExtensionContainer { { Modify-E-HICH-Resource-Pool-LCR-PSCH-ReconfRqst-ExtIEs} }		OPTIONAL,
	...
}

Modify-E-HICH-Resource-Pool-LCR-PSCH-ReconfRqst-ExtIEs  NBAP-PROTOCOL-EXTENSION ::= {
	...
}

E-HICH-InformationModify-LCR-PSCH-ReconfRqst ::= SEQUENCE (SIZE (1..maxNrOfEHICHs)) OF E-HICH-InformationModifyItem-LCR-PSCH-ReconfRqst

E-HICH-InformationModifyItem-LCR-PSCH-ReconfRqst ::= SEQUENCE {
	e-HICH-ID-TDD							E-HICH-ID-TDD,
	e-HICH-Type								E-HICH-Type  			OPTIONAL,
	tdd-ChannelisationCode					TDD-ChannelisationCode  OPTIONAL,
	timeSlotLCR								TimeSlotLCR   			OPTIONAL,
	midambleShiftLCR						MidambleShiftLCR   		OPTIONAL,
	e-HICH-MaxPower							DL-Power   				OPTIONAL,
	iE-Extensions							ProtocolExtensionContainer { { E-HICH-InformationModifyItem-LCR-PSCH-ReconfRqst-ExtIEs} }		OPTIONAL,
	...
}

E-HICH-InformationModifyItem-LCR-PSCH-ReconfRqst-ExtIEs  NBAP-PROTOCOL-EXTENSION ::= {
	{ ID id-Extended-E-HICH-ID-TDD			CRITICALITY ignore EXTENSION Extended-E-HICH-ID-TDD PRESENCE optional}|
	--Applicable to 1.28Mcps TDD only when the E-HICH identity has a value larger than 31.
	{ ID id-UARFCNforNt						CRITICALITY ignore		EXTENSION UARFCN			PRESENCE optional},
	-- Mandatory for 1.28Mcps TDD when using multiple frequencies
	...
}

Delete-From-E-HICH-Resource-Pool-PSCH-ReconfRqst ::= SEQUENCE (SIZE (1.. maxNrOfEHICHs)) OF Delete-From-E-HICH-Resource-PoolItem-PSCH-ReconfRqst

Delete-From-E-HICH-Resource-PoolItem-PSCH-ReconfRqst	::= SEQUENCE {
	e-HICH-ID-TDD									E-HICH-ID-TDD,
	iE-Extensions									ProtocolExtensionContainer { { Delete-From-E-HICH-Resource-PoolItem-PSCH-ReconfRqst-ExtIEs} }		OPTIONAL,
	...
}

Delete-From-E-HICH-Resource-PoolItem-PSCH-ReconfRqst-ExtIEs  NBAP-PROTOCOL-EXTENSION ::= {
	{ ID id-Extended-E-HICH-ID-TDD			CRITICALITY ignore EXTENSION Extended-E-HICH-ID-TDD PRESENCE optional},
	-- Applicable to 1.28Mcps TDD only when the E-HICH identity has a value larger than 31.
	...
}

SYNC-UL-Partition-LCR ::= SEQUENCE {
	eRUCCH-SYNC-UL-codes-bitmap					BIT STRING (SIZE (8)),
	iE-Extensions								ProtocolExtensionContainer { { SYNC-UL-Partition-LCR-ExtIEs} }		OPTIONAL,
	...
}

SYNC-UL-Partition-LCR-ExtIEs NBAP-PROTOCOL-EXTENSION ::= {
	...
}

Delete-From-HS-SCCH-Resource-PoolExt-PSCH-ReconfRqst ::= SEQUENCE (SIZE (1.. maxNrOfHSSCCHsinExt)) OF Delete-From-HS-SCCH-Resource-PoolItem-PSCH-ReconfRqst

MultipleFreq-E-PUCH-Timeslot-InformationList-LCR-PSCH-ReconfRqst ::= SEQUENCE (SIZE (1..maxFrequencyinCell-1)) OF ProtocolIE-Single-Container {{ MultipleFreq-E-PUCH-Timeslot-InformationItemIE-LCR-PSCH-ReconfRqst}} 
--Includes the 2nd through the max number of frequencies information repetitions.

MultipleFreq-E-PUCH-Timeslot-InformationItemIE-LCR-PSCH-ReconfRqst NBAP-PROTOCOL-IES ::= {
	{ ID id-MultipleFreq-E-PUCH-Timeslot-Information-LCRItem-PSCH-ReconfRqst	CRITICALITY ignore	TYPE MultipleFreq-E-PUCH-Timeslot-Information-LCRItem-PSCH-ReconfRqst		PRESENCE optional }
}

MultipleFreq-E-PUCH-Timeslot-Information-LCRItem-PSCH-ReconfRqst ::= SEQUENCE {
	e-PUCH-Timeslot-InfoLCR					E-PUCH-Timeslot-InfoLCR		OPTIONAL,
	uARFCN													UARFCN,
	iE-Extensions											ProtocolExtensionContainer { { MultipleFreq-E-PUCH-Timeslot-Information-LCRItem-PSCH-ReconfRqst-ExtIEs} }		OPTIONAL,
	...
}

MultipleFreq-E-PUCH-Timeslot-Information-LCRItem-PSCH-ReconfRqst-ExtIEs  NBAP-PROTOCOL-EXTENSION ::= {
	...
}

-- **************************************************************
--
-- PHYSICAL SHARED CHANNEL RECONFIGURATION RESPONSE
--
-- **************************************************************

PhysicalSharedChannelReconfigurationResponse ::= SEQUENCE {
	protocolIEs			ProtocolIE-Container  		{{PhysicalSharedChannelReconfigurationResponse-IEs}},
	protocolExtensions	ProtocolExtensionContainer {{PhysicalSharedChannelReconfigurationResponse-Extensions}}                   OPTIONAL,
	...
}

PhysicalSharedChannelReconfigurationResponse-IEs NBAP-PROTOCOL-IES ::= {
	{ ID	id-CriticalityDiagnostics		CRITICALITY		ignore		TYPE		CriticalityDiagnostics		PRESENCE	optional	},
	...
}

PhysicalSharedChannelReconfigurationResponse-Extensions NBAP-PROTOCOL-EXTENSION ::= {
	{ ID id-E-HICH-TimeOffset								CRITICALITY reject	EXTENSION E-HICH-TimeOffset										PRESENCE optional }|
	{ ID id-E-HICH-TimeOffsetLCR							CRITICALITY reject	EXTENSION E-HICH-TimeOffsetLCR										PRESENCE optional }|
	{ ID id-HSDSCH-Common-System-Information-ResponseFDD	CRITICALITY ignore	EXTENSION HSDSCH-Common-System-Information-ResponseFDD			PRESENCE optional }|
	{ ID id-HSDSCH-Paging-System-Information-ResponseFDD	CRITICALITY ignore	EXTENSION HSDSCH-Paging-System-Information-ResponseFDD			PRESENCE optional }|
	{ ID id-UARFCNforNt										CRITICALITY reject	EXTENSION UARFCN										PRESENCE optional}|
	-- Applicable to 1.28Mcps TDD when using multiple frequencies. This is the UARFCN for the first Frequency repetition.
	{ ID id-E-HICH-TimeOffset-Extension						CRITICALITY reject	EXTENSION E-HICH-TimeOffset-ExtensionLCR								PRESENCE optional }|
	-- Applicable to 1.28Mcps TDD when using multiple frequencies. This E-HICH-TimeOffset-ExtensionLCR is the E-HICH Time Offset LCR for the 2nd and beyond frequencies.
	{ ID id-Common-EDCH-System-Information-ResponseFDD	CRITICALITY ignore	EXTENSION Common-EDCH-System-Information-ResponseFDD			PRESENCE optional }|
	-- FDD only
	{ ID id-HSDSCH-Common-System-Information-ResponseLCR	CRITICALITY ignore	EXTENSION HSDSCH-Common-System-Information-ResponseLCR			PRESENCE optional }|
	{ ID id-HSDSCH-Paging-System-Information-ResponseLCR	CRITICALITY ignore	EXTENSION HSDSCH-Paging-System-Information-ResponseLCR			PRESENCE optional }|
	{ ID id-Common-EDCH-System-Information-ResponseLCR	CRITICALITY ignore	EXTENSION Common-EDCH-System-Information-ResponseLCR			PRESENCE optional },
	...
}

E-HICH-TimeOffset-ExtensionLCR ::= SEQUENCE (SIZE (1..maxFrequencyinCell-1)) OF ProtocolIE-Single-Container{{ Multiple-E-HICH-TimeOffsetLCR }}

Multiple-E-HICH-TimeOffsetLCR NBAP-PROTOCOL-IES ::= {
	{ ID id-MultipleFreq-E-HICH-TimeOffsetLCR	CRITICALITY reject	TYPE	MultipleFreq-E-HICH-TimeOffsetLCR PRESENCE optional }
}
MultipleFreq-E-HICH-TimeOffsetLCR ::= SEQUENCE {
	e-HICH-TimeOffsetLCR					E-HICH-TimeOffsetLCR,
	uARFCN									UARFCN,
	iE-Extensions							ProtocolExtensionContainer { { MultipleFreq-E-HICH-TimeOffsetLCR-ExtIEs} }		OPTIONAL,
	...
}
MultipleFreq-E-HICH-TimeOffsetLCR-ExtIEs  NBAP-PROTOCOL-EXTENSION ::= {
	...
}

-- **************************************************************
--
-- PHYSICAL SHARED CHANNEL RECONFIGURATION FAILURE
--
-- **************************************************************

PhysicalSharedChannelReconfigurationFailure ::= SEQUENCE {
	protocolIEs			ProtocolIE-Container  		{{PhysicalSharedChannelReconfigurationFailure-IEs}},
	protocolExtensions	ProtocolExtensionContainer {{PhysicalSharedChannelReconfigurationFailure-Extensions}}                   OPTIONAL,
	...
}

PhysicalSharedChannelReconfigurationFailure-IEs NBAP-PROTOCOL-IES ::= {
	{ ID id-CauseLevel-PSCH-ReconfFailure		CRITICALITY ignore	TYPE CauseLevel-PSCH-ReconfFailure	PRESENCE mandatory }|
	{ ID id-CriticalityDiagnostics				CRITICALITY ignore	TYPE CriticalityDiagnostics		PRESENCE optional },
	...
}

PhysicalSharedChannelReconfigurationFailure-Extensions NBAP-PROTOCOL-EXTENSION ::= {
	...
}

CauseLevel-PSCH-ReconfFailure ::= CHOICE {
	generalCause								GeneralCauseList-PSCH-ReconfFailure,
	setSpecificCause							SetSpecificCauseList-PSCH-ReconfFailureTDD,
	...,
	extension-CauseLevel-PSCH-ReconfFailure		Extension-CauseLevel-PSCH-ReconfFailure
}


GeneralCauseList-PSCH-ReconfFailure ::= SEQUENCE {
	cause						Cause,
	iE-Extensions				ProtocolExtensionContainer { { GeneralCauseItem-PSCH-ReconfFailure-ExtIEs} }		OPTIONAL,
	...
}

GeneralCauseItem-PSCH-ReconfFailure-ExtIEs NBAP-PROTOCOL-EXTENSION ::= {
	...
}

SetSpecificCauseList-PSCH-ReconfFailureTDD ::= SEQUENCE {
	unsuccessful-PDSCHSetList-PSCH-ReconfFailureTDD	Unsuccessful-PDSCHSetList-PSCH-ReconfFailureTDD		OPTIONAL,
	unsuccessful-PUSCHSetList-PSCH-ReconfFailureTDD	Unsuccessful-PUSCHSetList-PSCH-ReconfFailureTDD		OPTIONAL,
	iE-Extensions									ProtocolExtensionContainer { { SetSpecificCauseItem-PSCH-ReconfFailureTDD-ExtIEs} }		OPTIONAL,
	...
}

SetSpecificCauseItem-PSCH-ReconfFailureTDD-ExtIEs NBAP-PROTOCOL-EXTENSION ::= {
	...
}

Unsuccessful-PDSCHSetList-PSCH-ReconfFailureTDD ::= SEQUENCE (SIZE (0.. maxNrOfPDSCHSets)) OF ProtocolIE-Single-Container {{ Unsuccessful-PDSCHSetItemIE-PSCH-ReconfFailureTDD }}

Unsuccessful-PDSCHSetItemIE-PSCH-ReconfFailureTDD NBAP-PROTOCOL-IES ::= {
	{ ID	id-Unsuccessful-PDSCHSetItem-PSCH-ReconfFailureTDD	CRITICALITY ignore	TYPE Unsuccessful-PDSCHSetItem-PSCH-ReconfFailureTDD	PRESENCE mandatory}
}

Unsuccessful-PDSCHSetItem-PSCH-ReconfFailureTDD ::= SEQUENCE {
	pDSCHSet-ID				PDSCHSet-ID,
	cause					Cause,
	iE-Extensions			ProtocolExtensionContainer { {Unsuccessful-PDSCHSetItem-PSCH-ReconfFailureTDD-ExtIEs} }		OPTIONAL,
	...
}

Unsuccessful-PDSCHSetItem-PSCH-ReconfFailureTDD-ExtIEs NBAP-PROTOCOL-EXTENSION ::= {
	...
}

Unsuccessful-PUSCHSetList-PSCH-ReconfFailureTDD ::= SEQUENCE (SIZE (0.. maxNrOfPUSCHSets)) OF ProtocolIE-Single-Container {{ Unsuccessful-PUSCHSetItemIE-PSCH-ReconfFailureTDD }}

Unsuccessful-PUSCHSetItemIE-PSCH-ReconfFailureTDD NBAP-PROTOCOL-IES ::= {
	{ ID	id-Unsuccessful-PUSCHSetItem-PSCH-ReconfFailureTDD	CRITICALITY ignore	TYPE Unsuccessful-PUSCHSetItem-PSCH-ReconfFailureTDD	PRESENCE mandatory}
}

Unsuccessful-PUSCHSetItem-PSCH-ReconfFailureTDD ::= SEQUENCE {
	pUSCHSet-ID				PUSCHSet-ID,
	cause					Cause,
	iE-Extensions			ProtocolExtensionContainer { {Unsuccessful-PUSCHSetItem-PSCH-ReconfFailureTDD-ExtIEs} }		OPTIONAL,
	...
}

Unsuccessful-PUSCHSetItem-PSCH-ReconfFailureTDD-ExtIEs NBAP-PROTOCOL-EXTENSION ::= {
	...
}

Extension-CauseLevel-PSCH-ReconfFailure	::= ProtocolIE-Single-Container {{ Extension-CauseLevel-PSCH-ReconfFailureIE }}

Extension-CauseLevel-PSCH-ReconfFailureIE NBAP-PROTOCOL-IES ::= {
	{ ID id-UARFCNSpecificCauseList	CRITICALITY ignore	TYPE UARFCNSpecificCauseList-PSCH-ReconfFailureTDD	PRESENCE mandatory }
}

UARFCNSpecificCauseList-PSCH-ReconfFailureTDD ::= SEQUENCE (SIZE (0.. maxFrequencyinCell)) OF ProtocolIE-Single-Container {{ Unsuccessful-UARFCNItemIE-PSCH-ReconfFailureTDD }}

Unsuccessful-UARFCNItemIE-PSCH-ReconfFailureTDD NBAP-PROTOCOL-IES ::= {
	{ ID id-Unsuccessful-UARFCNItem-PSCH-ReconfFailureTDD	CRITICALITY ignore	TYPE Unsuccessful-UARFCNItem-PSCH-ReconfFailureTDD	PRESENCE mandatory }
}

Unsuccessful-UARFCNItem-PSCH-ReconfFailureTDD ::= SEQUENCE {
	uARFCN					UARFCN,
	-- Used for 1.28 Mcps TDD to indicate the carrier on which HSDPA or HSUPA resources configuration failure occurs.
	cause					Cause,
	iE-Extensions			ProtocolExtensionContainer { {Unsuccessful-UARFCNItem-PSCH-ReconfFailureTDD-ExtIEs} }		OPTIONAL,
	...
}

Unsuccessful-UARFCNItem-PSCH-ReconfFailureTDD-ExtIEs NBAP-PROTOCOL-EXTENSION ::= {
	{ ID	id-HS-Cause	CRITICALITY	ignore		EXTENSION	Cause		PRESENCE	optional}|
	-- Used to indicate the cause of HSDPA related configuration failure.
	{ ID	id-E-Cause	CRITICALITY	ignore		EXTENSION	Cause		PRESENCE	optional},
	-- Used to indicate the cause of E-DCH related configuration failure.
	...
}

-- **************************************************************
--
-- RESET REQUEST
--
-- **************************************************************

ResetRequest ::= SEQUENCE {
	protocolIEs				ProtocolIE-Container		{{ResetRequest-IEs}},
	protocolExtensions		ProtocolExtensionContainer	{{ResetRequest-Extensions}}		OPTIONAL,
	...
}

ResetRequest-IEs NBAP-PROTOCOL-IES ::= {
	{ID	id-ResetIndicator		CRITICALITY	ignore		TYPE 	ResetIndicator		PRESENCE 	mandatory},
	...
}

ResetRequest-Extensions NBAP-PROTOCOL-EXTENSION ::= {
	...
}

ResetIndicator ::= CHOICE {
	communicationContext			CommunicationContextList-Reset,
	communicationControlPort		CommunicationControlPortList-Reset,
	nodeB							NULL,
	...
}

CommunicationContextList-Reset ::= SEQUENCE {
	communicationContextInfoList-Reset		CommunicationContextInfoList-Reset,
	iE-Extensions							ProtocolExtensionContainer  { {CommunicationContextItem-Reset-ExtIEs} }		OPTIONAL,
	...
}

CommunicationContextItem-Reset-ExtIEs NBAP-PROTOCOL-EXTENSION ::= {
	...
}

CommunicationContextInfoList-Reset ::= SEQUENCE (SIZE (1.. maxCommunicationContext))	OF ProtocolIE-Single-Container {{ CommunicationContextInfoItemIE-Reset }}

CommunicationContextInfoItemIE-Reset NBAP-PROTOCOL-IES ::= {
	{ID id-CommunicationContextInfoItem-Reset		CRITICALITY reject		TYPE CommunicationContextInfoItem-Reset		PRESENCE mandatory}
}

CommunicationContextInfoItem-Reset ::= SEQUENCE {
	communicationContextType-Reset			CommunicationContextType-Reset,
	iE-Extensions							ProtocolExtensionContainer  { { CommunicationContextInfoItem-Reset-ExtIEs} }		OPTIONAL,
	...
}

CommunicationContextInfoItem-Reset-ExtIEs NBAP-PROTOCOL-EXTENSION ::= {
	...
}

CommunicationContextType-Reset ::= CHOICE {
	cRNC-CommunicationContextID				CRNC-CommunicationContextID,
	nodeB-CommunicationContextID			NodeB-CommunicationContextID,
	...
}

CommunicationControlPortList-Reset ::= SEQUENCE {
	communicationControlPortInfoList-Reset		CommunicationControlPortInfoList-Reset,
	iE-Extensions								ProtocolExtensionContainer  { {CommunicationControlPortItem-Reset-ExtIEs} }		OPTIONAL,
	...
}

CommunicationControlPortItem-Reset-ExtIEs NBAP-PROTOCOL-EXTENSION ::= {
	...
}

CommunicationControlPortInfoList-Reset ::= SEQUENCE (SIZE (1.. maxCCPinNodeB))	OF ProtocolIE-Single-Container {{CommunicationControlPortInfoItemIE-Reset }}

CommunicationControlPortInfoItemIE-Reset NBAP-PROTOCOL-IES ::= {
	{ID id-CommunicationControlPortInfoItem-Reset		CRITICALITY reject		TYPE CommunicationControlPortInfoItem-Reset		PRESENCE mandatory}
}

CommunicationControlPortInfoItem-Reset ::= SEQUENCE {
	communicationControlPortID			CommunicationControlPortID,
	iE-Extensions						ProtocolExtensionContainer { {CommunicationControlPortInfoItem-Reset-ExtIEs} }	OPTIONAL,
	...
}

CommunicationControlPortInfoItem-Reset-ExtIEs NBAP-PROTOCOL-EXTENSION ::= {
	...
}

-- **************************************************************
--
-- RESET RESPONSE
--
-- **************************************************************

ResetResponse ::= SEQUENCE {
	protocolIEs				ProtocolIE-Container		{{ResetResponse-IEs}},
	protocolExtensions		ProtocolExtensionContainer	{{ResetResponse-Extensions}}     		OPTIONAL,
	...
}

ResetResponse-IEs NBAP-PROTOCOL-IES ::= {
	{ID	id-CriticalityDiagnostics		CRITICALITY		ignore		TYPE	CriticalityDiagnostics		PRESENCE	optional},
	...
}

ResetResponse-Extensions NBAP-PROTOCOL-EXTENSION ::= {
	...
}

-- **************************************************************
--
-- INFORMATION EXCHANGE INITIATION REQUEST
--
-- **************************************************************

InformationExchangeInitiationRequest ::= SEQUENCE {
	protocolIEs				ProtocolIE-Container		{{InformationExchangeInitiationRequest-IEs}},
	protocolExtensions		ProtocolExtensionContainer	{{InformationExchangeInitiationRequest-Extensions}}		OPTIONAL,
	...
}

InformationExchangeInitiationRequest-IEs NBAP-PROTOCOL-IES ::= {
	{ ID id-InformationExchangeID						CRITICALITY	reject		TYPE InformationExchangeID					PRESENCE mandatory }|
	{ ID id-InformationExchangeObjectType-InfEx-Rqst	CRITICALITY	reject		TYPE InformationExchangeObjectType-InfEx-Rqst	PRESENCE mandatory }|
	{ ID id-InformationType								CRITICALITY	reject		TYPE InformationType					PRESENCE mandatory }|
	{ ID id-InformationReportCharacteristics			CRITICALITY	reject		TYPE InformationReportCharacteristics				PRESENCE mandatory },
	...
}

InformationExchangeInitiationRequest-Extensions NBAP-PROTOCOL-EXTENSION ::= {
	...
}

InformationExchangeObjectType-InfEx-Rqst ::= CHOICE {
	cell							Cell-InfEx-Rqst,
	...
}

Cell-InfEx-Rqst ::= SEQUENCE {
	c-ID							C-ID,
	iE-Extensions					ProtocolExtensionContainer  { { CellItem-InfEx-Rqst-ExtIEs} }		OPTIONAL,
	...
}

CellItem-InfEx-Rqst-ExtIEs NBAP-PROTOCOL-EXTENSION ::= {
	...
}

-- **************************************************************
--
-- INFORMATION EXCHANGE INITIATION RESPONSE
--
-- **************************************************************

InformationExchangeInitiationResponse ::= SEQUENCE {
	protocolIEs				ProtocolIE-Container		{{InformationExchangeInitiationResponse-IEs}},
	protocolExtensions		ProtocolExtensionContainer	{{InformationExchangeInitiationResponse-Extensions}}		OPTIONAL,
	...
}

InformationExchangeInitiationResponse-IEs NBAP-PROTOCOL-IES ::= {
	{ ID id-InformationExchangeID					CRITICALITY	ignore	TYPE InformationExchangeID		PRESENCE mandatory }|
	{ ID id-InformationExchangeObjectType-InfEx-Rsp	CRITICALITY	ignore	TYPE InformationExchangeObjectType-InfEx-Rsp	PRESENCE optional }|
	{ ID id-CriticalityDiagnostics					CRITICALITY	ignore	TYPE CriticalityDiagnostics		PRESENCE optional },
	...
}

InformationExchangeInitiationResponse-Extensions NBAP-PROTOCOL-EXTENSION ::= {
	...
}

InformationExchangeObjectType-InfEx-Rsp ::= CHOICE {
 	cell						Cell-InfEx-Rsp,
	...
 }

Cell-InfEx-Rsp ::= SEQUENCE {
 	requestedDataValue			    RequestedDataValue,
	iE-Extensions					ProtocolExtensionContainer  { { CellItem-InfEx-Rsp-ExtIEs} }		OPTIONAL,
	...
 }

CellItem-InfEx-Rsp-ExtIEs NBAP-PROTOCOL-EXTENSION ::= {
	...
}

-- **************************************************************
--
-- INFORMATION EXCHANGE INITIATION FAILURE
--
-- **************************************************************

InformationExchangeInitiationFailure ::= SEQUENCE {
	protocolIEs				ProtocolIE-Container		{{InformationExchangeInitiationFailure-IEs}},
	protocolExtensions		ProtocolExtensionContainer	{{InformationExchangeInitiationFailure-Extensions}}		OPTIONAL,
	...
}

InformationExchangeInitiationFailure-IEs NBAP-PROTOCOL-IES ::= {
	{ ID id-InformationExchangeID		CRITICALITY ignore			TYPE InformationExchangeID		PRESENCE	mandatory	}|
	{ ID id-Cause						CRITICALITY ignore			TYPE Cause						PRESENCE	mandatory	}|
	{ ID id-CriticalityDiagnostics		CRITICALITY ignore			TYPE CriticalityDiagnostics		PRESENCE	optional	},
	...
}

InformationExchangeInitiationFailure-Extensions NBAP-PROTOCOL-EXTENSION ::= {
	...
}

-- **************************************************************
--
-- INFORMATION REPORT
--
-- **************************************************************

InformationReport ::= SEQUENCE {
	protocolIEs				ProtocolIE-Container	{{InformationReport-IEs}},
	protocolExtensions		ProtocolExtensionContainer	{{InformationReport-Extensions}}		OPTIONAL,
	...
}

InformationReport-IEs NBAP-PROTOCOL-IES ::= {
	{ ID id-InformationExchangeID						CRITICALITY	ignore	TYPE InformationExchangeID				PRESENCE mandatory }|
	{ ID id-InformationExchangeObjectType-InfEx-Rprt	CRITICALITY	ignore	TYPE InformationExchangeObjectType-InfEx-Rprt		PRESENCE mandatory },
	...
}

InformationReport-Extensions NBAP-PROTOCOL-EXTENSION ::= {
	...
}

InformationExchangeObjectType-InfEx-Rprt ::= CHOICE {
	cell							Cell-Inf-Rprt,
	...
 }

Cell-Inf-Rprt ::= SEQUENCE {
	requestedDataValueInformation	RequestedDataValueInformation,
	iE-Extensions					ProtocolExtensionContainer  {{ CellItem-Inf-Rprt-ExtIEs }}		OPTIONAL,
	...

 }

CellItem-Inf-Rprt-ExtIEs NBAP-PROTOCOL-EXTENSION ::= {
	...
}

-- **************************************************************
--
-- INFORMATION EXCHANGE TERMINATION REQUEST
--
-- **************************************************************

InformationExchangeTerminationRequest ::= SEQUENCE {
	protocolIEs				ProtocolIE-Container		{{InformationExchangeTerminationRequest-IEs}},
	protocolExtensions		ProtocolExtensionContainer	{{InformationExchangeTerminationRequest-Extensions}}		OPTIONAL,
	...
}

InformationExchangeTerminationRequest-IEs NBAP-PROTOCOL-IES ::= {
	{ ID	id-InformationExchangeID			CRITICALITY		ignore				TYPE	InformationExchangeID			PRESENCE	mandatory},
	...
}

InformationExchangeTerminationRequest-Extensions NBAP-PROTOCOL-EXTENSION ::= {
	...
}

-- **************************************************************
--
-- INFORMATION EXCHANGE FAILURE INDICATION
--
-- **************************************************************

InformationExchangeFailureIndication ::= SEQUENCE {
	protocolIEs				ProtocolIE-Container			{{InformationExchangeFailureIndication-IEs}},
	protocolExtensions			ProtocolExtensionContainer	{{InformationExchangeFailureIndication-Extensions}}				OPTIONAL,
	...
}

InformationExchangeFailureIndication-IEs NBAP-PROTOCOL-IES ::= {
	{ ID id-InformationExchangeID	CRITICALITY ignore			TYPE InformationExchangeID		PRESENCE mandatory }|
	{ ID id-Cause					CRITICALITY ignore			TYPE Cause						PRESENCE mandatory },
	...
}

InformationExchangeFailureIndication-Extensions NBAP-PROTOCOL-EXTENSION ::= {
	...
}

-- **************************************************************
--
-- CELL SYNCHRONISATION INITIATION REQUEST TDD
--
-- **************************************************************

CellSynchronisationInitiationRequestTDD ::= SEQUENCE {
	protocolIEs				ProtocolIE-Container		{{CellSynchronisationInitiationRequestTDD-IEs}},
	protocolExtensions		ProtocolExtensionContainer	{{CellSynchronisationInitiationRequestTDD-Extensions}}     OPTIONAL,
	...
}

CellSynchronisationInitiationRequestTDD-IEs NBAP-PROTOCOL-IES ::= {
	{ ID	id-C-ID							CRITICALITY		reject		TYPE	C-ID							PRESENCE	mandatory	}|
	{ ID	id-cellSyncBurstRepetitionPeriod			CRITICALITY		reject		TYPE	CellSyncBurstRepetitionPeriod		PRESENCE	mandatory	}|
	{ ID	id-timeslotInfo-CellSyncInitiationRqstTDD	CRITICALITY 	reject		TYPE	TimeslotInfo-CellSyncInitiationRqstTDD		PRESENCE 	optional	}|	-- Mandatory for 3.84Mcps TDD. Not Applicable to 1.28Mcps TDD.
	{ ID	id-CellSyncBurstTransInit-CellSyncInitiationRqstTDD		CRITICALITY 	reject		TYPE	CellSyncBurstTransInit-CellSyncInitiationRqstTDD		PRESENCE 	optional	}|	-- Applicable to 3.84Mcps TDD only
	{ ID	id-CellSyncBurstMeasureInit-CellSyncInitiationRqstTDD		CRITICALITY 	reject		TYPE	CellSyncBurstMeasureInit-CellSyncInitiationRqstTDD		PRESENCE 	optional	},	-- Applicable to 3.84Mcps TDD only
	...
}

CellSynchronisationInitiationRequestTDD-Extensions NBAP-PROTOCOL-EXTENSION ::= {
	{ ID id-SYNCDlCodeId-TransInitLCR-CellSyncInitiationRqstTDD		CRITICALITY reject	EXTENSION SYNCDlCodeId-TransInitLCR-CellSyncInitiationRqstTDD	PRESENCE optional }|	-- Applicable to 1.28Mcps TDD only
	{ ID id-SYNCDlCodeId-MeasureInitLCR-CellSyncInitiationRqstTDD	CRITICALITY reject	EXTENSION SYNCDlCodeId-MeasureInitLCR-CellSyncInitiationRqstTDD	PRESENCE optional },	-- Applicable to 1.28Mcps TDD only
	...
}

TimeslotInfo-CellSyncInitiationRqstTDD::= SEQUENCE (SIZE (1..15)) OF TimeSlot

CellSyncBurstTransInit-CellSyncInitiationRqstTDD::= SEQUENCE {
	cSBTransmissionID						CSBTransmissionID,
	sfn										SFN,
	cellSyncBurstCode						CellSyncBurstCode,
	cellSyncBurstCodeShift					CellSyncBurstCodeShift,
	initialDLTransPower						DL-Power,
	iE-Extensions							ProtocolExtensionContainer { { CellSyncBurstTransInit-CellSyncInitiationRqstTDD-ExtIEs} }		OPTIONAL,
	...
}

CellSyncBurstTransInit-CellSyncInitiationRqstTDD-ExtIEs NBAP-PROTOCOL-EXTENSION ::= {
	...
}

CellSyncBurstMeasureInit-CellSyncInitiationRqstTDD::= SEQUENCE {
	cSBMeasurementID						CSBMeasurementID,
	cellSyncBurstCode						CellSyncBurstCode,
	cellSyncBurstCodeShift					CellSyncBurstCodeShift,
	synchronisationReportType				SynchronisationReportType,
	sfn										SFN										OPTIONAL,
	synchronisationReportCharacteristics	SynchronisationReportCharacteristics,
	iE-Extensions							ProtocolExtensionContainer { { CellSyncBurstMeasureInit-CellSyncInitiationRqstTDD-ExtIEs} }		OPTIONAL,
	...
 }

CellSyncBurstMeasureInit-CellSyncInitiationRqstTDD-ExtIEs NBAP-PROTOCOL-EXTENSION ::= {
	...
}

SYNCDlCodeId-TransInitLCR-CellSyncInitiationRqstTDD::= SEQUENCE {
	cSBTransmissionID						CSBTransmissionID,
	sfn										SFN,
	uARFCN									UARFCN,
	sYNCDlCodeId							SYNCDlCodeId,
	dwPCH-Power								DwPCH-Power,
	iE-Extensions							ProtocolExtensionContainer { { SYNCDlCodeId-TransInitLCR-CellSyncInitiationRqstTDD-ExtIEs } }	OPTIONAL,
	...
}

SYNCDlCodeId-TransInitLCR-CellSyncInitiationRqstTDD-ExtIEs NBAP-PROTOCOL-EXTENSION ::= {
	...
}

SYNCDlCodeId-MeasureInitLCR-CellSyncInitiationRqstTDD::= SEQUENCE {
	cSBMeasurementID						CSBMeasurementID,
	sfn										SFN										OPTIONAL,
	uARFCN									UARFCN,
	sYNCDlCodeId							SYNCDlCodeId,
	synchronisationReportType				SynchronisationReportType,
	synchronisationReportCharacteristics	SynchronisationReportCharacteristics,
	iE-Extensions							ProtocolExtensionContainer { { SYNCDlCodeId-MeasureInitLCR-CellSyncInitiationRqstTDD-ExtIEs } }	OPTIONAL,
	...
}

SYNCDlCodeId-MeasureInitLCR-CellSyncInitiationRqstTDD-ExtIEs NBAP-PROTOCOL-EXTENSION ::= {
	...
}

-- **************************************************************
--
-- CELL SYNCHRONISATION INITIATION RESPONSE TDD
--
-- **************************************************************

CellSynchronisationInitiationResponseTDD ::= SEQUENCE {
	protocolIEs				ProtocolIE-Container		{{CellSynchronisationInitiationResponseTDD-IEs}},
	protocolExtensions		ProtocolExtensionContainer	{{CellSynchronisationInitiationResponseTDD-Extensions}}     OPTIONAL,
	...
}

CellSynchronisationInitiationResponseTDD-Extensions NBAP-PROTOCOL-EXTENSION ::= {
	...
}

CellSynchronisationInitiationResponseTDD-IEs NBAP-PROTOCOL-IES ::= {
	{ ID id-CriticalityDiagnostics			CRITICALITY ignore		TYPE CriticalityDiagnostics			PRESENCE optional },
	...
}

-- **************************************************************
--
-- CELL SYNCHRONISATION INITIATION FAILURE TDD
--
-- **************************************************************

CellSynchronisationInitiationFailureTDD ::= SEQUENCE {
	protocolIEs				ProtocolIE-Container		{{CellSynchronisationInitiationFailureTDD-IEs}},
	protocolExtensions		ProtocolExtensionContainer	{{CellSynchronisationInitiationFailureTDD-Extensions}}     OPTIONAL,
	...
}

CellSynchronisationInitiationFailureTDD-Extensions NBAP-PROTOCOL-EXTENSION ::= {
	...
}

CellSynchronisationInitiationFailureTDD-IEs NBAP-PROTOCOL-IES ::= {
	{ ID id-Cause							CRITICALITY ignore		TYPE Cause						PRESENCE mandatory }|
	{ ID id-CriticalityDiagnostics			CRITICALITY ignore		TYPE CriticalityDiagnostics		PRESENCE optional },
	...
}

-- **************************************************************
--
-- CELL SYNCHRONISATION RECONFIGURATION REQUEST TDD
--
-- **************************************************************

CellSynchronisationReconfigurationRequestTDD ::= SEQUENCE {
	protocolIEs				ProtocolIE-Container		{{CellSynchronisationReconfigurationRequestTDD-IEs}},
	protocolExtensions		ProtocolExtensionContainer	{{CellSynchronisationReconfigurationRequestTDD-Extensions}}     OPTIONAL,
	...
}

CellSynchronisationReconfigurationRequestTDD-IEs NBAP-PROTOCOL-IES ::= {
	{ ID	id-C-ID							CRITICALITY		reject		TYPE	C-ID							PRESENCE		mandatory	}|
	{ ID	id-TimeSlot						CRITICALITY		reject		TYPE	TimeSlot						PRESENCE 	mandatory	}|
	-- Applicable to 3.84Mcps TDD only. For 1.28Mcps TDD, the CRNC should set this to 0 and the Node B shall ignore it.
	{ ID	id-NCyclesPerSFNperiod			CRITICALITY		reject		TYPE	NCyclesPerSFNperiod			PRESENCE 	mandatory	}|
	{ ID	id-NRepetitionsPerCyclePeriod	CRITICALITY		reject		TYPE	NRepetitionsPerCyclePeriod PRESENCE 	mandatory	}|
	{ ID	id-CellSyncBurstTransReconfInfo-CellSyncReconfRqstTDD		CRITICALITY 	reject		TYPE	CellSyncBurstTransReconfInfo-CellSyncReconfRqstTDD		PRESENCE 	optional	}|	-- Applicable to 3.84Mcps TDD only
	{ ID	id-CellSyncBurstMeasReconfiguration-CellSyncReconfRqstTDD		CRITICALITY 	reject		TYPE	CellSyncBurstMeasInfo-CellSyncReconfRqstTDD		PRESENCE 	optional	},	-- Applicable to 3.84Mcps TDD only
	...
}

CellSynchronisationReconfigurationRequestTDD-Extensions NBAP-PROTOCOL-EXTENSION ::= {
	{ ID id-NSubCyclesPerCyclePeriod-CellSyncReconfRqstTDD				CRITICALITY reject	EXTENSION	NSubCyclesPerCyclePeriod										PRESENCE optional }|	-- Applicable to 1.28Mcps TDD only
	{ ID id-SYNCDlCodeIdTransReconfInfoLCR-CellSyncReconfRqstTDD			CRITICALITY reject	EXTENSION	SYNCDlCodeIdTransReconfInfoLCR-CellSyncReconfRqstTDD			PRESENCE optional }|	-- Applicable to 1.28Mcps TDD only
	{ ID id-SYNCDlCodeIdMeasReconfigurationLCR-CellSyncReconfRqstTDD		CRITICALITY reject	EXTENSION	SYNCDlCodeIdMeasInfoLCR-CellSyncReconfRqstTDD		PRESENCE optional },	-- Applicable to 1.28Mcps TDD only
	...
}

CellSyncBurstTransReconfInfo-CellSyncReconfRqstTDD ::= SEQUENCE (SIZE (1.. maxNrOfCellSyncBursts)) OF CellSyncBurstTransInfoItem-CellSyncReconfRqstTDD

CellSyncBurstTransInfoItem-CellSyncReconfRqstTDD ::= SEQUENCE {
	cSBTransmissionID							CSBTransmissionID,
	syncFrameNumberToTransmit					SyncFrameNumber,
	cellSyncBurstCode							CellSyncBurstCode			OPTIONAL,
	cellSyncBurstCodeShift						CellSyncBurstCodeShift		OPTIONAL,
	dlTransPower								DL-Power					OPTIONAL,
	iE-Extensions								ProtocolExtensionContainer { { CellSyncBurstTransInfoItem-CellSyncReconfRqstTDD-ExtIEs} }		OPTIONAL,
	...
}

CellSyncBurstTransInfoItem-CellSyncReconfRqstTDD-ExtIEs NBAP-PROTOCOL-EXTENSION ::= {
	...
}


CellSyncBurstMeasInfo-CellSyncReconfRqstTDD ::= SEQUENCE {
	cellSyncBurstMeasInfoList-CellSyncReconfRqstTDD		CellSyncBurstMeasInfoList-CellSyncReconfRqstTDD,
	synchronisationReportType							SynchronisationReportTypeIE				OPTIONAL,
	synchronisationReportCharacteristics				SynchronisationReportCharacteristicsIE	OPTIONAL,
	iE-Extensions										ProtocolExtensionContainer { { CellSyncBurstMeasInfo-CellSyncReconfRqstTDD-ExtIEs} }		OPTIONAL,
	...
}

CellSyncBurstMeasInfo-CellSyncReconfRqstTDD-ExtIEs NBAP-PROTOCOL-EXTENSION ::= {
	...
}

CellSyncBurstMeasInfoList-CellSyncReconfRqstTDD ::= ProtocolIE-Single-Container {{ CellSyncBurstMeasInfoListIEs-CellSyncReconfRqstTDD }}

CellSyncBurstMeasInfoListIEs-CellSyncReconfRqstTDD NBAP-PROTOCOL-IES ::= {
	{ ID id-CellSyncBurstMeasInfoList-CellSyncReconfRqstTDD   CRITICALITY reject	TYPE CellSyncBurstMeasInfoListIE-CellSyncReconfRqstTDD		PRESENCE mandatory }
}

SynchronisationReportTypeIE ::= ProtocolIE-Single-Container {{ SynchronisationReportTypeIEs }}

SynchronisationReportTypeIEs NBAP-PROTOCOL-IES ::= {
	{ ID id-SynchronisationReportType					CRITICALITY reject	TYPE SynchronisationReportType			 				PRESENCE	mandatory }
}

SynchronisationReportCharacteristicsIE ::= ProtocolIE-Single-Container {{ SynchronisationReportCharacteristicsIEs }}

SynchronisationReportCharacteristicsIEs NBAP-PROTOCOL-IES ::= {
	{ ID id-SynchronisationReportCharacteristics		CRITICALITY reject	TYPE SynchronisationReportCharacteristics		 	PRESENCE	mandatory }
}


CellSyncBurstMeasInfoListIE-CellSyncReconfRqstTDD ::= SEQUENCE (SIZE (1.. maxNrOfCellSyncBursts)) OF CellSyncBurstMeasInfoItem-CellSyncReconfRqstTDD

CellSyncBurstMeasInfoItem-CellSyncReconfRqstTDD ::= SEQUENCE {
	syncFrameNrToReceive					SyncFrameNumber,
	syncBurstInfo							CellSyncBurstInfoList-CellSyncReconfRqstTDD,
	iE-Extensions							ProtocolExtensionContainer { { CellSyncBurstMeasInfoItem-CellSyncReconfRqstTDD-ExtIEs} }		OPTIONAL,
	...
}

CellSyncBurstMeasInfoItem-CellSyncReconfRqstTDD-ExtIEs NBAP-PROTOCOL-EXTENSION ::= {
	...
}

CellSyncBurstInfoList-CellSyncReconfRqstTDD ::= SEQUENCE (SIZE (1..maxNrOfReceptsPerSyncFrame)) OF CellSyncBurstInfoItem-CellSyncReconfRqstTDD

CellSyncBurstInfoItem-CellSyncReconfRqstTDD ::= SEQUENCE {
	cSBMeasurementID							CSBMeasurementID,
	cellSyncBurstCode							CellSyncBurstCode,
	cellSyncBurstCodeShift						CellSyncBurstCodeShift,
	iE-Extensions								ProtocolExtensionContainer { { CellSyncBurstInfoItem-CellSyncReconfRqstTDD-ExtIEs} }		OPTIONAL,
	...
}

CellSyncBurstInfoItem-CellSyncReconfRqstTDD-ExtIEs NBAP-PROTOCOL-EXTENSION ::= {
	...
}

SYNCDlCodeIdTransReconfInfoLCR-CellSyncReconfRqstTDD ::= SEQUENCE (SIZE (1..maxNrOfSyncFramesLCR)) OF SYNCDlCodeIdTransReconfItemLCR-CellSyncReconfRqstTDD

SYNCDlCodeIdTransReconfItemLCR-CellSyncReconfRqstTDD ::= SEQUENCE {
	cSBTransmissionID							CSBTransmissionID,
	syncFrameNumberforTransmit					SyncFrameNumber,
	uARFCN										UARFCN,
	sYNCDlCodeId								SYNCDlCodeId	OPTIONAL,
	dwPCH-Power									DwPCH-Power		OPTIONAL,
	iE-Extensions								ProtocolExtensionContainer { { SYNCDlCodeIdTransReconfInfoLCR-CellSyncReconfRqstTDD-ExtIEs} }		OPTIONAL,
	...
}

SYNCDlCodeIdTransReconfInfoLCR-CellSyncReconfRqstTDD-ExtIEs NBAP-PROTOCOL-EXTENSION ::= {
	...
}


SYNCDlCodeIdMeasInfoLCR-CellSyncReconfRqstTDD::= SEQUENCE {

	sYNCDlCodeIdMeasInfoList					SYNCDlCodeIdMeasInfoList-CellSyncReconfRqstTDD,
	synchronisationReportType					SynchronisationReportType						OPTIONAL,
	synchronisationReportCharacteristics		SynchronisationReportCharacteristics   		OPTIONAL,
	iE-Extensions		ProtocolExtensionContainer	 { { SYNCDlCodeIdMeasInfoLCR-CellSyncReconfRqstTDD-ExtIEs} } OPTIONAL,
	...
}

SYNCDlCodeIdMeasInfoLCR-CellSyncReconfRqstTDD-ExtIEs NBAP-PROTOCOL-EXTENSION ::= {
	...
}

SYNCDlCodeIdMeasInfoList-CellSyncReconfRqstTDD::= SEQUENCE (SIZE (1.. maxNrOfSyncDLCodesLCR)) OF SYNCDlCodeIdMeasInfoItem-CellSyncReconfRqstTDD

SYNCDlCodeIdMeasInfoItem-CellSyncReconfRqstTDD ::= SEQUENCE {
	syncFrameNrToReceive					SyncFrameNumber,
	sYNCDlCodeIdInfoLCR						SYNCDlCodeIdInfoListLCR-CellSyncReconfRqstTDD,
	iE-Extensions							ProtocolExtensionContainer { { SYNCDlCodeIdMeasInfoItem-CellSyncReconfRqstTDD-ExtIEs} }		OPTIONAL,
	...
}

SYNCDlCodeIdMeasInfoItem-CellSyncReconfRqstTDD-ExtIEs NBAP-PROTOCOL-EXTENSION ::= {
	...
}

SYNCDlCodeIdInfoListLCR-CellSyncReconfRqstTDD ::= SEQUENCE (SIZE (1.. maxNrOfReceptionsperSyncFrameLCR)) OF SYNCDlCodeIdInfoItemLCR-CellSyncReconfRqstTDD

SYNCDlCodeIdInfoItemLCR-CellSyncReconfRqstTDD ::= SEQUENCE {
	cSBMeasurementID							CSBMeasurementID,
	sYNCDlCodeId								SYNCDlCodeId,
	uARFCN										UARFCN,
	propagationDelayCompensation				TimingAdjustmentValueLCR		OPTIONAL,
	iE-Extensions								ProtocolExtensionContainer { { SYNCDlCodeIdInfoItemLCR-CellSyncReconfRqstTDD-ExtIEs} }		OPTIONAL,
	...
}

SYNCDlCodeIdInfoItemLCR-CellSyncReconfRqstTDD-ExtIEs NBAP-PROTOCOL-EXTENSION ::= {
	...
}

-- **************************************************************
--
-- CELL SYNCHRONISATION RECONFIGURATION RESPONSE TDD
--
-- **************************************************************

CellSynchronisationReconfigurationResponseTDD ::= SEQUENCE {
	protocolIEs				ProtocolIE-Container		{{CellSynchronisationReconfigurationResponseTDD-IEs}},
	protocolExtensions		ProtocolExtensionContainer	{{CellSynchronisationReconfigurationResponseTDD-Extensions}}     OPTIONAL,
	...
}

CellSynchronisationReconfigurationResponseTDD-Extensions NBAP-PROTOCOL-EXTENSION ::= {
	...
}

CellSynchronisationReconfigurationResponseTDD-IEs NBAP-PROTOCOL-IES ::= {
	{ ID	id-CriticalityDiagnostics					CRITICALITY		ignore		TYPE	CriticalityDiagnostics			PRESENCE	optional	},
	...
}

-- **************************************************************
--
-- CELL SYNCHRONISATION RECONFIGURATION FAILURE TDD
--
-- **************************************************************

CellSynchronisationReconfigurationFailureTDD ::= SEQUENCE {
	protocolIEs				ProtocolIE-Container		{{CellSynchronisationReconfigurationFailureTDD-IEs}},
	protocolExtensions		ProtocolExtensionContainer	{{CellSynchronisationReconfigurationFailureTDD-Extensions}}     OPTIONAL,
	...
}

CellSynchronisationReconfigurationFailureTDD-Extensions NBAP-PROTOCOL-EXTENSION ::= {
	...
}

CellSynchronisationReconfigurationFailureTDD-IEs NBAP-PROTOCOL-IES ::= {
	{ ID id-Cause							CRITICALITY ignore		TYPE Cause						PRESENCE mandatory }|
	{ ID id-CriticalityDiagnostics			CRITICALITY ignore		TYPE CriticalityDiagnostics		PRESENCE optional },
	...
}

-- **************************************************************
--
-- CELL SYNCHRONISATION ADJUSTMENT REQUEST TDD
--
-- **************************************************************

CellSynchronisationAdjustmentRequestTDD ::= SEQUENCE {
	protocolIEs				ProtocolIE-Container		{{CellSynchronisationAdjustmentRequestTDD-IEs}},
	protocolExtensions		ProtocolExtensionContainer	{{CellSynchronisationAdjustmentRequestTDD-Extensions}}     OPTIONAL,
	...
}

CellSynchronisationAdjustmentRequestTDD-Extensions NBAP-PROTOCOL-EXTENSION ::= {
	...
}

CellSynchronisationAdjustmentRequestTDD-IEs NBAP-PROTOCOL-IES ::= {
	{ ID	id-CellAdjustmentInfo-SyncAdjustmntRqstTDD	CRITICALITY	ignore	TYPE CellAdjustmentInfo-SyncAdjustmentRqstTDD	PRESENCE mandatory	},
	...
}

CellAdjustmentInfo-SyncAdjustmentRqstTDD::= SEQUENCE (SIZE (1..maxCellinNodeB)) OF ProtocolIE-Single-Container {{ CellAdjustmentInfoItemIE-SyncAdjustmntRqstTDD }}

CellAdjustmentInfoItemIE-SyncAdjustmntRqstTDD NBAP-PROTOCOL-IES ::= {
	{ ID id-CellAdjustmentInfoItem-SyncAdjustmentRqstTDD	CRITICALITY ignore	TYPE CellAdjustmentInfoItem-SyncAdjustmentRqstTDD	PRESENCE mandatory }
}

CellAdjustmentInfoItem-SyncAdjustmentRqstTDD ::= SEQUENCE {
	c-ID									C-ID,
	frameAdjustmentValue					FrameAdjustmentValue		OPTIONAL,
	timingAdjustmentValue					TimingAdjustmentValue		OPTIONAL,
	dLTransPower							DL-Power					OPTIONAL, -- Applicable to 3.84Mcps TDD only
	sfn										SFN							OPTIONAL,
	iE-Extensions							ProtocolExtensionContainer { { CellAdjustmentInfoItem-SyncAdjustmntRqstTDD-ExtIEs} }		OPTIONAL,
	...
 }

CellAdjustmentInfoItem-SyncAdjustmntRqstTDD-ExtIEs NBAP-PROTOCOL-EXTENSION ::= {
	{ ID id-DwPCH-Power					CRITICALITY ignore	EXTENSION DwPCH-Power				PRESENCE optional }|
	-- Applicable to 1.28Mcps TDD only
	{ ID id-TimingAdjustmentValueLCR	CRITICALITY ignore	EXTENSION TimingAdjustmentValueLCR	PRESENCE optional },
	-- Applicable to 1.28Mcps TDD only
	...
}

-- **************************************************************
--
-- CELL SYNCHRONISATION ADJUSTMENT RESPONSE TDD
--
-- **************************************************************

CellSynchronisationAdjustmentResponseTDD ::= SEQUENCE {
	protocolIEs				ProtocolIE-Container		{{CellSynchronisationAdjustmentResponseTDD-IEs}},
	protocolExtensions		ProtocolExtensionContainer	{{CellSynchronisationAdjustmentResponseTDD-Extensions}}     OPTIONAL,
	...
}

CellSynchronisationAdjustmentResponseTDD-Extensions NBAP-PROTOCOL-EXTENSION ::= {
	...
}

CellSynchronisationAdjustmentResponseTDD-IEs NBAP-PROTOCOL-IES ::= {
	{ ID	id-CriticalityDiagnostics			CRITICALITY		ignore		TYPE	CriticalityDiagnostics					PRESENCE	optional	},
	...
}

-- **************************************************************
--
-- CELL SYNCHRONISATION ADJUSTMENT FAILURE TDD
--
-- **************************************************************

CellSynchronisationAdjustmentFailureTDD ::= SEQUENCE {
	protocolIEs				ProtocolIE-Container		{{CellSynchronisationAdjustmentFailureTDD-IEs}},
	protocolExtensions		ProtocolExtensionContainer	{{CellSynchronisationAdjustmentFailureTDD-Extensions}}     OPTIONAL,
	...
}

CellSynchronisationAdjustmentFailureTDD-Extensions NBAP-PROTOCOL-EXTENSION ::= {
	...
}

CellSynchronisationAdjustmentFailureTDD-IEs NBAP-PROTOCOL-IES ::= {
	{ ID	id-CauseLevel-SyncAdjustmntFailureTDD	CRITICALITY	ignore		TYPE	CauseLevel-SyncAdjustmntFailureTDD		PRESENCE	mandatory	}|
	{ ID	id-CriticalityDiagnostics				CRITICALITY	ignore		TYPE	CriticalityDiagnostics			PRESENCE	optional	},
	...
}

CauseLevel-SyncAdjustmntFailureTDD ::= CHOICE {
	generalCause			GeneralCauseList-SyncAdjustmntFailureTDD,
	cellSpecificCause		CellSpecificCauseList-SyncAdjustmntFailureTDD,
	...
}

GeneralCauseList-SyncAdjustmntFailureTDD::= SEQUENCE {
	cause										Cause,
	iE-Extensions								ProtocolExtensionContainer { { GeneralCauseList-SyncAdjustmntFailureTDD-ExtIEs} }		OPTIONAL,
	...
}

GeneralCauseList-SyncAdjustmntFailureTDD-ExtIEs NBAP-PROTOCOL-EXTENSION ::= {
	...
}

CellSpecificCauseList-SyncAdjustmntFailureTDD ::= SEQUENCE {
	unsuccessful-cell-InformationRespList-SyncAdjustmntFailureTDD		Unsuccessful-cell-InformationRespList-SyncAdjustmntFailureTDD,
	iE-Extensions								ProtocolExtensionContainer { { CellSpecificCauseList-SyncAdjustmntFailureTDD-ExtIEs} }		OPTIONAL,
	...
}

CellSpecificCauseList-SyncAdjustmntFailureTDD-ExtIEs NBAP-PROTOCOL-EXTENSION ::= {
	...
}

Unsuccessful-cell-InformationRespList-SyncAdjustmntFailureTDD ::= SEQUENCE (SIZE (1..maxCellinNodeB))	OF ProtocolIE-Single-Container {{ Unsuccessful-cell-InformationRespItemIE-SyncAdjustmntFailureTDD }}

Unsuccessful-cell-InformationRespItemIE-SyncAdjustmntFailureTDD NBAP-PROTOCOL-IES ::= {
	{ ID	id-Unsuccessful-cell-InformationRespItem-SyncAdjustmntFailureTDD		CRITICALITY		ignore		TYPE	Unsuccessful-cell-InformationRespItem-SyncAdjustmntFailureTDD		PRESENCE	mandatory},
	...
}

Unsuccessful-cell-InformationRespItem-SyncAdjustmntFailureTDD::= SEQUENCE {
	c-ID										C-ID,
	cause										Cause,
	iE-Extensions								ProtocolExtensionContainer { { Unsuccessful-cell-InformationRespItem-SyncAdjustmntFailureTDD-ExtIEs} }		OPTIONAL,
	...
}

Unsuccessful-cell-InformationRespItem-SyncAdjustmntFailureTDD-ExtIEs NBAP-PROTOCOL-EXTENSION ::= {
	...
}

-- **************************************************************
--
-- CELL SYNCHRONISATION TERMINATION REQUEST TDD
--
-- **************************************************************

CellSynchronisationTerminationRequestTDD ::= SEQUENCE {
	protocolIEs				ProtocolIE-Container		{{CellSynchronisationTerminationRequestTDD-IEs}},
	protocolExtensions		ProtocolExtensionContainer	{{CellSynchronisationTerminationRequestTDD-Extensions}}     OPTIONAL,
	...
}

CellSynchronisationTerminationRequestTDD-Extensions NBAP-PROTOCOL-EXTENSION ::= {
	...
}

CellSynchronisationTerminationRequestTDD-IEs NBAP-PROTOCOL-IES ::= {
	{ ID	id-C-ID							CRITICALITY		ignore		TYPE	C-ID							PRESENCE	mandatory	}|
	{ ID	id-CSBTransmissionID			CRITICALITY		ignore		TYPE	CSBTransmissionID				PRESENCE	optional		}|
	{ ID	id-CSBMeasurementID				CRITICALITY		ignore		TYPE	CSBMeasurementID				PRESENCE	optional		},
	...
}

-- **************************************************************
--
-- CELL SYNCHRONISATION FAILURE INDICATION TDD
--
-- **************************************************************

CellSynchronisationFailureIndicationTDD ::= SEQUENCE {
	protocolIEs				ProtocolIE-Container		{{CellSynchronisationFailureIndicationTDD-IEs}},
	protocolExtensions		ProtocolExtensionContainer	{{CellSynchronisationFailureIndicationTDD-Extensions}}     OPTIONAL,
	...
}

CellSynchronisationFailureIndicationTDD-Extensions NBAP-PROTOCOL-EXTENSION ::= {
	...
}

CellSynchronisationFailureIndicationTDD-IEs NBAP-PROTOCOL-IES ::= {
	{ ID	id-C-ID							CRITICALITY		ignore		TYPE	C-ID							PRESENCE	mandatory	}|
	{ ID	id-CSBTransmissionID			CRITICALITY		ignore		TYPE	CSBTransmissionID				PRESENCE	optional		}|
	{ ID	id-CSBMeasurementID				CRITICALITY		ignore		TYPE	CSBMeasurementID				PRESENCE	optional		}|
	{ ID	id-Cause						CRITICALITY		ignore		TYPE	Cause							PRESENCE	mandatory	},
	...
}

-- **************************************************************
--
-- CELL SYNCHRONISATION REPORT TDD
--
-- **************************************************************

CellSynchronisationReportTDD ::= SEQUENCE {
	protocolIEs				ProtocolIE-Container		{{CellSynchronisationReportTDD-IEs}},
	protocolExtensions		ProtocolExtensionContainer	{{CellSynchronisationReportTDD-Extensions}}     OPTIONAL,
	...
}

CellSynchronisationReportTDD-Extensions NBAP-PROTOCOL-EXTENSION ::= {
	...
}

CellSynchronisationReportTDD-IEs NBAP-PROTOCOL-IES ::= {
	{ ID id-CellSyncInfo-CellSyncReprtTDD		CRITICALITY ignore		TYPE CellSyncInfo-CellSyncReprtTDD			PRESENCE mandatory },
	...
}

CellSyncInfo-CellSyncReprtTDD ::= SEQUENCE (SIZE (1..maxCellinNodeB))	OF CellSyncInfoItemIE-CellSyncReprtTDD

CellSyncInfoItemIE-CellSyncReprtTDD ::= SEQUENCE {
	c-ID-CellSyncReprtTDD				C-ID-IE-CellSyncReprtTDD,
	syncReportType-CellSyncReprtTDD		SyncReportTypeIE-CellSyncReprtTDD		OPTIONAL,
	...
}

C-ID-IE-CellSyncReprtTDD ::= ProtocolIE-Single-Container {{ C-ID-IEs-CellSyncReprtTDD }}

C-ID-IEs-CellSyncReprtTDD NBAP-PROTOCOL-IES ::= {
	{ ID id-C-ID						CRITICALITY ignore			TYPE C-ID					PRESENCE mandatory }
}

SyncReportTypeIE-CellSyncReprtTDD::= ProtocolIE-Single-Container {{ SyncReportTypeIEs-CellSyncReprtTDD }}

SyncReportTypeIEs-CellSyncReprtTDD NBAP-PROTOCOL-IES ::= {
	{ ID	id-SyncReportType-CellSyncReprtTDD		CRITICALITY	ignore		TYPE SyncReportType-CellSyncReprtTDD		PRESENCE	mandatory}
}


SyncReportType-CellSyncReprtTDD ::= CHOICE {
	intStdPhSyncInfo-CellSyncReprtTDD		IntStdPhCellSyncInfo-CellSyncReprtTDD,
	lateEntrantCell							NULL,
	frequencyAcquisition					NULL,
	...
}

IntStdPhCellSyncInfo-CellSyncReprtTDD ::= SEQUENCE {
	cellSyncBurstMeasuredInfo					CellSyncBurstMeasInfoList-CellSyncReprtTDD,
	iE-Extensions								ProtocolExtensionContainer { { IntStdPhCellSyncInfoList-CellSyncReprtTDD-ExtIEs} }		OPTIONAL,
	...
}

IntStdPhCellSyncInfoList-CellSyncReprtTDD-ExtIEs NBAP-PROTOCOL-EXTENSION ::= {
	{ ID id-AccumulatedClockupdate-CellSyncReprtTDD		CRITICALITY	ignore	EXTENSION	TimingAdjustmentValue	PRESENCE	optional	}|
	{ ID id-SyncDLCodeIdsMeasInfoList-CellSyncReprtTDD 	CRITICALITY	ignore EXTENSION	SyncDLCodeIdsMeasInfoList-CellSyncReprtTDD	PRESENCE optional }, -- Mandatory for 1.28Mcps TDD. Not Applicable to 3.84Mcps TDD.
	...
}

CellSyncBurstMeasInfoList-CellSyncReprtTDD ::= SEQUENCE (SIZE (0.. maxNrOfCellSyncBursts)) OF CellSyncBurstMeasInfoItem-CellSyncReprtTDD -- Mandatory for 3.84Mcps TDD. Not Applicable to 1.28Mcps TDD.

CellSyncBurstMeasInfoItem-CellSyncReprtTDD ::= SEQUENCE {
	sFN										SFN,
	cellSyncBurstInfo-CellSyncReprtTDD		SEQUENCE (SIZE (1..maxNrOfReceptsPerSyncFrame)) OF CellSyncBurstInfo-CellSyncReprtTDD,
	iE-Extensions							ProtocolExtensionContainer { { CellSyncBurstMeasInfoItem-CellSyncReprtTDD-ExtIEs} }		OPTIONAL,
	...
}

CellSyncBurstMeasInfoItem-CellSyncReprtTDD-ExtIEs NBAP-PROTOCOL-EXTENSION ::= {
	...
}

CellSyncBurstInfo-CellSyncReprtTDD ::= CHOICE {
	cellSyncBurstAvailable		CellSyncBurstAvailable-CellSyncReprtTDD,
	cellSyncBurstNotAvailable	NULL,
	...
}

CellSyncBurstAvailable-CellSyncReprtTDD ::= SEQUENCE {
	cellSyncBurstTiming			CellSyncBurstTiming,
	cellSyncBurstSIR			CellSyncBurstSIR,
	iE-Extensions				ProtocolExtensionContainer { { CellSyncBurstAvailable-CellSyncReprtTDD-ExtIEs} }		OPTIONAL,
	...
}

CellSyncBurstAvailable-CellSyncReprtTDD-ExtIEs NBAP-PROTOCOL-EXTENSION ::= {
	...
}

SyncDLCodeIdsMeasInfoList-CellSyncReprtTDD ::= SEQUENCE (SIZE (0..maxNrOfSyncFramesLCR)) OF SyncDLCodeIdsMeasInfoItem-CellSyncReprtTDD
-- Mandatory for 1.28Mcps TDD. Not Applicable to 3.84Mcps TDD.

SyncDLCodeIdsMeasInfoItem-CellSyncReprtTDD ::= SEQUENCE {
	sFN										SFN,
	syncDLCodeIdInfo-CellSyncReprtTDD		SyncDLCodeIdInfo-CellSyncReprtTDD,
	iE-Extensions							ProtocolExtensionContainer { { SyncDLCodeIdsMeasInfoItem-CellSyncReprtTDD-ExtIEs } }		OPTIONAL,
	...
}

SyncDLCodeIdsMeasInfoItem-CellSyncReprtTDD-ExtIEs NBAP-PROTOCOL-EXTENSION ::= {
	...
}

SyncDLCodeIdInfo-CellSyncReprtTDD ::= SEQUENCE (SIZE (1..maxNrOfReceptionsperSyncFrameLCR)) OF SyncDLCodeIdItem-CellSyncReprtTDD

SyncDLCodeIdItem-CellSyncReprtTDD ::= CHOICE {
	syncDLCodeIdAvailable				SyncDLCodeIdAvailable-CellSyncReprtTDD,
	syncDLCodeIDNotAvailable			NULL,
	...
}

SyncDLCodeIdAvailable-CellSyncReprtTDD ::= SEQUENCE {
	syncDLCodeIdTiming			CellSyncBurstTimingLCR,
	syncDLCodeIdSIR				CellSyncBurstSIR,
	iE-Extensions				ProtocolExtensionContainer { { SyncDLCodeIdAvailable-CellSyncReprtTDD-ExtIEs } }		OPTIONAL,
	...
}

SyncDLCodeIdAvailable-CellSyncReprtTDD-ExtIEs NBAP-PROTOCOL-EXTENSION ::= {
	...
}

-- **************************************************************
--
-- BEARER REARRANGEMENT INDICATION
--
-- **************************************************************

BearerRearrangementIndication ::= SEQUENCE {
	protocolIEs                     ProtocolIE-Container       {{BearerRearrangementIndication-IEs}},
	protocolExtensions              ProtocolExtensionContainer {{BearerRearrangementIndication-Extensions}}                   OPTIONAL,
	...
}

BearerRearrangementIndication-IEs NBAP-PROTOCOL-IES ::= {
	{ ID id-CRNC-CommunicationContextID					CRITICALITY ignore	TYPE CRNC-CommunicationContextID				PRESENCE mandatory } |
	{ ID id-SignallingBearerRequestIndicator			CRITICALITY ignore	TYPE SignallingBearerRequestIndicator				PRESENCE optional } |
	{ ID id-DCH-RearrangeList-Bearer-RearrangeInd		CRITICALITY ignore	TYPE DCH-RearrangeList-Bearer-RearrangeInd			PRESENCE optional } |
	{ ID id-DSCH-RearrangeList-Bearer-RearrangeInd		CRITICALITY ignore	TYPE DSCH-RearrangeList-Bearer-RearrangeInd		PRESENCE optional } |
	-- TDD only.
	{ ID id-USCH-RearrangeList-Bearer-RearrangeInd		CRITICALITY ignore	TYPE USCH-RearrangeList-Bearer-RearrangeInd		PRESENCE optional } |
	-- TDD only.
	{ ID id-HSDSCH-RearrangeList-Bearer-RearrangeInd	CRITICALITY ignore	TYPE HSDSCH-RearrangeList-Bearer-RearrangeInd		PRESENCE optional },
	...
}

BearerRearrangementIndication-Extensions NBAP-PROTOCOL-EXTENSION ::= {
	{ ID id-E-DCH-RearrangeList-Bearer-RearrangeInd		CRITICALITY ignore	EXTENSION E-DCH-RearrangeList-Bearer-RearrangeInd	PRESENCE optional },
	...
}

DCH-RearrangeList-Bearer-RearrangeInd ::= SEQUENCE (SIZE (1..maxNrOfDCHs)) OF DCH-RearrangeItem-Bearer-RearrangeInd

DCH-RearrangeItem-Bearer-RearrangeInd ::= SEQUENCE {
	dCH-ID											DCH-ID,
	iE-Extensions									ProtocolExtensionContainer { { DCH-RearrangeItem-Bearer-RearrangeInd-ExtIEs} }		OPTIONAL,
	...
}

DCH-RearrangeItem-Bearer-RearrangeInd-ExtIEs  NBAP-PROTOCOL-EXTENSION ::= {
	...
}

DSCH-RearrangeList-Bearer-RearrangeInd ::= SEQUENCE (SIZE (1..maxNrOfDSCHs)) OF DSCH-RearrangeItem-Bearer-RearrangeInd

DSCH-RearrangeItem-Bearer-RearrangeInd ::= SEQUENCE {
	dSCH-ID											DSCH-ID,
	iE-Extensions									ProtocolExtensionContainer { { DSCH-RearrangeItem-Bearer-RearrangeInd-ExtIEs} }		OPTIONAL,
	...
}

DSCH-RearrangeItem-Bearer-RearrangeInd-ExtIEs  NBAP-PROTOCOL-EXTENSION ::= {
	...
}

USCH-RearrangeList-Bearer-RearrangeInd ::= SEQUENCE (SIZE (1..maxNrOfUSCHs)) OF USCH-RearrangeItem-Bearer-RearrangeInd

USCH-RearrangeItem-Bearer-RearrangeInd ::= SEQUENCE {
	uSCH-ID											USCH-ID,
	iE-Extensions									ProtocolExtensionContainer { { USCH-RearrangeItem-Bearer-RearrangeInd-ExtIEs} }		OPTIONAL,
	...
}

USCH-RearrangeItem-Bearer-RearrangeInd-ExtIEs  NBAP-PROTOCOL-EXTENSION ::= {
	...
}

HSDSCH-RearrangeList-Bearer-RearrangeInd ::= SEQUENCE (SIZE (1..maxNrOfMACdFlows)) OF HSDSCH-RearrangeItem-Bearer-RearrangeInd

HSDSCH-RearrangeItem-Bearer-RearrangeInd ::= SEQUENCE {
	hsDSCH-MACdFlow-ID								HSDSCH-MACdFlow-ID,
	iE-Extensions									ProtocolExtensionContainer { { HSDSCH-RearrangeItem-Bearer-RearrangeInd-ExtIEs} }		OPTIONAL,
	...
}

HSDSCH-RearrangeItem-Bearer-RearrangeInd-ExtIEs  NBAP-PROTOCOL-EXTENSION ::= {
	...
}

E-DCH-RearrangeList-Bearer-RearrangeInd ::= SEQUENCE (SIZE (1.. maxNrOfEDCHMACdFlows)) OF E-DCH-RearrangeItem-Bearer-RearrangeInd

E-DCH-RearrangeItem-Bearer-RearrangeInd ::= SEQUENCE {
	e-DCH-MACdFlow-ID								E-DCH-MACdFlow-ID,
	iE-Extensions									ProtocolExtensionContainer { { E-DCH-RearrangeItem-Bearer-RearrangeInd-ExtIEs} }		OPTIONAL,
	...
}

E-DCH-RearrangeItem-Bearer-RearrangeInd-ExtIEs  NBAP-PROTOCOL-EXTENSION ::= {
	...
}

-- **************************************************************
--
-- RADIO LINK ACTIVATION COMMAND FDD
--
-- **************************************************************

RadioLinkActivationCommandFDD ::= SEQUENCE {
	protocolIEs				ProtocolIE-Container		{{RadioLinkActivationCommandFDD-IEs}},
	protocolExtensions		ProtocolExtensionContainer	{{RadioLinkActivationCommandFDD-Extensions}}			OPTIONAL,
	...
}

RadioLinkActivationCommandFDD-IEs NBAP-PROTOCOL-IES ::= {
	{ ID	id-NodeB-CommunicationContextID						CRITICALITY	ignore	TYPE	NodeB-CommunicationContextID								PRESENCE	mandatory	}|
	{ ID	id-DelayedActivationList-RL-ActivationCmdFDD		CRITICALITY	ignore	TYPE	DelayedActivationInformationList-RL-ActivationCmdFDD			PRESENCE	mandatory	},
	...
}

RadioLinkActivationCommandFDD-Extensions NBAP-PROTOCOL-EXTENSION ::= {
	...
}

DelayedActivationInformationList-RL-ActivationCmdFDD ::= SEQUENCE (SIZE (1..maxNrOfRLs)) OF ProtocolIE-Single-Container { 
	{ DelayedActivationInformation-RL-ActivationCmdFDD-IEs} }

DelayedActivationInformation-RL-ActivationCmdFDD-IEs NBAP-PROTOCOL-IES ::= {
	{ ID id-DelayedActivationInformation-RL-ActivationCmdFDD	CRITICALITY ignore	TYPE DelayedActivationInformation-RL-ActivationCmdFDD	PRESENCE optional	}
}

DelayedActivationInformation-RL-ActivationCmdFDD ::= SEQUENCE {
	rL-ID						RL-ID,
	delayed-activation-update	DelayedActivationUpdate,
	iE-Extensions				ProtocolExtensionContainer { { DelayedActivationInformation-RL-ActivationCmdFDD-ExtIEs} } OPTIONAL,
	...
}

DelayedActivationInformation-RL-ActivationCmdFDD-ExtIEs NBAP-PROTOCOL-EXTENSION ::= {
	...
}

-- **************************************************************
--
-- RADIO LINK ACTIVATION COMMAND TDD
--
-- **************************************************************

RadioLinkActivationCommandTDD ::= SEQUENCE {
	protocolIEs				ProtocolIE-Container		{{RadioLinkActivationCommandTDD-IEs}},
	protocolExtensions		ProtocolExtensionContainer	{{RadioLinkActivationCommandTDD-Extensions}}			OPTIONAL,
	...
}

RadioLinkActivationCommandTDD-IEs NBAP-PROTOCOL-IES ::= {
	{ ID	id-NodeB-CommunicationContextID						CRITICALITY	ignore	TYPE	NodeB-CommunicationContextID								PRESENCE	mandatory	}|
	{ ID	id-DelayedActivationList-RL-ActivationCmdTDD		CRITICALITY	ignore	TYPE	DelayedActivationInformationList-RL-ActivationCmdTDD			PRESENCE	mandatory	},
	...
}

RadioLinkActivationCommandTDD-Extensions NBAP-PROTOCOL-EXTENSION ::= {
	...
}

DelayedActivationInformationList-RL-ActivationCmdTDD ::= SEQUENCE (SIZE (1..maxNrOfRLs)) OF ProtocolIE-Single-Container { 
	{ DelayedActivationInformation-RL-ActivationCmdTDD-IEs} }

DelayedActivationInformation-RL-ActivationCmdTDD-IEs NBAP-PROTOCOL-IES ::= {
	{ ID id-DelayedActivationInformation-RL-ActivationCmdTDD	CRITICALITY ignore	TYPE DelayedActivationInformation-RL-ActivationCmdTDD	PRESENCE optional	}
}

DelayedActivationInformation-RL-ActivationCmdTDD ::= SEQUENCE {
	rL-ID						RL-ID,
	delayed-activation-update	DelayedActivationUpdate,
	iE-Extensions				ProtocolExtensionContainer { { DelayedActivationInformation-RL-ActivationCmdTDD-ExtIEs} } OPTIONAL,
	...
}

DelayedActivationInformation-RL-ActivationCmdTDD-ExtIEs NBAP-PROTOCOL-EXTENSION ::= {
	...
}

-- **************************************************************
--
-- RADIO LINK PARAMETER UPDATE INDICATION FDD
--
-- **************************************************************

RadioLinkParameterUpdateIndicationFDD ::= SEQUENCE {
	protocolIEs				ProtocolIE-Container		{{RadioLinkParameterUpdateIndicationFDD-IEs}},
	protocolExtensions		ProtocolExtensionContainer	{{RadioLinkParameterUpdateIndicationFDD-Extensions}}		OPTIONAL,
	...
}

RadioLinkParameterUpdateIndicationFDD-IEs NBAP-PROTOCOL-IES ::= {
	{ ID id-CRNC-CommunicationContextID			CRITICALITY		ignore		TYPE	CRNC-CommunicationContextID			PRESENCE	mandatory	} |
	{ ID id-HSDSCH-FDD-Update-Information		CRITICALITY		ignore		TYPE	HSDSCH-FDD-Update-Information			PRESENCE	optional	},
	...
}

RadioLinkParameterUpdateIndicationFDD-Extensions NBAP-PROTOCOL-EXTENSION ::= {
	{ ID id-E-DCH-FDD-Update-Information		CRITICALITY		ignore		EXTENSION	E-DCH-FDD-Update-Information			PRESENCE	optional	}|
	{ ID id-Additional-HS-Cell-Information-RL-Param-Upd	CRITICALITY ignore		EXTENSION Additional-HS-Cell-Information-RL-Param-Upd		PRESENCE optional },
	...
}

Additional-HS-Cell-Information-RL-Param-Upd	::= SEQUENCE (SIZE (1..maxNrOfHSDSCH-1)) OF Additional-HS-Cell-Information-RL-Param-Upd-ItemIEs

Additional-HS-Cell-Information-RL-Param-Upd-ItemIEs	::=SEQUENCE{
	hSPDSCH-RL-ID										RL-ID,
	hS-DSCH-FDD-Secondary-Serving-Update-Information	HS-DSCH-FDD-Secondary-Serving-Update-Information,
	iE-Extensions					ProtocolExtensionContainer { { Additional-HS-Cell-Information-RL-Setup-ExtIEs} } OPTIONAL,
	...
}

Additional-HS-Cell-Information-RL-Setup-ExtIEs	NBAP-PROTOCOL-EXTENSION ::= {
	...
}

-- **************************************************************
--
-- RADIO LINK PARAMETER UPDATE INDICATION TDD
--
-- **************************************************************

RadioLinkParameterUpdateIndicationTDD ::= SEQUENCE {
	protocolIEs				ProtocolIE-Container		{{RadioLinkParameterUpdateIndicationTDD-IEs}},
	protocolExtensions		ProtocolExtensionContainer	{{RadioLinkParameterUpdateIndicationTDD-Extensions}}		OPTIONAL,
	...
}

RadioLinkParameterUpdateIndicationTDD-IEs NBAP-PROTOCOL-IES ::= {
	{ ID id-CRNC-CommunicationContextID			CRITICALITY		ignore		TYPE	CRNC-CommunicationContextID			PRESENCE	mandatory	} |
	{ ID id-HSDSCH-TDD-Update-Information		CRITICALITY		ignore		TYPE	HSDSCH-TDD-Update-Information			PRESENCE	optional	},
	...
}

RadioLinkParameterUpdateIndicationTDD-Extensions NBAP-PROTOCOL-EXTENSION ::= {
	...
}

-- **************************************************************
--
-- MBMS NOTIFICATION UPDATE COMMAND
--
-- **************************************************************

MBMSNotificationUpdateCommand ::= SEQUENCE {
	protocolIEs				ProtocolIE-Container	{{ MBMSNotificationUpdateCommand-IEs}},
	protocolExtensions		ProtocolExtensionContainer	{{ MBMSNotificationUpdateCommand-Extensions}}		OPTIONAL,
	...
}

MBMSNotificationUpdateCommand-IEs NBAP-PROTOCOL-IES ::= {
	{ ID id-C-ID								CRITICALITY ignore	TYPE C-ID								PRESENCE mandatory	}|
	{ ID id-CommonPhysicalChannelID				CRITICALITY ignore	TYPE CommonPhysicalChannelID			PRESENCE mandatory	}|
	{ ID id-Modification-Period					CRITICALITY ignore	TYPE Modification-Period				PRESENCE optional		}|
	{ ID id-MICH-CFN							CRITICALITY ignore	TYPE MICH-CFN							PRESENCE mandatory	}|
	{ ID id-NI-Information-NotifUpdateCmd		CRITICALITY ignore	TYPE NI-Information						PRESENCE mandatory	},
	...
}

MBMSNotificationUpdateCommand-Extensions NBAP-PROTOCOL-EXTENSION ::= {
	...
}


-- **************************************************************
--
-- UE STATUS UPDATE
--
-- **************************************************************

UEStatusUpdateCommand ::= SEQUENCE {
	protocolIEs			ProtocolIE-Container		{{UEStatusUpdateCommand-IEs}},
	protocolExtensions	ProtocolExtensionContainer	{{UEStatusUpdateCommand-Extensions}}	OPTIONAL,
	...
}

UEStatusUpdateCommand-IEs NBAP-PROTOCOL-IES ::= {
	{ ID id-Cell-ERNTI-Status-Information					CRITICALITY ignore	TYPE Cell-ERNTI-Status-Information							PRESENCE mandatory },
	...
}

UEStatusUpdateCommand-Extensions NBAP-PROTOCOL-EXTENSION ::= {
	...
}

END

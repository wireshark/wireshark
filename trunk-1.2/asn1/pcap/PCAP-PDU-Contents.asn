-- $Id$
--
-- 3GPP TS 25.453 V7.9.0 (2007-12)
--
--9.3.3	PDU Definitions
-- **************************************************************
--
-- PDU definitions for PCAP.
--
-- **************************************************************

PCAP-PDU-Contents {
itu-t (0) identified-organization (4) etsi (0) mobileDomain (0) 
umts-Access (20) modules (3) pcap(4) version1 (1) pcap-PDU-Contents (1) }

DEFINITIONS AUTOMATIC TAGS ::= 

BEGIN

-- **************************************************************
--
-- IE parameter types from other modules.
--
-- **************************************************************

IMPORTS
	Cause,
	CriticalityDiagnostics,
	GPS-UTRAN-TRU,
	InformationExchangeID,
	InformationReportCharacteristics,
	InformationType,
	MeasuredResultsList,
	RequestedDataValue,
	RequestedDataValueInformation,
	UE-PositionEstimate,
	CellId-MeasuredResultsSets,
	OTDOA-MeasurementGroup,
	AccuracyFulfilmentIndicator,
	HorizontalAccuracyCode,
	VerticalAccuracyCode,
	RequestType,
	UE-PositioningCapability, 
	UC-ID, 
	ResponseTime,
	PositioningPriority,
	ClientType,
	PositioningMethod,
	UTDOAPositioning,
	GPSPositioning,
	OTDOAAssistanceData,
	UTDOA-Group,
	Positioning-ResponseTime,
	EnvironmentCharacterisation,
	PositionData,
	IncludeVelocity,
	VelocityEstimate,
	UE-PositionEstimateInfo,
	OTDOA-MeasuredResultsSets,
	PeriodicPosCalcInfo,
	PeriodicLocationInfo,
	AmountOfReporting,
	MeasInstructionsUsed,
	RRCstateChange,
	PeriodicTerminationCause,
	CellIDPositioning,
	GANSS-MeasuredResultsList,
	GANSSPositioning,
	GANSS-UTRAN-TRU,
	AdditionalGPSAssistDataRequired,
	AdditionalGanssAssistDataRequired

FROM PCAP-IEs

	TransactionID
FROM PCAP-CommonDataTypes

	ProtocolExtensionContainer{},
	ProtocolIE-ContainerList{},
	ProtocolIE-Container{},
	ProtocolIE-Single-Container{},
	PrivateIE-Container{},
	PCAP-PRIVATE-IES,
	PCAP-PROTOCOL-EXTENSION,
	PCAP-PROTOCOL-IES
FROM PCAP-Containers

	id-Cause,
	id-CriticalityDiagnostics,
	id-GPS-UTRAN-TRU,
	id-InformationExchangeID,
	id-InformationExchangeObjectType-InfEx-Rprt,
	id-InformationExchangeObjectType-InfEx-Rqst,
	id-InformationExchangeObjectType-InfEx-Rsp,
	id-InformationReportCharacteristics,
	id-InformationType,
	id-GPS-MeasuredResultsList,
	id-RequestedDataValue,
	id-RequestedDataValueInformation,
	id-TransactionID,
	id-UE-PositionEstimate,
	id-CellId-MeasuredResultsSets,
	id-OTDOA-MeasurementGroup,
	id-AccuracyFulfilmentIndicator,
	id-HorizontalAccuracyCode,
	id-VerticalAccuracyCode,
	id-RequestType,
	id-UE-PositioningCapability, 
	id-UC-id,
	id-ResponseTime,
	id-PositioningPriority,
	id-ClientType,
	id-PositioningMethod,
	id-UTDOAPositioning,
	id-GPSPositioning,
	id-OTDOAAssistanceData,
	id-UTDOA-Group,
	id-Positioning-ResponseTime,
	id-EnvironmentCharacterisation,
	id-PositionData,
	id-IncludeVelocity,
	id-VelocityEstimate,
	id-UE-PositionEstimateInfo,
	id-UC-ID-InfEx-Rqst,
	id-OTDOA-MeasuredResultsSets,
	id-PeriodicPosCalcInfo,
	id-PeriodicLocationInfo,
	id-AmountOfReporting,
	id-MeasInstructionsUsed,
	id-RRCstateChange,
	id-PeriodicTerminationCause,
	id-CellIDPositioning,
	id-GANSS-MeasuredResultsList,
	id-GANSSPositioning,
	id-GANSS-UTRAN-TRU,
	id-AdditionalGPSAssistDataRequired,
	id-AdditionalGanssAssistDataRequired

FROM PCAP-Constants;


-- **************************************************************
--
-- POSITION CALCULATION REQUEST
--
-- **************************************************************

PositionCalculationRequest ::= SEQUENCE {
	protocolIEs			ProtocolIE-Container       { {PositionCalculationRequestIEs} },
	protocolExtensions	ProtocolExtensionContainer { {PositionCalculationRequestExtensions} } 	OPTIONAL,
	...
}

PositionCalculationRequestIEs PCAP-PROTOCOL-IES ::= {
	{ ID id-UE-PositionEstimate					CRITICALITY reject	TYPE UE-PositionEstimate					PRESENCE optional } |
	{ ID id-GPS-MeasuredResultsList				CRITICALITY reject	TYPE MeasuredResultsList					PRESENCE optional },
	...
}

PositionCalculationRequestExtensions PCAP-PROTOCOL-EXTENSION ::= {
	{ ID id-CellId-MeasuredResultsSets		CRITICALITY reject	EXTENSION CellId-MeasuredResultsSets		PRESENCE optional } |
	{ ID id-OTDOA-MeasurementGroup			CRITICALITY reject	EXTENSION OTDOA-MeasurementGroup			PRESENCE optional } |
	{ ID id-HorizontalAccuracyCode			CRITICALITY ignore	EXTENSION HorizontalAccuracyCode			PRESENCE optional } |
	{ ID id-VerticalAccuracyCode			CRITICALITY ignore	EXTENSION VerticalAccuracyCode				PRESENCE optional } | 	
	{ ID id-UTDOA-Group						CRITICALITY reject	EXTENSION UTDOA-Group						PRESENCE optional } | 	
	{ ID id-Positioning-ResponseTime		CRITICALITY ignore	EXTENSION Positioning-ResponseTime		PRESENCE optional } |
	{ ID id-IncludeVelocity					CRITICALITY ignore	EXTENSION IncludeVelocity					PRESENCE optional } |
	{ ID id-PeriodicPosCalcInfo				CRITICALITY ignore	EXTENSION PeriodicPosCalcInfo				PRESENCE optional }|
	{ ID id-GANSS-MeasuredResultsList		CRITICALITY reject	EXTENSION GANSS-MeasuredResultsList		PRESENCE optional },
	...
}

-- **************************************************************
--
-- POSITION CALCULATION RESPONSE
--
-- **************************************************************

PositionCalculationResponse ::= SEQUENCE {
	protocolIEs			ProtocolIE-Container       { {PositionCalculationResponseIEs} },
	protocolExtensions	ProtocolExtensionContainer { {PositionCalculationResponseExtensions} } 	OPTIONAL,
	...
}

PositionCalculationResponseIEs PCAP-PROTOCOL-IES ::= {
	{ ID id-UE-PositionEstimate			CRITICALITY ignore	TYPE UE-PositionEstimate		PRESENCE mandatory } |
	{ ID id-CriticalityDiagnostics		CRITICALITY ignore	TYPE CriticalityDiagnostics		PRESENCE optional	},
	...
}

PositionCalculationResponseExtensions PCAP-PROTOCOL-EXTENSION ::= {
	{ ID id-AccuracyFulfilmentIndicator	CRITICALITY ignore	EXTENSION AccuracyFulfilmentIndicator			PRESENCE optional} |
	{ ID id-VelocityEstimate			CRITICALITY ignore 	EXTENSION VelocityEstimate					PRESENCE optional},
	...
}

-- **************************************************************
--
-- POSITION CALCULATION FAILURE
--
-- **************************************************************

PositionCalculationFailure ::= SEQUENCE {
	protocolIEs			ProtocolIE-Container       { {PositionCalculationFailureIEs} },
	protocolExtensions	ProtocolExtensionContainer { {PositionCalculationFailureExtensions} } 	OPTIONAL,
	...
}

PositionCalculationFailureIEs PCAP-PROTOCOL-IES ::= {
	{ ID id-Cause						CRITICALITY ignore	TYPE Cause						PRESENCE mandatory} |
	{ ID id-CriticalityDiagnostics		CRITICALITY ignore	TYPE CriticalityDiagnostics		PRESENCE optional },
	...
}

PositionCalculationFailureExtensions PCAP-PROTOCOL-EXTENSION ::= {
	...
}


-- **************************************************************
--
-- INFORMATION EXCHANGE INITIATION REQUEST
--
-- **************************************************************

InformationExchangeInitiationRequest ::= SEQUENCE {
	protocolIEs				ProtocolIE-Container	{{InformationExchangeInitiationRequest-IEs}},
	protocolExtensions		ProtocolExtensionContainer	{{InformationExchangeInitiationRequest-Extensions}}		OPTIONAL,
	...
}

InformationExchangeInitiationRequest-IEs PCAP-PROTOCOL-IES ::= {
	{ ID id-InformationExchangeID						CRITICALITY	reject	TYPE InformationExchangeID								PRESENCE	mandatory }|
	{ ID id-InformationExchangeObjectType-InfEx-Rqst	CRITICALITY	reject	TYPE InformationExchangeObjectType-InfEx-Rqst		PRESENCE mandatory }|
	-- This IE represents both the Information Exchange Object Type IE and the choice based on the Information Exchange Object Type
	-- as described in the tabular message format in clause 9.1.
	{ ID id-InformationType								CRITICALITY	reject	TYPE InformationType										PRESENCE	mandatory }|
	{ ID id-InformationReportCharacteristics			CRITICALITY	reject	TYPE InformationReportCharacteristics				PRESENCE	mandatory }|
	{ ID id-GPS-UTRAN-TRU								CRITICALITY reject	TYPE GPS-UTRAN-TRU											PRESENCE conditional },
	-- This IE shall be present if the information requested in the Information Type IE contains GPS-related data
	...
}

InformationExchangeInitiationRequest-Extensions PCAP-PROTOCOL-EXTENSION ::= {
	{ ID id-GANSS-UTRAN-TRU							CRITICALITY reject	EXTENSION GANSS-UTRAN-TRU										PRESENCE conditional },
	-- This IE shall be present if the information requested in the Information Type IE contains GANSS-related data
	...
}

InformationExchangeObjectType-InfEx-Rqst ::= CHOICE {
	referencePosition										RefPosition-InfEx-Rqst,
	... ,
	extension-InformationExchangeObjectType-InfEx-Rqst		Extension-InformationExchangeObjectType-InfEx-Rqst
}

RefPosition-InfEx-Rqst ::= SEQUENCE {
	referencePositionEstimate		UE-PositionEstimate,
	iE-Extensions					ProtocolExtensionContainer  { { RefPositionItem-InfEx-Rqst-ExtIEs} }		OPTIONAL,
	...
}

RefPositionItem-InfEx-Rqst-ExtIEs PCAP-PROTOCOL-EXTENSION ::= {
	...
}

Extension-InformationExchangeObjectType-InfEx-Rqst	::= ProtocolIE-Single-Container {{ Extension-InformationExchangeObjectType-InfEx-RqstIE }}

Extension-InformationExchangeObjectType-InfEx-RqstIE PCAP-PROTOCOL-IES ::= {
	{ ID id-UC-ID-InfEx-Rqst			CRITICALITY reject	TYPE UC-ID-InfEx-Rqst			PRESENCE mandatory } |
	{ ID id-CellId-MeasuredResultsSets	CRITICALITY ignore	TYPE CellId-MeasuredResultsSets	PRESENCE optional }
}

UC-ID-InfEx-Rqst ::= SEQUENCE {
	referenceUC-ID					UC-ID,
	iE-Extensions					ProtocolExtensionContainer  { { UCIDItem-InfEx-Rqst-ExtIEs} }		OPTIONAL,
	...
}

UCIDItem-InfEx-Rqst-ExtIEs PCAP-PROTOCOL-EXTENSION ::= {
	...
}


-- **************************************************************
--
-- INFORMATION EXCHANGE INITIATION RESPONSE
--
-- **************************************************************

InformationExchangeInitiationResponse ::= SEQUENCE {
	protocolIEs				ProtocolIE-Container	{{InformationExchangeInitiationResponse-IEs}},
	protocolExtensions		ProtocolExtensionContainer	{{InformationExchangeInitiationResponse-Extensions}}		OPTIONAL,
	...
}

InformationExchangeInitiationResponse-IEs PCAP-PROTOCOL-IES ::= {
	{ ID	id-InformationExchangeID					CRITICALITY	ignore	TYPE InformationExchangeID								PRESENCE	mandatory }|
	{ ID	id-InformationExchangeObjectType-InfEx-Rsp	CRITICALITY	ignore	TYPE InformationExchangeObjectType-InfEx-Rsp		PRESENCE	optional }|
	{ ID	id-CriticalityDiagnostics					CRITICALITY	ignore	TYPE CriticalityDiagnostics								PRESENCE	optional	},
	...
}

InformationExchangeInitiationResponse-Extensions PCAP-PROTOCOL-EXTENSION ::= {
	...
}

InformationExchangeObjectType-InfEx-Rsp ::= CHOICE {
	referencePosition				RefPosition-InfEx-Rsp,
	...
}

RefPosition-InfEx-Rsp ::= SEQUENCE {
	requestedDataValue				RequestedDataValue,
	iE-Extensions					ProtocolExtensionContainer  { { RefPositionItem-InfEx-Rsp-ExtIEs} }		OPTIONAL,
	...
}

RefPositionItem-InfEx-Rsp-ExtIEs PCAP-PROTOCOL-EXTENSION ::= {
	...
}


-- **************************************************************
--
-- INFORMATION EXCHANGE INITIATION FAILURE
--
-- **************************************************************

InformationExchangeInitiationFailure ::= SEQUENCE {
	protocolIEs				ProtocolIE-Container	{{InformationExchangeInitiationFailure-IEs}},
	protocolExtensions		ProtocolExtensionContainer	{{InformationExchangeInitiationFailure-Extensions}}		OPTIONAL,
	...
}

InformationExchangeInitiationFailure-IEs PCAP-PROTOCOL-IES ::= {
	{ ID	id-InformationExchangeID		CRITICALITY	ignore	TYPE InformationExchangeID		PRESENCE	mandatory }|
	{ ID	id-Cause						CRITICALITY	ignore	TYPE Cause						PRESENCE	mandatory }|
	{ ID	id-CriticalityDiagnostics		CRITICALITY	ignore	TYPE CriticalityDiagnostics		PRESENCE	optional	},
	...
}

InformationExchangeInitiationFailure-Extensions PCAP-PROTOCOL-EXTENSION ::= {
	...
}

-- **************************************************************
--
-- POSITION INITIATION REQUEST
--
-- **************************************************************

PositionInitiationRequest ::= SEQUENCE {
	protocolIEs			ProtocolIE-Container       { {PositionInitiationRequestIEs} },
	protocolExtensions	ProtocolExtensionContainer { {PositionInitiationRequestExtensions} } 	OPTIONAL,
	...
}

PositionInitiationRequestIEs PCAP-PROTOCOL-IES ::= {
	{ ID id-RequestType					CRITICALITY reject	TYPE RequestType				PRESENCE mandatory } |
	{ ID id-UE-PositioningCapability	CRITICALITY reject	TYPE UE-PositioningCapability	PRESENCE mandatory } |
	{ ID id-UC-id						CRITICALITY reject	TYPE UC-ID						PRESENCE mandatory } |
	{ ID id-VerticalAccuracyCode		CRITICALITY ignore	TYPE VerticalAccuracyCode		PRESENCE optional } |
	{ ID id-ResponseTime				CRITICALITY ignore	TYPE ResponseTime				PRESENCE optional } |
	{ ID id-PositioningPriority			CRITICALITY ignore	TYPE PositioningPriority		PRESENCE optional } |
	{ ID id-ClientType					CRITICALITY ignore	TYPE ClientType					PRESENCE optional },
	...
}

PositionInitiationRequestExtensions PCAP-PROTOCOL-EXTENSION ::= {
	{ ID id-IncludeVelocity				CRITICALITY ignore	EXTENSION IncludeVelocity			PRESENCE optional }|
	{ ID id-PeriodicLocationInfo		CRITICALITY ignore	EXTENSION PeriodicLocationInfo		PRESENCE optional },
	...
}


-- **************************************************************
--
-- POSITION INITIATION RESPONSE
--
-- **************************************************************

PositionInitiationResponse ::= SEQUENCE {
	protocolIEs			ProtocolIE-Container       { {PositionInitiationResponseIEs} },
	protocolExtensions	ProtocolExtensionContainer { {PositionInitiationResponseExtensions} } 	OPTIONAL,
	...
}

PositionInitiationResponseIEs PCAP-PROTOCOL-IES ::= {
	{ ID id-UE-PositionEstimate				CRITICALITY reject	TYPE UE-PositionEstimate				PRESENCE mandatory } |
	{ ID id-PositionData					CRITICALITY ignore	TYPE PositionData						PRESENCE mandatory } |
	{ ID id-AccuracyFulfilmentIndicator		CRITICALITY ignore	TYPE AccuracyFulfilmentIndicator		PRESENCE optional },
	...
}

PositionInitiationResponseExtensions PCAP-PROTOCOL-EXTENSION ::= {
	{ ID id-VelocityEstimate				CRITICALITY ignore	EXTENSION VelocityEstimate	PRESENCE optional },
	...
}


-- **************************************************************
--
-- POSITION INITIATION FAILURE
--
-- **************************************************************

PositionInitiationFailure ::= SEQUENCE {
	protocolIEs			ProtocolIE-Container       { {PositionInitiationFailureIEs} },
	protocolExtensions	ProtocolExtensionContainer { {PositionInitiationFailureExtensions} } 	OPTIONAL,
	...
}

PositionInitiationFailureIEs PCAP-PROTOCOL-IES ::= {
	{ ID id-Cause					CRITICALITY ignore	TYPE Cause						PRESENCE mandatory } |
	{ ID id-CriticalityDiagnostics	CRITICALITY ignore	TYPE CriticalityDiagnostics		PRESENCE optional },
	...
}

PositionInitiationFailureExtensions PCAP-PROTOCOL-EXTENSION ::= {
	...
}


-- **************************************************************
--
-- POSITION ACTIVATION REQUEST
--
-- **************************************************************

PositionActivationRequest ::= SEQUENCE {
	protocolIEs			ProtocolIE-Container       { {PositionActivationRequestIEs} },
	protocolExtensions	ProtocolExtensionContainer { {PositionActivationRequestExtensions} } OPTIONAL,
	...
}

PositionActivationRequestIEs PCAP-PROTOCOL-IES ::= {
	{ ID id-PositioningMethod			CRITICALITY reject	TYPE PositioningMethod				PRESENCE mandatory } |
	{ ID id-Positioning-ResponseTime	CRITICALITY ignore	TYPE Positioning-ResponseTime		PRESENCE mandatory } |
	{ ID id-PositioningPriority			CRITICALITY ignore	TYPE PositioningPriority			PRESENCE optional } |
	{ ID id-EnvironmentCharacterisation	CRITICALITY ignore	TYPE EnvironmentCharacterisation	PRESENCE optional } |
	{ ID id-UTDOAPositioning			CRITICALITY reject	TYPE UTDOAPositioning				PRESENCE optional } |
	{ ID id-GPSPositioning				CRITICALITY reject	TYPE GPSPositioning					PRESENCE optional } |
	{ ID id-OTDOAAssistanceData			CRITICALITY reject	TYPE OTDOAAssistanceData			PRESENCE optional },
	...
}

PositionActivationRequestExtensions PCAP-PROTOCOL-EXTENSION ::= { 
	{ ID id-IncludeVelocity				CRITICALITY ignore	EXTENSION IncludeVelocity				PRESENCE optional } |
	{ ID id-AmountOfReporting			CRITICALITY ignore	EXTENSION AmountOfReporting				PRESENCE optional } |
	{ ID id-CellIDPositioning			CRITICALITY ignore	EXTENSION CellIDPositioning				PRESENCE optional }|
	{ ID id-GANSSPositioning			CRITICALITY reject	EXTENSION GANSSPositioning				PRESENCE optional },
	...
}


-- **************************************************************
--
-- POSITION ACTIVATION RESPONSE
-- 
-- **************************************************************

PositionActivationResponse ::= SEQUENCE {
	protocolIEs			ProtocolIE-Container       { {PositionActivationResponseIEs} },
	protocolExtensions	ProtocolExtensionContainer { {PositionActivationResponseExtensions} } 	OPTIONAL,
	...
}

PositionActivationResponseIEs PCAP-PROTOCOL-IES ::= {
	{ ID id-UE-PositionEstimateInfo			CRITICALITY ignore	TYPE UE-PositionEstimateInfo		PRESENCE optional } |
	{ ID id-GPS-MeasuredResultsList			CRITICALITY reject	TYPE MeasuredResultsList			PRESENCE optional } | 
	{ ID id-CellId-MeasuredResultsSets		CRITICALITY reject	TYPE CellId-MeasuredResultsSets		PRESENCE optional } |
	{ ID id-OTDOA-MeasuredResultsSets		CRITICALITY reject	TYPE OTDOA-MeasuredResultsSets			PRESENCE optional } |
	{ ID id-UTDOA-Group						CRITICALITY reject	TYPE UTDOA-Group					PRESENCE optional },
	...
}

PositionActivationResponseExtensions PCAP-PROTOCOL-EXTENSION ::= {
	{ ID id-VelocityEstimate				CRITICALITY ignore	EXTENSION VelocityEstimate		PRESENCE optional} |
	{ ID id-MeasInstructionsUsed			CRITICALITY ignore	EXTENSION MeasInstructionsUsed	PRESENCE optional} |
	{ ID id-GANSS-MeasuredResultsList		CRITICALITY reject	EXTENSION GANSS-MeasuredResultsList	PRESENCE optional } |
	{ ID id-AdditionalGPSAssistDataRequired			CRITICALITY ignore	EXTENSION AdditionalGPSAssistDataRequired			PRESENCE optional } |
	{ ID id-AdditionalGanssAssistDataRequired		CRITICALITY ignore	EXTENSION AdditionalGanssAssistDataRequired		PRESENCE optional },
	...
}


-- **************************************************************
--
-- POSITION ACTIVATION FAILURE
--
-- **************************************************************

PositionActivationFailure ::= SEQUENCE {
	protocolIEs			ProtocolIE-Container       { {PositionActivationFailureIEs} },
	protocolExtensions	ProtocolExtensionContainer { {PositionActivationFailureExtensions} } 	OPTIONAL,
	...
}

PositionActivationFailureIEs PCAP-PROTOCOL-IES ::= {
	{ ID id-Cause					CRITICALITY ignore	TYPE Cause						PRESENCE mandatory } |
	{ ID id-CriticalityDiagnostics	CRITICALITY ignore	TYPE CriticalityDiagnostics		PRESENCE optional },
	...
}

PositionActivationFailureExtensions PCAP-PROTOCOL-EXTENSION ::= {
	...
}


-- **************************************************************
--
-- INFORMATION REPORT
--
-- **************************************************************

InformationReport ::= SEQUENCE {
	protocolIEs				ProtocolIE-Container		{{InformationReport-IEs}},
	protocolExtensions		ProtocolExtensionContainer	{{InformationReport-Extensions}}		OPTIONAL,
	...
}

InformationReport-IEs PCAP-PROTOCOL-IES ::= {
	{ ID	id-InformationExchangeID						CRITICALITY	ignore	TYPE InformationExchangeID								PRESENCE	mandatory }|
	{ ID	id-InformationExchangeObjectType-InfEx-Rprt		CRITICALITY	ignore	TYPE InformationExchangeObjectType-InfEx-Rprt	PRESENCE	mandatory },
	...
}

InformationReport-Extensions PCAP-PROTOCOL-EXTENSION ::= {
	...
}

InformationExchangeObjectType-InfEx-Rprt ::= CHOICE {
	referencePosition				RefPosition-InfEx-Rprt,
	...
 }

RefPosition-InfEx-Rprt ::= SEQUENCE {
	requestedDataValueInformation	RequestedDataValueInformation,
	iE-Extensions					ProtocolExtensionContainer  {{ RefPositionItem-InfEx-Rprt-ExtIEs }}		OPTIONAL,
	...

 }

RefPositionItem-InfEx-Rprt-ExtIEs PCAP-PROTOCOL-EXTENSION ::= {
	...
}


-- **************************************************************
--
-- INFORMATION EXCHANGE TERMINATION REQUEST
--
-- **************************************************************

InformationExchangeTerminationRequest ::= SEQUENCE {
	protocolIEs				ProtocolIE-Container		{{InformationExchangeTerminationRequest-IEs}},
	protocolExtensions		ProtocolExtensionContainer	{{InformationExchangeTerminationRequest-Extensions}}	OPTIONAL,
	...
}

InformationExchangeTerminationRequest-IEs PCAP-PROTOCOL-IES ::= {
	{ ID	id-InformationExchangeID			CRITICALITY		ignore	TYPE InformationExchangeID			PRESENCE	mandatory},
	...
}

InformationExchangeTerminationRequest-Extensions PCAP-PROTOCOL-EXTENSION ::= {
	...
}


-- **************************************************************
--
-- INFORMATION EXCHANGE FAILURE INDICATION
--
-- **************************************************************

InformationExchangeFailureIndication ::= SEQUENCE {
	protocolIEs				ProtocolIE-Container		{{InformationExchangeFailureIndication-IEs}},
	protocolExtensions		ProtocolExtensionContainer	{{InformationExchangeFailureIndication-Extensions}}	OPTIONAL,
	...
}

InformationExchangeFailureIndication-IEs PCAP-PROTOCOL-IES ::= {
	{ ID	id-InformationExchangeID			CRITICALITY	ignore			TYPE InformationExchangeID			PRESENCE	mandatory	}|
	{ ID	id-Cause							CRITICALITY	ignore			TYPE Cause								PRESENCE	mandatory	},
	...
}

InformationExchangeFailureIndication-Extensions PCAP-PROTOCOL-EXTENSION ::= {
	...
}


-- **************************************************************
--
-- ERROR INDICATION
--
-- **************************************************************

ErrorIndication ::= SEQUENCE {
	protocolIEs			ProtocolIE-Container       { {ErrorIndicationIEs} },
	protocolExtensions	ProtocolExtensionContainer { {ErrorIndicationExtensions} } 	OPTIONAL,
	...
}

ErrorIndicationIEs PCAP-PROTOCOL-IES ::= {
	{ ID id-Cause						CRITICALITY ignore	TYPE Cause						PRESENCE optional } |
	{ ID id-CriticalityDiagnostics		CRITICALITY ignore	TYPE CriticalityDiagnostics		PRESENCE optional },
		...
}

ErrorIndicationExtensions PCAP-PROTOCOL-EXTENSION ::= {
	...
}

-- **************************************************************
--
-- POSITION PARAMETER MODIFICATION
--
-- **************************************************************

PositionParameterModification ::= SEQUENCE {
	protocolIEs			ProtocolIE-Container       { {PositionParameterModificationIEs} },
	protocolExtensions	ProtocolExtensionContainer { {PositionParameterModificationExtensions} } 	OPTIONAL,
	...
}

PositionParameterModificationIEs PCAP-PROTOCOL-IES ::= {
	{ ID id-UC-id						CRITICALITY reject	TYPE UC-ID						PRESENCE optional }|
	{ ID id-UTDOA-Group					CRITICALITY reject	TYPE UTDOA-Group				PRESENCE optional },
	...
}

PositionParameterModificationExtensions PCAP-PROTOCOL-EXTENSION ::= {
	{ ID id-RRCstateChange			CRITICALITY ignore	EXTENSION RRCstateChange	PRESENCE optional},
	...
} 
-- **************************************************************
--
-- PRIVATE MESSAGE
--
-- **************************************************************

PrivateMessage ::= SEQUENCE {
	privateIEs		PrivateIE-Container  {{PrivateMessage-IEs}},
	...
}

PrivateMessage-IEs PCAP-PRIVATE-IES ::= {
	...
}

-- **************************************************************
--
-- ABORT
--
-- **************************************************************

Abort ::= SEQUENCE {
	protocolIEs			ProtocolIE-Container       { {AbortIEs} },
	protocolExtensions	ProtocolExtensionContainer { {AbortExtensions} } 	OPTIONAL,
	...
}

AbortIEs PCAP-PROTOCOL-IES ::= {
	{ ID id-Cause		CRITICALITY ignore	TYPE Cause		PRESENCE mandatory },
	...
}

AbortExtensions PCAP-PROTOCOL-EXTENSION ::= { 
	...
}
 

-- **************************************************************
--
-- POSITION PERIODIC REPORT
--
-- **************************************************************

PositionPeriodicReport ::= SEQUENCE {
	protocolIEs				ProtocolIE-Container		{{PositionPeriodicReport-IEs}},
	protocolExtensions		ProtocolExtensionContainer	{{PositionPeriodicReport-Extensions}}		OPTIONAL,
	...
}

PositionPeriodicReport-IEs PCAP-PROTOCOL-IES ::= {
	{ ID id-UE-PositionEstimateInfo			CRITICALITY ignore	TYPE UE-PositionEstimateInfo		PRESENCE optional } |
	{ ID id-VelocityEstimate				CRITICALITY ignore	TYPE VelocityEstimate				PRESENCE optional } |
	{ ID id-GPS-MeasuredResultsList			CRITICALITY ignore	TYPE MeasuredResultsList			PRESENCE optional } | 
	{ ID id-CellId-MeasuredResultsSets		CRITICALITY ignore	TYPE CellId-MeasuredResultsSets		PRESENCE optional } |
	{ ID id-OTDOA-MeasuredResultsSets		CRITICALITY ignore	TYPE OTDOA-MeasuredResultsSets		PRESENCE optional } |
	{ ID id-Cause							CRITICALITY ignore	TYPE Cause							PRESENCE optional } ,
	...
}

PositionPeriodicReport-Extensions PCAP-PROTOCOL-EXTENSION ::= {
	{ ID id-GANSS-MeasuredResultsList				CRITICALITY ignore	EXTENSION GANSS-MeasuredResultsList				PRESENCE optional } |
	{ ID id-AdditionalGPSAssistDataRequired			CRITICALITY ignore	EXTENSION AdditionalGPSAssistDataRequired		PRESENCE optional } |
	{ ID id-AdditionalGanssAssistDataRequired		CRITICALITY ignore	EXTENSION AdditionalGanssAssistDataRequired		PRESENCE optional },
	...
}

-- **************************************************************
--
-- POSITION PERIODIC RESULT
--
-- **************************************************************

PositionPeriodicResult ::= SEQUENCE {
	protocolIEs			ProtocolIE-Container       {{PositionPeriodicResult-IEs}},
	protocolExtensions	ProtocolExtensionContainer {{PositionPeriodicResult-Extensions}} 	OPTIONAL,
	...
}

PositionPeriodicResult-IEs PCAP-PROTOCOL-IES ::= {
	{ ID id-UE-PositionEstimate				CRITICALITY ignore	TYPE UE-PositionEstimate				PRESENCE optional } |
	{ ID id-VelocityEstimate				CRITICALITY ignore	TYPE VelocityEstimate					PRESENCE optional } |
	{ ID id-PositionData					CRITICALITY ignore	TYPE PositionData						PRESENCE optional } |
	{ ID id-AccuracyFulfilmentIndicator		CRITICALITY ignore	TYPE AccuracyFulfilmentIndicator		PRESENCE optional } |
	{ ID id-Cause							CRITICALITY ignore	TYPE Cause								PRESENCE optional },
	...
}

PositionPeriodicResult-Extensions PCAP-PROTOCOL-EXTENSION ::= {
	...
}

-- **************************************************************
--
-- POSITION PERIODIC TERMINATION
--
-- **************************************************************

PositionPeriodicTermination ::= SEQUENCE {
	protocolIEs			ProtocolIE-Container       {{PositionPeriodicTermination-IEs}},
	protocolExtensions	ProtocolExtensionContainer {{PositionPeriodicTermination-Extensions}} 	OPTIONAL,
	...
}

PositionPeriodicTermination-IEs PCAP-PROTOCOL-IES ::= {
	{ ID id-PeriodicTerminationCause		CRITICALITY ignore	TYPE PeriodicTerminationCause			PRESENCE optional },
	...
}

PositionPeriodicTermination-Extensions PCAP-PROTOCOL-EXTENSION ::= { 
	...
}
END

--
-- EN 301 001-1 Ver. 1.2.2
--
Outgoing-Call-Barring-Operations-and-Errors {itu-t(0) identified-organization(4) etsi(0) 1001
                                             operations-and-errors(1)}

DEFINITIONS EXPLICIT TAGS ::=

BEGIN

EXPORTS
        ActivationOcb,
        ActivationStatusNotificationOcb,
        DeactivationOcb,
        DeactivationStatusNotificationOcb,
        InterrogationOcb,
        DisableOcb,
        OcbInvoked,
        InvalidBarringProgram,
        NoBarringProgram
;

IMPORTS
        OPERATION, ERROR
        FROM Remote-Operations-Information-Objects 
            {joint-iso-itu-t (2) remote-operations (4) informationObjects(5) version1(0)}

        PartyNumber
        FROM Addressing-Data-Elements
            {itu-t(0) identified-organization(4) etsi(0) 196 addressing-data-elements(6)}

        BasicService
        FROM Basic-Service-Elements
            {itu-t(0) identified-organization(4) etsi(0) 196 basic-service-elements(8)}

        notSubscribed, notAvailable, basicServiceNotProvided, invalidServedUserNr,
        resourceUnavailable, notImplemented, supplementaryServiceInteractionNotAllowed
        FROM General-Errors
            {itu-t(0) identified-organization(4) etsi(0) 196 general-errors(2)}

        NotActivated
        FROM Diversion-Operations
            {itu-t(0) identified-organization(4) etsi(0) 207 operations-and errors(1)}

        Pin, invalidPin, userControlBlocked, changeOfPinRequired
        FROM Pin-Set-Operations-and-Errors
            {itu-t(0) identified-organization(4) etsi(0) 1002 operations-and-errors(1)}
;

  activationOcb OPERATION::=
    {  
      ARGUMENT
          ActivationOcbArgument
 
      ERRORS {
          notSubscribed |
          notAvailable |
          basicServiceNotProvided |
          invalidServedUserNr |
          invalidPin |
          invalidBarringProgram |
          noBarringProgram |
          userControlBlocked |
          supplementaryServiceInteractionNotAllowed |
          resourceUnavailable |
          changeOfPinRequired }   
          
       CODE global:{oCBOID  1}         
      }

  deactivationOcb OPERATION::=
     {
       ARGUMENT
         DeactivationOcbArgument

       ERRORS {
         notSubscribed |
         notAvailable |
         basicServiceNotProvided |
         invalidServedUserNr |
         notActivated |
         invalidPin |
         userControlBlocked |
         changeOfPinRequired }      
         
       CODE global:{oCBOID  2}             
     }

  interrogationOcb OPERATION::=
    {
       ARGUMENT
         InterrogationOcbArgument

 
       RESULT 
         IntOcbResultList

 
       ERRORS {
         notSubscribed |
         notAvailable |
         basicServiceNotProvided |
         invalidServedUserNr }    
         
       CODE global:{oCBOID  5}                
     }

  activationStatusNotificationOcb OPERATION::=
    {
       ARGUMENT
         ActStatusNotificationOcbArg   
         
       CODE global:{oCBOID  3}                 
    }

  deactivationStatusNotificationOcb OPERATION::=
    {
       ARGUMENT
         DeactStatusNotificationOcbArg  
         
       CODE global:{oCBOID  4}                  
    }

  disableOcb OPERATION::=
    {
       ARGUMENT
         Pin  
  
       ERRORS {
         notImplemented |
         invalidPin |
         userControlBlocked |
         changeOfPinRequired }  
         
       CODE global:{oCBOID  6}                  
    }

  ocbInvoked OPERATION::=
    {
       CODE global:{oCBOID  7}        
    } 

ActivationOcbArgument				::=  SEQUENCE {
											basicService		BasicService,
											pin					Pin,
											barringProgram		BarringProgram	OPTIONAL,
											servedUserNr		ServedUserNr	OPTIONAL}

DeactivationOcbArgument				::= SEQUENCE {
											basicService		BasicService,
											pin					Pin,
											barringProgram		BarringProgram	OPTIONAL,
											servedUserNr		ServedUserNr	OPTIONAL}

InterrogationOcbArgument			::= SEQUENCE {
											basicService		BasicService,
											servedUserNr		ServedUserNr		OPTIONAL}

ActStatusNotificationOcbArg			::= SEQUENCE {
											basicService		BasicService,
											barringProgram		BarringProgram,
											servedUserNr		ServedUserNr}

DeactStatusNotificationOcbArg		::= SEQUENCE {
											basicService		BasicService,
											barringProgram		BarringProgram	OPTIONAL,
											servedUserNr		ServedUserNr}

ServedUserNr						::= CHOICE {
											individualNumber	PartyNumber,
											allNumbers			NULL}

IntOcbResultList					::= SET SIZE(0..30) OF IntOcbResult

IntOcbResult						::= SEQUENCE {
											servedUserNr		ServedUserNr,
											basicService		BasicService,
											barringProgramList	BarringProgramList}

BarringProgram						::= INTEGER (0..255)
BarringProgramList					::= SET SIZE(0...255) OF BarringProgram

invalidBarringProgram ERROR ::={CODE global:{oCBOID 10}}
noBarringProgram      ERROR ::={CODE global:{oCBOID 11}}

oCBOID OBJECT IDENTIFIER ::= {itu-t(0) identified-organization(4) etsi(0) 1001 operations-and-errors(1)}

activationOcb						ActivationOcb						::= globalValue {oCBOID  1}
deactivationOcb						DeactivationOcb						::= globalValue {oCBOID  2}
activationStatusNotificationOcb		ActivationStatusNotificationOcb		::= globalValue {oCBOID  3}
deactivationStatusNotificationOcb	DeactivationStatusNotificationOcb	::= globalValue {oCBOID  4}
interrogationOcb					InterrogationOcb					::= globalValue {oCBOID  5}
disableOcb							DisableOcb							::= globalValue {oCBOID  6}
ocbInvoked							OcbInvoked							::= globalValue {oCBOID  7}
invalidBarringProgram				InvalidBarringProgram				::= globalValue {oCBOID 10}
noBarringProgram					NoBarringProgram					::= globalValue {oCBOID 11}

notActivated						NotActivated						::= localValue 46

END -- of Outgoing-Call-Barring-Operations-and-Errors

--
-- EN 300 359-1 Ver. 1.3.2
--
CCBS-private-networks-Operations-and-Errors {ccitt identified-organization etsi(0) 359
                                             private-networks-operations-and-errors(2)}

DEFINITIONS EXPLICIT TAGS ::=

BEGIN

EXPORTS             CCBS-T-Request, CCBS-T-Call, CCBS-T-Suspend, CCBS-T-Resume,
                    CCBS-T-RemoteUserFree, CCBS-T-Available, LongTermDenial, ShortTermDenial;

IMPORTS             OPERATION, ERROR
                    FROM Remote-Operations-Information-Objects 
                        {joint-iso-itu-t (2) remote-operations (4) informationObjects(5) version1(0)}

                    notSubscribed
                    FROM General-Errors
                        {ccitt identified-organization etsi(0) 196 general-errors(2)}

                    Address
                    FROM Addressing-Data-Elements
                        {ccitt identified-organization etsi(0) 196 addressing-data-elements(6)}
                    Q931InformationElement
                    FROM Embedded-Q931-Types
                        {ccitt identified-organization etsi(0) 196 embedded-q931-types(7)};

CCBS-T-Request              ::= OPERATION
                                ARGUMENT SEQUENCE {
                                            destinationAddress           Address,
                                            q931InfoElement              Q931InformationElement,
                                            -- contains HLC, LLC and BC information
                                            retentionSupported           [1] IMPLICIT BOOLEAN
                                                                             DEFAULT FALSE,
                                            presentationAllowedIndicator [2] IMPLICIT BOOLEAN
                                                                             OPTIONAL,
                                            -- The use of this parameter is specified in 
                                            -- EN 300 195-1 for interaction of CCBS with CLIP
                                            originatingAddress           Address OPTIONAL}
                                            -- The use of this parameter is specified in 
                                            -- EN 300 195-1 for interaction of CCBS with CLIP
                                RESULT      retentionSupported BOOLEAN   -- Default False
                                ERRORS     {ShortTermDenial, notSubscribed, LongTermDenial}

CCBS-T-Call                 ::= OPERATION
CCBS-T-Suspend              ::= OPERATION
CCBS-T-Resume               ::= OPERATION
CCBS-T-RemoteUserFree       ::= OPERATION
CCBS-T-Available            ::= OPERATION

ShortTermDenial             ::= ERROR
LongTermDenial              ::= ERROR

cCBS-T-OID OBJECT IDENTIFIER   ::= {ccitt identified-organization etsi(0) 359
                                    private-networks-operations-and-errors(2)}

cCBS-T-Request              CCBS-T-Request          ::= globalValue {cCBS-T-OID 1}
cCBS-T-Call                 CCBS-T-Call             ::= globalValue {cCBS-T-OID 2}
cCBS-T-Suspend              CCBS-T-Suspend          ::= globalValue {cCBS-T-OID 3}
cCBS-T-Resume               CCBS-T-Resume           ::= globalValue {cCBS-T-OID 4}
cCBS-T-RemoteUserFree       CCBS-T-RemoteUserFree   ::= globalValue {cCBS-T-OID 5}
cCBS-T-Available            CCBS-T-Available        ::= globalValue {cCBS-T-OID 6}

longTermDenial              LongTermDenial          ::= globalValue {cCBS-T-OID 20}
shortTermDenial             ShortTermDenial         ::= globalValue {cCBS-T-OID 21}


END -- of CCBS-private-networks-operations-and-errors

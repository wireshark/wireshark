-- 3GPP TS 37.483 V19.2.0 (2026-03)
-- **************************************************************
--
-- Information Element Definitions
--
-- **************************************************************

E1AP-IEs {
itu-t (0) identified-organization (4) etsi (0) mobileDomain (0)
ngran-access (22) modules (3) e1ap (5) version1 (1) e1ap-IEs (2) }

DEFINITIONS AUTOMATIC TAGS ::=

BEGIN

IMPORTS

	id-CommonNetworkInstance,
	id-SNSSAI,
	id-OldQoSFlowMap-ULendmarkerexpected,
	id-DRB-QoS,
	id-endpoint-IP-Address-and-Port,
	id-NetworkInstance,
	id-QoSFlowMappingIndication,
	id-TNLAssociationTransportLayerAddressgNBCUUP,
	id-Cause,
	id-BCBearerContextNGU-TNLInfoatNGRAN-Request,
	id-QoSMonitoringRequest,
	id-QosMonitoringReportingFrequency,
	id-QoSMonitoringDisabled,
	id-PDCP-StatusReportIndication,
	id-RedundantCommonNetworkInstance,
	id-redundant-nG-UL-UP-TNL-Information,
	id-redundant-nG-DL-UP-TNL-Information,
	id-RedundantQosFlowIndicator,
	id-TSCTrafficCharacteristics,
	id-ExtendedPacketDelayBudget,
	id-CNPacketDelayBudgetDownlink,
	id-CNPacketDelayBudgetUplink,
	id-AdditionalPDCPduplicationInformation,
	id-RedundantPDUSessionInformation,
	id-RedundantPDUSessionInformation-used,
	id-QoS-Mapping-Information,
	id-MDTConfiguration,
	id-TraceCollectionEntityURI,
	id-EHC-Parameters,
	id-DAPSRequestInfo,
	id-EarlyForwardingCOUNTReq,
	id-EarlyForwardingCOUNTInfo,
	id-AlternativeQoSParaSetList,
	id-MCG-OfferedGBRQoSFlowInfo,
	id-Number-of-tunnels,
	id-DataForwardingtoE-UTRANInformationList,
	id-DataForwardingtoNG-RANQoSFlowInformationList,
	id-MaxCIDEHCDL,
	id-ignoreMappingRuleIndication,
	id-EarlyDataForwardingIndicator,
	id-QoSFlowsDRBRemapping,
	id-SecurityIndicationModify,
	id-DataForwardingSourceIPAddress,
	id-M4ReportAmount,
	id-M6ReportAmount,
	id-M7ReportAmount,
	id-PDUSession-PairID,
	id-SurvivalTime,
	id-UDC-Parameters,
	id-SecurityIndication,
	id-SecurityResult,
	id-SDTindicatorSetup,
	id-SDTindicatorMod,
	id-DiscardTimerExtended,
	id-MCForwardingResourceRequest,
	id-MCForwardingResourceIndication,
	id-MCForwardingResourceResponse,
	id-MCForwardingResourceRelease,
	id-MCForwardingResourceReleaseIndication,
	id-PDCP-COUNT-Reset,
	id-MBSSessionAssociatedInfoNonSupportToSupport,
	id-VersionID,
	id-MBSAreaSessionID,
	id-Secondary-PDU-Session-Data-Forwarding-Information,
	id-MBSSessionResourceNotification,
	id-MCBearerContextInactivityTimer,
	id-MCBearerContextStatusChange,
	id-SpecialTriggeringPurpose,
	id-F1UTunnelNotEstablished,
	id-PDUSetQoSParameters,
	id-N6JitterInformation,
	id-ECNMarkingorCongestionInformationReportingRequest,
	id-ECNMarkingorCongestionInformationReportingStatus,
	id-PDUSetbasedHandlingIndicator,
	id-IndirectPathIndication,
	id-F1U-TNL-InfoToAdd-List,
	id-F1U-TNL-InfoAdded-List,
	id-F1U-TNL-InfoToAddOrModify-List,
	id-F1U-TNL-InfoAddedOrModified-List,
	id-F1U-TNL-InfoToRelease-List,
	id-BroadcastF1U-ContextReferenceE1,
	id-PSIbasedDiscardTimer,
	id-UserPlaneErrorIndicator,
	id-MaximumDataBurstVolume,
	id-PDCPSNGapReport,
	id-UserPlaneFailureIndication,
	id-MCBearerContextNGUTnlInfoatNGRANReplaceRequest,
	id-PduSetDelayBudgetDownlink,
	id-PduSetDelayBudgetUplink,
	id-PduSetErrorRateDownlink,
	id-PduSetErrorRateUplink,
	id-MonitoringRequestonAvailableBitrate,
	id-MMSID,
	id-Remaining-time-based-rLC-retransmission-threshold,
	id-Remaining-time-based-rLC-polling-threshold,
	id-DL-PDU-Set-Info-Marking-Support-Ind,
	maxnoofMBSAreaSessionIDs,
	maxnoofSharedNG-UTerminations,
	maxnoofMRBs,
	maxnoofMBSSessionIDs,
	maxnoofQoSParaSets,
	maxnoofErrors,
	maxnoofSliceItems,
	maxnoofEUTRANQOSParameters,
	maxnoofNGRANQOSParameters,
	maxnoofDRBs,
	maxnoofPDUSessionResource,
	maxnoofQoSFlows,
	maxnoofUPParameters,
	maxnoofCellGroups,
	maxnooftimeperiods,
	maxnoofNRCGI,
	maxnoofTLAs,
	maxnoofGTPTLAs,
	maxnoofSPLMNs,
	maxnoofMDTPLMNs,
	maxnoofExtSliceItems,
	maxnoofDataForwardingTunneltoE-UTRAN,
	maxnoofExtNRCGI,
	maxnoofECGI,
	maxnoofSMBRValues,
	maxnoofCellsforMBS,
	maxnoofTAIforMBS,
	maxnoofMBSServiceAreaInformation,
	maxnoofDUs,
	maxnoofUEReports,
	maxnoofThresholds,
	maxFailedMeasPerNode




FROM E1AP-Constants

	Criticality,
	ProcedureCode,
	ProtocolIE-ID,
	TriggeringMessage

FROM E1AP-CommonDataTypes

	ProtocolExtensionContainer{},
	ProtocolIE-SingleContainer{},
	E1AP-PROTOCOL-EXTENSION,
	E1AP-PROTOCOL-IES


FROM E1AP-Containers;

-- A

ActivityInformation	::=	CHOICE	{
	dRB-Activity-List						DRB-Activity-List,
	pDU-Session-Resource-Activity-List		PDU-Session-Resource-Activity-List,
	uE-Activity								UE-Activity,
	choice-extension						ProtocolIE-SingleContainer	{{ActivityInformation-ExtIEs}}
}

ActivityInformation-ExtIEs E1AP-PROTOCOL-IES ::= {
	...
}

ActivityNotificationLevel	::=	ENUMERATED	{
	drb,
	pdu-session,
	ue,
	...
}

AdditionalHandoverInfo ::= ENUMERATED	{
	discard-pdpc-SN,
	...
}

AdditionalPDCPduplicationInformation	::=	ENUMERATED	{
	three,
	four,
	...
}

AdditionalRRMPriorityIndex ::= BIT STRING (SIZE(32))

AvailableBitrateReportThresholdList	::= SEQUENCE (SIZE(1..maxnoofThresholds)) OF AvailableBitrateReportThresholdItem

AvailableBitrateReportThresholdItem	::= SEQUENCE {
	bitRateThreshold				ReportingThreshold,
	iE-Extensions					ProtocolExtensionContainer { { AvailableBitrateReportThresholdItem-ExtIEs} }	OPTIONAL,
	...
}

AvailableBitrateReportThresholdItem-ExtIEs E1AP-PROTOCOL-EXTENSION::= {
	...
}

AveragingWindow  ::= INTEGER (0..4095, ...)

AlternativeQoSParaSetList ::= SEQUENCE (SIZE(1..maxnoofQoSParaSets)) OF AlternativeQoSParaSetItem

AlternativeQoSParaSetItem ::= SEQUENCE {
	alternativeQoSParameterIndex		INTEGER(1..8,...),
	guaranteedFlowBitRateDL				BitRate					OPTIONAL,
	guaranteedFlowBitRateUL				BitRate					OPTIONAL,
	packetDelayBudget					PacketDelayBudget		OPTIONAL,
	packetErrorRate						PacketErrorRate			OPTIONAL,
	iE-Extensions		ProtocolExtensionContainer { {AlternativeQoSParaSetItem-ExtIEs} }	OPTIONAL,
	...
}

AlternativeQoSParaSetItem-ExtIEs E1AP-PROTOCOL-EXTENSION ::= {
		{ ID id-MaximumDataBurstVolume	CRITICALITY ignore	EXTENSION MaxDataBurstVolume		PRESENCE optional		}|
		{ ID id-PduSetDelayBudgetDownlink 	CRITICALITY ignore	EXTENSION ExtendedPacketDelayBudget		PRESENCE optional		}|
		{ ID id-PduSetDelayBudgetUplink		CRITICALITY ignore	EXTENSION ExtendedPacketDelayBudget		PRESENCE optional		}|
		{ ID id-PduSetErrorRateDownlink		CRITICALITY ignore	EXTENSION PacketErrorRate				PRESENCE optional		}|
		{ ID id-PduSetErrorRateUplink		CRITICALITY ignore	EXTENSION PacketErrorRate				PRESENCE optional		},
	...
}

AssociatedSessionID ::= OCTET STRING

AveragePacketDelay ::= SEQUENCE {
	uL-AveragePacketDelay		AveragePacketDelayValue,
	dL-AveragePacketDelay		AveragePacketDelayValue,
	iE-Extensions		ProtocolExtensionContainer { {AveragePacketDelay-ExtIEs} }	OPTIONAL,
	...
}

AveragePacketDelay-ExtIEs E1AP-PROTOCOL-EXTENSION ::= {
	...
}

AveragePacketDelayValue ::= INTEGER (0..10000)



-- B

-- BCBearerContextToSetup

BCBearerContextToSetup ::= SEQUENCE {
	snssai									SNSSAI,
	bcBearerContextNGU-TNLInfoat5GC			BCBearerContextNGU-TNLInfoat5GC				OPTIONAL,
	bcMRBToSetupList						BCMRBSetupConfiguration,
	requestedAction							RequestedAction4AvailNGUTermination			OPTIONAL,
	iE-Extensions		ProtocolExtensionContainer { {BCBearerContextToSetup-ExtIEs} }	OPTIONAL,
	...
}

BCBearerContextToSetup-ExtIEs E1AP-PROTOCOL-EXTENSION ::= {
	...
}


BCBearerContextNGU-TNLInfoat5GC::= CHOICE {
	locationindependent				MBSNGUInformationAt5GC,
	locationdependent				LocationDependentMBSNGUInformationAt5GC,
	choice-extension	ProtocolIE-SingleContainer	{{BCBearerContextNGU-TNLInfoat5GC-ExtIEs}}
}

BCBearerContextNGU-TNLInfoat5GC-ExtIEs E1AP-PROTOCOL-IES ::= {
	...
}

BCMRBSetupConfiguration ::= SEQUENCE (SIZE(1..maxnoofMRBs)) OF BCMRBSetupConfiguration-Item

BCMRBSetupConfiguration-Item ::= SEQUENCE {
	mrb-ID								MRB-ID,
	mbs-pdcp-config					PDCP-Configuration,
	qoS-Flow-QoS-Parameter-List		QoS-Flow-QoS-Parameter-List,
	qoSFlowLevelQoSParameters		QoSFlowLevelQoSParameters		OPTIONAL,
	iE-Extensions		ProtocolExtensionContainer { {BCMRBSetupConfiguration-Item-ExtIEs} }	OPTIONAL,
	...
}

BCMRBSetupConfiguration-Item-ExtIEs E1AP-PROTOCOL-EXTENSION ::= {
	{ID id-F1U-TNL-InfoToAdd-List	CRITICALITY ignore	EXTENSION F1U-TNL-InfoToAdd-List	PRESENCE optional},
	...
}

-- BCBearerContextToSetupResponse

BCBearerContextToSetupResponse ::= SEQUENCE {
	bcBearerContextNGU-TNLInfoatNGRAN			BCBearerContextNGU-TNLInfoatNGRAN			OPTIONAL,
	bcMRBSetupResponseList					BCMRBSetupResponseList,
	bcMRBFailedList							BCMRBFailedList							OPTIONAL,
	availableBCMRBConfig						BCMRBSetupConfiguration					OPTIONAL,
	iE-Extensions		ProtocolExtensionContainer { {BCBearerContextToSetupResponse-ExtIEs} }	OPTIONAL,
	...
}

BCBearerContextToSetupResponse-ExtIEs E1AP-PROTOCOL-EXTENSION ::= {
	...
}


BCBearerContextNGU-TNLInfoatNGRAN::= CHOICE {
	locationindependent				MBSNGUInformationAtNGRAN,
	locationdependent				LocationDependentMBSNGUInformationAtNGRAN,
	choice-extension	ProtocolIE-SingleContainer	{{BCBearerContextNGU-TNLInfoatNGRAN-ExtIEs}}
}

BCBearerContextNGU-TNLInfoatNGRAN-ExtIEs E1AP-PROTOCOL-IES ::= {
	...
}

BCMRBSetupResponseList ::= SEQUENCE (SIZE(1..maxnoofMRBs)) OF BCMRBSetupResponseList-Item
BCMRBSetupResponseList-Item ::= SEQUENCE {
	mrb-ID								MRB-ID,
	qosflow-setup						QoS-Flow-List,
	qosflow-failed						QoS-Flow-Failed-List		OPTIONAL,
	bcBearerContextF1U-TNLInfoatCU 		BCBearerContextF1U-TNLInfoatCU,
	iE-Extensions		ProtocolExtensionContainer { {BCMRBSetupResponseList-Item-ExtIEs} }	OPTIONAL,
	...
}

BCMRBSetupResponseList-Item-ExtIEs E1AP-PROTOCOL-EXTENSION ::= {
	{ID id-F1U-TNL-InfoAdded-List	CRITICALITY ignore	EXTENSION F1U-TNL-InfoAdded-List	PRESENCE optional},
	...
}

BCBearerContextF1U-TNLInfoatCU ::= CHOICE {
	locationindependent				MBSF1UInformationAtCU,
	locationdependent				LocationDependentMBSF1UInformationAtCU,
	choice-extension	ProtocolIE-SingleContainer	{{BCBearerContextF1U-TNLInfoatCU-ExtIEs}}
}

BCBearerContextF1U-TNLInfoatCU-ExtIEs E1AP-PROTOCOL-IES ::= {
	...
}


BCMRBFailedList ::= SEQUENCE (SIZE(1..maxnoofMRBs)) OF BCMRBFailedList-Item
BCMRBFailedList-Item ::= SEQUENCE {
	mrb-ID								MRB-ID,
	cause								Cause,
	iE-Extensions		ProtocolExtensionContainer { {BCMRBFailedList-Item-ExtIEs} }	OPTIONAL,
	...
}

BCMRBFailedList-Item-ExtIEs E1AP-PROTOCOL-EXTENSION ::= {
	...
}


-- BCBearerContextToModify

BCBearerContextToModify ::= SEQUENCE {
	bcBearerContextNGU-TNLInfoat5GC		BCBearerContextNGU-TNLInfoat5GC	OPTIONAL,
	bcMRBToSetupList						BCMRBSetupConfiguration			OPTIONAL,
	bcMRBToModifyList					BCMRBModifyConfiguration			OPTIONAL,
	bcMRBToRemoveList					BCMRBRemoveConfiguration			OPTIONAL,
	iE-Extensions		ProtocolExtensionContainer { {BCBearerContextToModify-ExtIEs} }	OPTIONAL,
	...
}

BCBearerContextToModify-ExtIEs E1AP-PROTOCOL-EXTENSION ::= {
	{ID id-BCBearerContextNGU-TNLInfoatNGRAN-Request	CRITICALITY ignore	EXTENSION BCBearerContextNGU-TNLInfoatNGRAN-Request	PRESENCE optional},
	...
}

BCBearerContextNGU-TNLInfoatNGRAN-Request ::= CHOICE {
	locationindependent				MBSNGUInformationAtNGRAN-Request,
	locationdependent				MBSNGUInformationAtNGRAN-Request-List,
	choice-extension	ProtocolIE-SingleContainer	{{ BCBearerContextNGU-TNLInfoatNGRAN-Request-ExtIEs}}
}

BCBearerContextNGU-TNLInfoatNGRAN-Request-ExtIEs E1AP-PROTOCOL-IES ::= {
	...
}

BCMRBModifyConfiguration ::= SEQUENCE (SIZE(1..maxnoofMRBs)) OF BCMRBModifyConfiguration-Item

BCMRBModifyConfiguration-Item ::= SEQUENCE {
	mrb-ID							MRB-ID,
	bcBearerContextF1U-TNLInfoatDU 	BCBearerContextF1U-TNLInfoatDU	OPTIONAL,
	mbs-pdcp-config					PDCP-Configuration				OPTIONAL,
	qoS-Flow-QoS-Parameter-List		QoS-Flow-QoS-Parameter-List		OPTIONAL,
	qoSFlowLevelQoSParameters		QoSFlowLevelQoSParameters		OPTIONAL,
	iE-Extensions		ProtocolExtensionContainer { {BCMRBModifyConfiguration-Item-ExtIEs} }	OPTIONAL,
	...
}

BCMRBModifyConfiguration-Item-ExtIEs E1AP-PROTOCOL-EXTENSION ::= {
	{ID id-F1U-TNL-InfoToAddOrModify-List	CRITICALITY ignore	EXTENSION F1U-TNL-InfoToAddOrModify-List	PRESENCE optional}|
	{ID id-F1U-TNL-InfoToRelease-List		CRITICALITY ignore	EXTENSION F1U-TNL-InfoToRelease-List			PRESENCE optional},
	...
}

BCBearerContextF1U-TNLInfoatDU ::= CHOICE {
	locationindependent				MBSF1UInformationAtDU,
	locationdependent				LocationDependentMBSF1UInformationAtDU,
	choice-extension	ProtocolIE-SingleContainer	{{BCBearerContextF1U-TNLInfoatDU-ExtIEs}}
}

BCBearerContextF1U-TNLInfoatDU-ExtIEs E1AP-PROTOCOL-IES ::= {
	...
}

BCMRBRemoveConfiguration ::= SEQUENCE (SIZE(1..maxnoofMRBs)) OF MRB-ID


-- BCBearerContextToModifyResponse

BCBearerContextToModifyResponse ::= SEQUENCE {
	bcBearerContextNGU-TNLInfoatNGRAN			BCBearerContextNGU-TNLInfoatNGRAN			OPTIONAL,
	bcMRBSetupModifyResponseList				BCMRBSetupModifyResponseList,
	bcMRBFailedList							BCMRBFailedList							OPTIONAL,
	availableBCMRBConfig						BCMRBSetupConfiguration					OPTIONAL,
	iE-Extensions		ProtocolExtensionContainer { {BCBearerContextToModifyResponse-ExtIEs} }	OPTIONAL,
	...
}

BCBearerContextToModifyResponse-ExtIEs E1AP-PROTOCOL-EXTENSION ::= {
	...
}

BCMRBSetupModifyResponseList ::= SEQUENCE (SIZE(1..maxnoofMRBs)) OF BCMRBSetupModifyResponseList-Item

BCMRBSetupModifyResponseList-Item ::= SEQUENCE {
	mrb-ID								MRB-ID,
	qosflow-setup						QoS-Flow-List			OPTIONAL,
	qosflow-failed						QoS-Flow-Failed-List		OPTIONAL,
	bcBearerContextF1U-TNLInfoatCU 		BCBearerContextF1U-TNLInfoatCU		OPTIONAL,
	iE-Extensions		ProtocolExtensionContainer { {BCMRBSetupModifyResponseList-Item-ExtIEs} }	OPTIONAL,
	...
}

BCMRBSetupModifyResponseList-Item-ExtIEs E1AP-PROTOCOL-EXTENSION ::= {
	{ID id-F1U-TNL-InfoAddedOrModified-List	CRITICALITY ignore	EXTENSION F1U-TNL-InfoAddedOrModified-List	PRESENCE optional},
	...
}

BroadcastF1U-ContextReferenceE1 ::= OCTET STRING (SIZE(4))


-- BCBearerContextToModifyRequired

BCBearerContextToModifyRequired ::= SEQUENCE {
	bcMRBToRemoveList	BCMRBRemoveConfiguration			OPTIONAL,
	iE-Extensions		ProtocolExtensionContainer { {BCBearerContextToModifyRequired-ExtIEs} }	OPTIONAL,
	...
}

BCBearerContextToModifyRequired-ExtIEs E1AP-PROTOCOL-EXTENSION ::= {
	...
}

-- BCBearerContextToModifyConfirm

BCBearerContextToModifyConfirm ::= SEQUENCE {
	iE-Extensions		ProtocolExtensionContainer { {BCBearerContextToModifyConfirm-ExtIEs} }	OPTIONAL,
	...
}

BCBearerContextToModifyConfirm-ExtIEs E1AP-PROTOCOL-EXTENSION ::= {
	...
}

BearerContextStatusChange	::= 	ENUMERATED {
	suspend,
	resume,
	... ,
	resumeforSDT
}

BitRate ::= INTEGER (0..4000000000000,...)

BufferSize	::=	ENUMERATED	{
	kbyte2,
	kbyte4,
	kbyte8,
	...
}


-- C

Cause ::= CHOICE {
	radioNetwork		CauseRadioNetwork,
	transport			CauseTransport,
	protocol			CauseProtocol,
	misc				CauseMisc,
	choice-extension	ProtocolIE-SingleContainer	{{Cause-ExtIEs}}
}

Cause-ExtIEs E1AP-PROTOCOL-IES ::= {
	...
}

CauseMisc ::= ENUMERATED {
	control-processing-overload,
	not-enough-user-plane-processing-resources,
	hardware-failure,
	om-intervention,
	unspecified,
	...
}

CauseProtocol ::= ENUMERATED {
	transfer-syntax-error,
	abstract-syntax-error-reject,
	abstract-syntax-error-ignore-and-notify,
	message-not-compatible-with-receiver-state,
	semantic-error,
	abstract-syntax-error-falsely-constructed-message,
	unspecified,
	...
}

CauseRadioNetwork ::= ENUMERATED {
	unspecified,
	unknown-or-already-allocated-gnb-cu-cp-ue-e1ap-id,
	unknown-or-already-allocated-gnb-cu-up-ue-e1ap-id,
	unknown-or-inconsistent-pair-of-ue-e1ap-id,
	interaction-with-other-procedure,
	pPDCP-Count-wrap-around,
	not-supported-QCI-value,
	not-supported-5QI-value,
	encryption-algorithms-not-supported,
	integrity-protection-algorithms-not-supported,
	uP-integrity-protection-not-possible,
	uP-confidentiality-protection-not-possible,
	multiple-PDU-Session-ID-Instances,
	unknown-PDU-Session-ID,
	multiple-QoS-Flow-ID-Instances,
	unknown-QoS-Flow-ID,
	multiple-DRB-ID-Instances,
	unknown-DRB-ID,
	invalid-QoS-combination,
	procedure-cancelled,
	normal-release,
	no-radio-resources-available,
	action-desirable-for-radio-reasons,
	resources-not-available-for-the-slice,
	pDCP-configuration-not-supported,
	...,
	ue-dl-max-IP-data-rate-reason,
	uP-integrity-protection-failure,
	release-due-to-pre-emption,
	rsn-not-available-for-the-up,
	nPN-not-supported,
	report-characteristic-empty,
	existing-measurement-ID,
	measurement-temporarily-not-available,
	measurement-not-supported-for-the-object,
	scg-activation-deactivation-failure,
	scg-deactivation-failure-due-to-data-transmission,
	unknown-or-already-allocated-gNB-CU-CP-MBS-E1AP-ID,
	unknown-or-already-allocated-gNB-CU-UP-MBS-E1AP-ID,
	unknown-or-inconsistent-pair-of-MBS-E1AP-ID,
	unknown-or-inconsistent-MRB-ID
}

CauseTransport ::= ENUMERATED {
	unspecified,
	transport-resource-unavailable,
	...,
	unknown-TNL-address-for-IAB
}

Cell-Group-Information	::= SEQUENCE (SIZE(1.. maxnoofCellGroups)) OF Cell-Group-Information-Item

Cell-Group-Information-Item	::=	SEQUENCE {
	cell-Group-ID							Cell-Group-ID,
	uL-Configuration						UL-Configuration		OPTIONAL,
	dL-TX-Stop								DL-TX-Stop				OPTIONAL,
	rAT-Type								RAT-Type				OPTIONAL,
	iE-Extensions							ProtocolExtensionContainer { { Cell-Group-Information-Item-ExtIEs } }	OPTIONAL,
	...
}

Cell-Group-Information-Item-ExtIEs		E1AP-PROTOCOL-EXTENSION ::= {
	{ ID id-Number-of-tunnels	CRITICALITY ignore	EXTENSION Number-of-tunnels 	PRESENCE optional},
	...
}


Cell-Group-ID	::=		INTEGER (0..3, ...)

CHOInitiation	::=		ENUMERATED {true, ...}

Number-of-tunnels  ::=		INTEGER (1..4, ...)

CipheringAlgorithm	::=	ENUMERATED {
	nEA0,
	c-128-NEA1,
	c-128-NEA2,
	c-128-NEA3,
	...
}

CNSupport ::= ENUMERATED {
	c-epc,
	c-5gc,
	both,
	...
}

CommonNetworkInstance ::= OCTET STRING

ConfidentialityProtectionIndication ::= ENUMERATED {
	required,
	preferred,
	not-needed,
	...
}


ConfidentialityProtectionResult ::= ENUMERATED {
	performed,
	not-performed,
	...
}

CP-TNL-Information		::= 	CHOICE {
	endpoint-IP-Address		TransportLayerAddress,
	choice-extension		ProtocolIE-SingleContainer	{{CP-TNL-Information-ExtIEs}}
}

CP-TNL-Information-ExtIEs E1AP-PROTOCOL-IES ::= {
	{ ID id-endpoint-IP-Address-and-Port	CRITICALITY reject	TYPE Endpoint-IP-address-and-port 	PRESENCE mandatory},
	...
}


CriticalityDiagnostics ::= SEQUENCE {
	procedureCode					ProcedureCode					OPTIONAL,
	triggeringMessage				TriggeringMessage				OPTIONAL,
	procedureCriticality			Criticality						OPTIONAL,
	transactionID					TransactionID					OPTIONAL,
	iEsCriticalityDiagnostics		CriticalityDiagnostics-IE-List	OPTIONAL,
	iE-Extensions					ProtocolExtensionContainer { {CriticalityDiagnostics-ExtIEs} }	OPTIONAL,
	...
}


CriticalityDiagnostics-ExtIEs E1AP-PROTOCOL-EXTENSION ::= {
	...
}

CriticalityDiagnostics-IE-List ::= SEQUENCE (SIZE (1..maxnoofErrors)) OF
	SEQUENCE {
		iECriticality			Criticality,
		iE-ID					ProtocolIE-ID,
		typeOfError				TypeOfError,
		iE-Extensions			ProtocolExtensionContainer { {CriticalityDiagnostics-IE-List-ExtIEs} } OPTIONAL,
		...
}

CriticalityDiagnostics-IE-List-ExtIEs E1AP-PROTOCOL-EXTENSION ::= {
	...
}

-- D

DAPSRequestInfo ::= SEQUENCE {
	dapsIndicator				ENUMERATED {daps-HO-required, ...},
	iE-Extensions				ProtocolExtensionContainer { {DAPSRequestInfo-ExtIEs} } OPTIONAL,
	...
}

DAPSRequestInfo-ExtIEs E1AP-PROTOCOL-EXTENSION ::= {
	...
}

DataCollectionID ::= SEQUENCE {
	gNB-CU-CP-Measurement-ID					INTEGER (1..4095, ...),
	gNB-CU-UP-Measurement-ID					INTEGER (1..4095, ...),
	iE-Extensions								ProtocolExtensionContainer { { DataCollectionID-ExtIEs} } OPTIONAL,
	...
}

DataCollectionID-ExtIEs E1AP-PROTOCOL-EXTENSION ::= {
	...
}

Data-Forwarding-Information-Request	::=	SEQUENCE {
	data-Forwarding-Request					Data-Forwarding-Request,
	qoS-Flows-Forwarded-On-Fwd-Tunnels	QoS-Flow-Mapping-List			OPTIONAL,
	iE-Extensions							ProtocolExtensionContainer { { Data-Forwarding-Information-Request-ExtIEs } }	OPTIONAL,
	...
}

Data-Forwarding-Information-Request-ExtIEs		E1AP-PROTOCOL-EXTENSION ::= {
	...
}

Data-Forwarding-Information	::=	SEQUENCE {
	uL-Data-Forwarding						UP-TNL-Information		OPTIONAL,
	dL-Data-Forwarding						UP-TNL-Information		OPTIONAL,
	iE-Extensions							ProtocolExtensionContainer { { Data-Forwarding-Information-ExtIEs } }	OPTIONAL,
	...
}

Data-Forwarding-Information-ExtIEs		E1AP-PROTOCOL-EXTENSION ::= {
	{ID id-DataForwardingtoNG-RANQoSFlowInformationList	CRITICALITY ignore	EXTENSION DataForwardingtoNG-RANQoSFlowInformationList	PRESENCE optional}|
	{ID id-PDUSetbasedHandlingIndicator CRITICALITY ignore	EXTENSION PDUSetbasedHandlingIndicator								PRESENCE optional},
	...
}

Data-Forwarding-Request ::= ENUMERATED	{
	uL,
	dL,
	both,
	...
}

DataForwardingtoE-UTRANInformationList ::= SEQUENCE (SIZE(1.. maxnoofDataForwardingTunneltoE-UTRAN)) OF DataForwardingtoE-UTRANInformationListItem

DataForwardingtoE-UTRANInformationListItem ::= SEQUENCE {
	data-forwarding-tunnel-information							UP-TNL-Information,
	qoS-Flows-to-be-forwarded-List						QoS-Flows-to-be-forwarded-List,
	iE-Extensions		ProtocolExtensionContainer { { DataForwardingtoE-UTRANInformationListItem-ExtIEs} }	OPTIONAL,
	...
}

DataForwardingtoE-UTRANInformationListItem-ExtIEs E1AP-PROTOCOL-EXTENSION ::= {
	...
}

Data-Usage-per-PDU-Session-Report ::= SEQUENCE {
	secondaryRATType			ENUMERATED {nR, e-UTRA, ...},
	pDU-session-Timed-Report-List			SEQUENCE (SIZE(1..maxnooftimeperiods)) OF MRDC-Data-Usage-Report-Item,
	iE-Extensions				ProtocolExtensionContainer { { Data-Usage-per-PDU-Session-Report-ExtIEs} } OPTIONAL,
...
}

Data-Usage-per-PDU-Session-Report-ExtIEs E1AP-PROTOCOL-EXTENSION ::= {
	...
}

Data-Usage-per-QoS-Flow-List	::= SEQUENCE (SIZE(1..maxnoofQoSFlows)) OF Data-Usage-per-QoS-Flow-Item

Data-Usage-per-QoS-Flow-Item ::= SEQUENCE {
	qoS-Flow-Identifier		QoS-Flow-Identifier,
	secondaryRATType			ENUMERATED {nR, e-UTRA, ...},
	qoS-Flow-Timed-Report-List			SEQUENCE (SIZE(1..maxnooftimeperiods)) OF MRDC-Data-Usage-Report-Item,
	iE-Extensions				ProtocolExtensionContainer { { Data-Usage-per-QoS-Flow-Item-ExtIEs} } OPTIONAL,
...
}

Data-Usage-per-QoS-Flow-Item-ExtIEs E1AP-PROTOCOL-EXTENSION ::= {
	...
}

Data-Usage-Report-List	::= SEQUENCE (SIZE(1.. maxnoofDRBs)) OF Data-Usage-Report-Item

Data-Usage-Report-Item	::= SEQUENCE {
	dRB-ID						DRB-ID,
	rAT-Type					RAT-Type,
	dRB-Usage-Report-List		DRB-Usage-Report-List,
	iE-Extensions	ProtocolExtensionContainer { { Data-Usage-Report-ItemExtIEs } }	OPTIONAL,
	...
}

Data-Usage-Report-ItemExtIEs 	E1AP-PROTOCOL-EXTENSION ::= {
	...
}

DefaultDRB	::=	ENUMERATED	{
	true,
	false,
	...
}

Dictionary	::=	ENUMERATED	{
	sip-SDP,
	operator,
	...
}

DirectForwardingPathAvailability ::= ENUMERATED {
	inter-system-direct-path-available,
	...,
	intra-system-direct-path-available
}

DiscardTimer	::=	ENUMERATED {ms10, ms20, ms30, ms40, ms50, ms60, ms75, ms100, ms150, ms200, ms250, ms300, ms500, ms750, ms1500, infinity}

DiscardTimerExtended	::=	ENUMERATED {ms0dot5, ms1, ms2, ms4, ms6, ms8,..., ms2000}

PSIbasedDiscardTimer	::=	ENUMERATED {ms0, ms2, ms4, ms6, ms8, ms10, ms12, ms14, ms18, ms22, ms26, ms30, ms40, ms50, ms75, ms100, ...}

DLDiscarding ::= SEQUENCE {
	dLDiscardingCountVal			PDCP-Count,
	iE-Extensions					ProtocolExtensionContainer { { DLDiscarding-ExtIEs } } 		OPTIONAL
}

DLDiscarding-ExtIEs E1AP-PROTOCOL-EXTENSION ::= {
	...
}

DL-PDU-Set-Info-Marking-Support-Ind	::=	ENUMERATED {true, ...}

DLUPTNLAddressToUpdateItem	::= SEQUENCE {
	oldTNLAdress						TransportLayerAddress,
	newTNLAdress						TransportLayerAddress,
	iE-Extensions	ProtocolExtensionContainer { { DLUPTNLAddressToUpdateItemExtIEs } }	OPTIONAL,
	...
}

DLUPTNLAddressToUpdateItemExtIEs 	E1AP-PROTOCOL-EXTENSION ::= {
	...
}

DL-TX-Stop	::=	ENUMERATED	{
	stop,
	resume,
	...
}

DRB-Activity	::= ENUMERATED {
	active,
	not-active,
	...
}

DRB-Activity-List ::= SEQUENCE (SIZE(1..maxnoofDRBs)) OF DRB-Activity-Item

DRB-Activity-Item	::= SEQUENCE {
	dRB-ID						DRB-ID,
	dRB-Activity				DRB-Activity,
	iE-Extensions	ProtocolExtensionContainer { { DRB-Activity-ItemExtIEs } }	OPTIONAL,
	...
}

DRB-Activity-ItemExtIEs 	E1AP-PROTOCOL-EXTENSION ::= {
	...
}

DRB-Confirm-Modified-List-EUTRAN	::= SEQUENCE (SIZE(1.. maxnoofDRBs)) OF DRB-Confirm-Modified-Item-EUTRAN

DRB-Confirm-Modified-Item-EUTRAN	::=	SEQUENCE {
	dRB-ID									DRB-ID,
	cell-Group-Information					Cell-Group-Information	OPTIONAL,
	iE-Extensions							ProtocolExtensionContainer { { DRB-Confirm-Modified-Item-EUTRAN-ExtIEs } }	OPTIONAL,
	...
}

DRB-Confirm-Modified-Item-EUTRAN-ExtIEs		E1AP-PROTOCOL-EXTENSION ::= {
	...
}

DRB-Confirm-Modified-List-NG-RAN	::= SEQUENCE (SIZE(1.. maxnoofDRBs)) OF DRB-Confirm-Modified-Item-NG-RAN

DRB-Confirm-Modified-Item-NG-RAN	::=	SEQUENCE {
	dRB-ID									DRB-ID,
	cell-Group-Information					Cell-Group-Information	OPTIONAL,
	iE-Extensions							ProtocolExtensionContainer { { DRB-Confirm-Modified-Item-NG-RAN-ExtIEs } }	OPTIONAL,
	...
}

DRB-Confirm-Modified-Item-NG-RAN-ExtIEs		E1AP-PROTOCOL-EXTENSION ::= {
	...
}

DRB-Failed-List-EUTRAN	::= SEQUENCE (SIZE(1.. maxnoofDRBs)) OF DRB-Failed-Item-EUTRAN

DRB-Failed-Item-EUTRAN	::=	SEQUENCE {
	dRB-ID									DRB-ID,
	cause									Cause,
	iE-Extensions							ProtocolExtensionContainer { { DRB-Failed-Item-EUTRAN-ExtIEs } }	OPTIONAL,
	...
}

DRB-Failed-Item-EUTRAN-ExtIEs		E1AP-PROTOCOL-EXTENSION ::= {
	...
}

DRB-Failed-Mod-List-EUTRAN	::= SEQUENCE (SIZE(1.. maxnoofDRBs)) OF DRB-Failed-Mod-Item-EUTRAN

DRB-Failed-Mod-Item-EUTRAN	::=	SEQUENCE {
	dRB-ID									DRB-ID,
	cause									Cause,
	iE-Extensions							ProtocolExtensionContainer { { DRB-Failed-Mod-Item-EUTRAN-ExtIEs } }	OPTIONAL,
	...
}

DRB-Failed-Mod-Item-EUTRAN-ExtIEs		E1AP-PROTOCOL-EXTENSION ::= {
	...
}

DRB-Failed-List-NG-RAN	::= SEQUENCE (SIZE(1.. maxnoofDRBs)) OF DRB-Failed-Item-NG-RAN

DRB-Failed-Item-NG-RAN	::=	SEQUENCE {
	dRB-ID									DRB-ID,
	cause									Cause,
	iE-Extensions							ProtocolExtensionContainer { { DRB-Failed-Item-NG-RAN-ExtIEs } }	OPTIONAL,
	...
}

DRB-Failed-Item-NG-RAN-ExtIEs		E1AP-PROTOCOL-EXTENSION ::= {
	...
}

DRB-Failed-Mod-List-NG-RAN	::= SEQUENCE (SIZE(1.. maxnoofDRBs)) OF DRB-Failed-Mod-Item-NG-RAN

DRB-Failed-Mod-Item-NG-RAN	::=	SEQUENCE {
	dRB-ID									DRB-ID,
	cause									Cause,
	iE-Extensions							ProtocolExtensionContainer { { DRB-Failed-Mod-Item-NG-RAN-ExtIEs } }	OPTIONAL,
	...
}

DRB-Failed-Mod-Item-NG-RAN-ExtIEs		E1AP-PROTOCOL-EXTENSION ::= {
	...
}

DRB-Failed-To-Modify-List-EUTRAN	::= SEQUENCE (SIZE(1.. maxnoofDRBs)) OF DRB-Failed-To-Modify-Item-EUTRAN

DRB-Failed-To-Modify-Item-EUTRAN	::=	SEQUENCE {
	dRB-ID									DRB-ID,
	cause									Cause,
	iE-Extensions							ProtocolExtensionContainer { { DRB-Failed-To-Modify-Item-EUTRAN-ExtIEs } }	OPTIONAL,
	...
}

DRB-Failed-To-Modify-Item-EUTRAN-ExtIEs		E1AP-PROTOCOL-EXTENSION ::= {
	...
}

DRB-Failed-To-Modify-List-NG-RAN	::= SEQUENCE (SIZE(1.. maxnoofDRBs)) OF DRB-Failed-To-Modify-Item-NG-RAN

DRB-Failed-To-Modify-Item-NG-RAN	::=	SEQUENCE {
	dRB-ID									DRB-ID,
	cause									Cause,
	iE-Extensions							ProtocolExtensionContainer { { DRB-Failed-To-Modify-Item-NG-RAN-ExtIEs } }	OPTIONAL,
	...
}

DRB-Failed-To-Modify-Item-NG-RAN-ExtIEs		E1AP-PROTOCOL-EXTENSION ::= {
	...
}

DRB-ID	::=	INTEGER (1..32, ...)
DRB-Measurement-Results-Information-List	::= SEQUENCE (SIZE(1.. maxnoofDRBs)) OF DRB-Measurement-Results-Information-Item
DRB-Measurement-Results-Information-Item	::=	SEQUENCE {
	dRB-ID										DRB-ID,
	uL-D1-Result								INTEGER (0..10000, ...)							OPTIONAL,
	iE-Extensions							ProtocolExtensionContainer { { DRB-Measurement-Results-Information-Item-ExtIEs } }	OPTIONAL,
	...
}

DRB-Measurement-Results-Information-Item-ExtIEs		E1AP-PROTOCOL-EXTENSION ::= {
	...
}

DRB-Modified-List-EUTRAN	::= SEQUENCE (SIZE(1.. maxnoofDRBs)) OF DRB-Modified-Item-EUTRAN

DRB-Modified-Item-EUTRAN	::=	SEQUENCE {
	dRB-ID									DRB-ID,
	s1-DL-UP-TNL-Information				UP-TNL-Information						OPTIONAL,
	pDCP-SN-Status-Information				PDCP-SN-Status-Information				OPTIONAL,
	uL-UP-Transport-Parameters				UP-Parameters							OPTIONAL,
	iE-Extensions							ProtocolExtensionContainer { { DRB-Modified-Item-EUTRAN-ExtIEs } }	OPTIONAL,
	...
}

DRB-Modified-Item-EUTRAN-ExtIEs		E1AP-PROTOCOL-EXTENSION ::= {
	...
}

DRB-Modified-List-NG-RAN	::= SEQUENCE (SIZE(1.. maxnoofDRBs)) OF DRB-Modified-Item-NG-RAN

DRB-Modified-Item-NG-RAN	::=	SEQUENCE {
	dRB-ID										DRB-ID,
	uL-UP-Transport-Parameters					UP-Parameters							OPTIONAL,
	pDCP-SN-Status-Information					PDCP-SN-Status-Information				OPTIONAL,
	flow-Setup-List								QoS-Flow-List							OPTIONAL,
	flow-Failed-List							QoS-Flow-Failed-List					OPTIONAL,
	iE-Extensions							ProtocolExtensionContainer { { DRB-Modified-Item-NG-RAN-ExtIEs } }	OPTIONAL,
	...
}

DRB-Modified-Item-NG-RAN-ExtIEs		E1AP-PROTOCOL-EXTENSION ::= {
	{ID id-EarlyForwardingCOUNTInfo				CRITICALITY reject	EXTENSION EarlyForwardingCOUNTInfo		PRESENCE optional}|
	{ID id-OldQoSFlowMap-ULendmarkerexpected	CRITICALITY ignore	EXTENSION QoS-Flow-List						PRESENCE optional},
	...
}

DRB-Removed-Item	::=	SEQUENCE {
	dRB-ID									DRB-ID,
	dRB-Released-In-Session					ENUMERATED {released-in-session, not-released-in-session, ...}		OPTIONAL,
	dRB-Accumulated-Session-Time			OCTET STRING (SIZE(5))													OPTIONAL,
	qoS-Flow-Removed-List					SEQUENCE (SIZE(1.. maxnoofQoSFlows)) OF QoS-Flow-Removed-Item		OPTIONAL,
	iE-Extensions							ProtocolExtensionContainer { { DRB-Removed-Item-ExtIEs } }			OPTIONAL,
	...
}

DRB-Removed-Item-ExtIEs		E1AP-PROTOCOL-EXTENSION ::= {
	...
}

DRB-Required-To-Modify-List-EUTRAN ::= SEQUENCE (SIZE(1.. maxnoofDRBs)) OF DRB-Required-To-Modify-Item-EUTRAN

DRB-Required-To-Modify-Item-EUTRAN	::=	SEQUENCE {
	dRB-ID									DRB-ID,
	s1-DL-UP-TNL-Information				UP-TNL-Information							OPTIONAL,
	gNB-CU-UP-CellGroupRelatedConfiguration	GNB-CU-UP-CellGroupRelatedConfiguration		OPTIONAL,
	cause									Cause		OPTIONAL,
	iE-Extensions							ProtocolExtensionContainer { { DRB-Required-To-Modify-Item-EUTRAN-ExtIEs } }	OPTIONAL,
	...
}

DRB-Required-To-Modify-Item-EUTRAN-ExtIEs		E1AP-PROTOCOL-EXTENSION ::= {
	...
}

DRB-Required-To-Modify-List-NG-RAN ::= SEQUENCE (SIZE(1.. maxnoofDRBs)) OF DRB-Required-To-Modify-Item-NG-RAN

DRB-Required-To-Modify-Item-NG-RAN	::=	SEQUENCE {
	dRB-ID									DRB-ID,
	gNB-CU-UP-CellGroupRelatedConfiguration	GNB-CU-UP-CellGroupRelatedConfiguration		OPTIONAL,
	flow-To-Remove							QoS-Flow-List								OPTIONAL,
	cause									Cause		OPTIONAL,
	iE-Extensions							ProtocolExtensionContainer { { DRB-Required-To-Modify-Item-NG-RAN-ExtIEs } }	OPTIONAL,
	...
}

DRB-Required-To-Modify-Item-NG-RAN-ExtIEs		E1AP-PROTOCOL-EXTENSION ::= {
	...
}


DRB-Setup-List-EUTRAN	::= SEQUENCE (SIZE(1.. maxnoofDRBs)) OF DRB-Setup-Item-EUTRAN

DRB-Setup-Item-EUTRAN	::=	SEQUENCE {
	dRB-ID									DRB-ID,
	s1-DL-UP-TNL-Information				UP-TNL-Information,
	data-Forwarding-Information-Response	Data-Forwarding-Information		OPTIONAL,
	uL-UP-Transport-Parameters				UP-Parameters,
	s1-DL-UP-Unchanged						ENUMERATED {true, ...}		OPTIONAL,
	iE-Extensions							ProtocolExtensionContainer { { DRB-Setup-Item-EUTRAN-ExtIEs } }	OPTIONAL,
	...
}

DRB-Setup-Item-EUTRAN-ExtIEs		E1AP-PROTOCOL-EXTENSION ::= {
	{ID id-DataForwardingSourceIPAddress			CRITICALITY ignore	EXTENSION TransportLayerAddress		PRESENCE optional}|
	{ID id-SecurityResult							CRITICALITY ignore	EXTENSION SecurityResult				PRESENCE optional},
	...
}

DRB-Setup-Mod-List-EUTRAN	::= SEQUENCE (SIZE(1.. maxnoofDRBs)) OF DRB-Setup-Mod-Item-EUTRAN

DRB-Setup-Mod-Item-EUTRAN	::=	SEQUENCE {
	dRB-ID									DRB-ID,
	s1-DL-UP-TNL-Information				UP-TNL-Information,
	data-Forwarding-Information-Response	Data-Forwarding-Information		OPTIONAL,
	uL-UP-Transport-Parameters				UP-Parameters,
	iE-Extensions							ProtocolExtensionContainer { { DRB-Setup-Mod-Item-EUTRAN-ExtIEs } }	OPTIONAL,
	...
}

DRB-Setup-Mod-Item-EUTRAN-ExtIEs		E1AP-PROTOCOL-EXTENSION ::= {
	{ID id-SecurityResult			CRITICALITY ignore	EXTENSION SecurityResult				PRESENCE optional}|
	{ID id-DataForwardingSourceIPAddress			CRITICALITY ignore	EXTENSION TransportLayerAddress		PRESENCE optional},
	...
}

DRB-Setup-List-NG-RAN	::= SEQUENCE (SIZE(1.. maxnoofDRBs)) OF DRB-Setup-Item-NG-RAN

DRB-Setup-Item-NG-RAN	::=	SEQUENCE {
	dRB-ID										DRB-ID,
	dRB-data-Forwarding-Information-Response	Data-Forwarding-Information		OPTIONAL,
	uL-UP-Transport-Parameters					UP-Parameters,
	flow-Setup-List								QoS-Flow-List,
	flow-Failed-List							QoS-Flow-Failed-List	OPTIONAL,
	iE-Extensions								ProtocolExtensionContainer { { DRB-Setup-Item-NG-RAN-ExtIEs } }	OPTIONAL,
	...
}

DRB-Setup-Item-NG-RAN-ExtIEs		E1AP-PROTOCOL-EXTENSION ::= {
	...
}

DRB-Setup-Mod-List-NG-RAN	::= SEQUENCE (SIZE(1.. maxnoofDRBs)) OF DRB-Setup-Mod-Item-NG-RAN

DRB-Setup-Mod-Item-NG-RAN	::=	SEQUENCE {
	dRB-ID										DRB-ID,
	dRB-data-Forwarding-Information-Response	Data-Forwarding-Information		OPTIONAL,
	uL-UP-Transport-Parameters					UP-Parameters,
	flow-Setup-List								QoS-Flow-List,
	flow-Failed-List							QoS-Flow-Failed-List	OPTIONAL,
	iE-Extensions								ProtocolExtensionContainer { { DRB-Setup-Mod-Item-NG-RAN-ExtIEs } }	OPTIONAL,
	...
}

DRB-Setup-Mod-Item-NG-RAN-ExtIEs		E1AP-PROTOCOL-EXTENSION ::= {
	...
}

DRB-Status-Item	::= SEQUENCE {
	dRB-ID						DRB-ID,
	pDCP-DL-Count				PDCP-Count		OPTIONAL,
	pDCP-UL-Count				PDCP-Count		OPTIONAL,
	iE-Extensions	ProtocolExtensionContainer { { DRB-Status-ItemExtIEs } }	OPTIONAL,
	...
}

DRB-Status-ItemExtIEs 	E1AP-PROTOCOL-EXTENSION ::= {
	...
}

DRBs-Subject-To-Counter-Check-List-EUTRAN	::= SEQUENCE (SIZE(1.. maxnoofDRBs)) OF DRBs-Subject-To-Counter-Check-Item-EUTRAN

DRBs-Subject-To-Counter-Check-Item-EUTRAN	::=	SEQUENCE {
	dRB-ID						DRB-ID,
	pDCP-UL-Count				PDCP-Count,
	pDCP-DL-Count				PDCP-Count,
	iE-Extensions		ProtocolExtensionContainer { { DRBs-Subject-To-Counter-Check-Item-EUTRAN-ExtIEs } }	OPTIONAL,
	...
}

DRBs-Subject-To-Counter-Check-Item-EUTRAN-ExtIEs		E1AP-PROTOCOL-EXTENSION ::= {
	...
}

DRBs-Subject-To-Counter-Check-List-NG-RAN	::= SEQUENCE (SIZE(1.. maxnoofDRBs)) OF DRBs-Subject-To-Counter-Check-Item-NG-RAN

DRBs-Subject-To-Counter-Check-Item-NG-RAN	::=	SEQUENCE {
	pDU-Session-ID				PDU-Session-ID,
	dRB-ID						DRB-ID,
	pDCP-UL-Count				PDCP-Count,
	pDCP-DL-Count				PDCP-Count,
	iE-Extensions			ProtocolExtensionContainer { { DRBs-Subject-To-Counter-Check-Item-NG-RAN-ExtIEs } }	OPTIONAL,
	...
}

DRBs-Subject-To-Counter-Check-Item-NG-RAN-ExtIEs		E1AP-PROTOCOL-EXTENSION ::= {
	...
}

DRBs-Subject-To-Early-Forwarding-List	::= SEQUENCE (SIZE(1.. maxnoofDRBs)) OF DRBs-Subject-To-Early-Forwarding-Item

DRBs-Subject-To-Early-Forwarding-Item	::=	SEQUENCE {
	dRB-ID										DRB-ID,
	dLCountValue								PDCP-Count,
	iE-Extensions							ProtocolExtensionContainer { { DRBs-Subject-To-Early-Forwarding-Item-ExtIEs } }	OPTIONAL,
	...
}

DRBs-Subject-To-Early-Forwarding-Item-ExtIEs		E1AP-PROTOCOL-EXTENSION ::= {
	...
}

DRB-To-Modify-List-EUTRAN	::= SEQUENCE (SIZE(1.. maxnoofDRBs)) OF DRB-To-Modify-Item-EUTRAN

DRB-To-Modify-Item-EUTRAN	::=	SEQUENCE {
	dRB-ID									DRB-ID,
	pDCP-Configuration						PDCP-Configuration						OPTIONAL,
	eUTRAN-QoS								EUTRAN-QoS								OPTIONAL,
	s1-UL-UP-TNL-Information				UP-TNL-Information						OPTIONAL,
	data-Forwarding-Information		Data-Forwarding-Information		OPTIONAL,
	pDCP-SN-Status-Request					PDCP-SN-Status-Request						OPTIONAL,
	pDCP-SN-Status-Information				PDCP-SN-Status-Information				OPTIONAL,
	dL-UP-Parameters						UP-Parameters							OPTIONAL,
	cell-Group-To-Add						Cell-Group-Information					OPTIONAL,
	cell-Group-To-Modify					Cell-Group-Information					OPTIONAL,
	cell-Group-To-Remove					Cell-Group-Information					OPTIONAL,
	dRB-Inactivity-Timer					Inactivity-Timer						OPTIONAL,
	iE-Extensions							ProtocolExtensionContainer { { DRB-To-Modify-Item-EUTRAN-ExtIEs } }	OPTIONAL,
	...
}

DRB-To-Modify-Item-EUTRAN-ExtIEs		E1AP-PROTOCOL-EXTENSION ::= {
	...
}

DRB-To-Modify-List-NG-RAN	::= SEQUENCE (SIZE(1.. maxnoofDRBs)) OF DRB-To-Modify-Item-NG-RAN

DRB-To-Modify-Item-NG-RAN	::=	SEQUENCE {
	dRB-ID										DRB-ID,
	sDAP-Configuration							SDAP-Configuration						OPTIONAL,
	pDCP-Configuration							PDCP-Configuration						OPTIONAL,
	dRB-Data-Forwarding-Information		Data-Forwarding-Information		OPTIONAL,
	pDCP-SN-Status-Request							PDCP-SN-Status-Request						OPTIONAL,
	pdcp-SN-Status-Information					PDCP-SN-Status-Information				OPTIONAL,
	dL-UP-Parameters							UP-Parameters							OPTIONAL,
	cell-Group-To-Add							Cell-Group-Information					OPTIONAL,
	cell-Group-To-Modify						Cell-Group-Information					OPTIONAL,
	cell-Group-To-Remove						Cell-Group-Information					OPTIONAL,
	flow-Mapping-Information					QoS-Flow-QoS-Parameter-List				OPTIONAL,
	dRB-Inactivity-Timer						Inactivity-Timer						OPTIONAL,
	iE-Extensions								ProtocolExtensionContainer { { DRB-To-Modify-Item-NG-RAN-ExtIEs } }	OPTIONAL,
	...
}

DRB-To-Modify-Item-NG-RAN-ExtIEs		E1AP-PROTOCOL-EXTENSION ::= {
	{ID id-OldQoSFlowMap-ULendmarkerexpected	CRITICALITY reject	EXTENSION QoS-Flow-List	PRESENCE optional}|
	{ID id-DRB-QoS						CRITICALITY ignore	EXTENSION QoSFlowLevelQoSParameters			PRESENCE optional}|
	{ID id-EarlyForwardingCOUNTReq		CRITICALITY reject	EXTENSION EarlyForwardingCOUNTReq			PRESENCE optional}|
	{ID id-EarlyForwardingCOUNTInfo		CRITICALITY reject	EXTENSION EarlyForwardingCOUNTInfo			PRESENCE optional}|
	{ID id-DAPSRequestInfo				CRITICALITY ignore	EXTENSION DAPSRequestInfo					PRESENCE optional}|
	{ID id-EarlyDataForwardingIndicator	CRITICALITY ignore	EXTENSION EarlyDataForwardingIndicator	PRESENCE optional}|
	{ID id-SDTindicatorMod				CRITICALITY reject	EXTENSION SDTindicatorMod					PRESENCE optional}|
	{ID id-PDCP-COUNT-Reset				CRITICALITY reject	EXTENSION PDCP-COUNT-Reset					PRESENCE optional	},
	...
}

DRB-To-Remove-List-EUTRAN	::= SEQUENCE (SIZE(1.. maxnoofDRBs)) OF DRB-To-Remove-Item-EUTRAN

DRB-To-Remove-Item-EUTRAN	::=	SEQUENCE {
	dRB-ID									DRB-ID,
	iE-Extensions							ProtocolExtensionContainer { { DRB-To-Remove-Item-EUTRAN-ExtIEs } }	OPTIONAL,
	...
}

DRB-To-Remove-Item-EUTRAN-ExtIEs		E1AP-PROTOCOL-EXTENSION ::= {
	...
}

DRB-Required-To-Remove-List-EUTRAN	::= SEQUENCE (SIZE(1.. maxnoofDRBs)) OF DRB-Required-To-Remove-Item-EUTRAN

DRB-Required-To-Remove-Item-EUTRAN	::=	SEQUENCE {
	dRB-ID									DRB-ID,
	cause									Cause,
	iE-Extensions							ProtocolExtensionContainer { { DRB-Required-To-Remove-Item-EUTRAN-ExtIEs } }	OPTIONAL,
	...
}

DRB-Required-To-Remove-Item-EUTRAN-ExtIEs		E1AP-PROTOCOL-EXTENSION ::= {
	...
}

DRB-To-Remove-List-NG-RAN	::= SEQUENCE (SIZE(1.. maxnoofDRBs)) OF DRB-To-Remove-Item-NG-RAN

DRB-To-Remove-Item-NG-RAN	::=	SEQUENCE {
	dRB-ID									DRB-ID,
	iE-Extensions							ProtocolExtensionContainer { { DRB-To-Remove-Item-NG-RAN-ExtIEs } }	OPTIONAL,
	...
}

DRB-To-Remove-Item-NG-RAN-ExtIEs		E1AP-PROTOCOL-EXTENSION ::= {
	...
}

DRB-Required-To-Remove-List-NG-RAN	::= SEQUENCE (SIZE(1.. maxnoofDRBs)) OF DRB-Required-To-Remove-Item-NG-RAN

DRB-Required-To-Remove-Item-NG-RAN	::=	SEQUENCE {
	dRB-ID									DRB-ID,
	cause									Cause,
	iE-Extensions							ProtocolExtensionContainer { { DRB-Required-To-Remove-Item-NG-RAN-ExtIEs } }	OPTIONAL,
	...
}

DRB-Required-To-Remove-Item-NG-RAN-ExtIEs		E1AP-PROTOCOL-EXTENSION ::= {
	...
}

DRB-To-Report-List	::= SEQUENCE (SIZE(1.. maxnoofDRBs)) OF DRB-To-Report-Item

DRB-To-Report-Item	::=	SEQUENCE {
	dRB-ID										DRB-ID,
	uEPerformance								UEPerformance		OPTIONAL,
	iE-Extensions							ProtocolExtensionContainer { { DRB-To-Report-Item-ExtIEs } }	OPTIONAL,
	...
}

DRB-To-Report-Item-ExtIEs		E1AP-PROTOCOL-EXTENSION ::= {
	...
}

DRB-To-Setup-List-EUTRAN	::= SEQUENCE (SIZE(1.. maxnoofDRBs)) OF DRB-To-Setup-Item-EUTRAN

DRB-To-Setup-Item-EUTRAN	::=	SEQUENCE {
	dRB-ID									DRB-ID,
	pDCP-Configuration						PDCP-Configuration,
	eUTRAN-QoS								EUTRAN-QoS,
	s1-UL-UP-TNL-Information				UP-TNL-Information,
	data-Forwarding-Information-Request		Data-Forwarding-Information-Request		OPTIONAL,
	cell-Group-Information					Cell-Group-Information,
	dL-UP-Parameters						UP-Parameters							OPTIONAL,
	dRB-Inactivity-Timer					Inactivity-Timer						OPTIONAL,
	existing-Allocated-S1-DL-UP-TNL-Info	UP-TNL-Information						OPTIONAL,
	iE-Extensions							ProtocolExtensionContainer { { DRB-To-Setup-Item-EUTRAN-ExtIEs } }	OPTIONAL,
	...
}

DRB-To-Setup-Item-EUTRAN-ExtIEs		E1AP-PROTOCOL-EXTENSION ::= {
	{ID id-DataForwardingSourceIPAddress			CRITICALITY ignore	EXTENSION TransportLayerAddress		PRESENCE optional}|
	{ID id-SecurityIndication						CRITICALITY reject	EXTENSION SecurityIndication			PRESENCE optional},
	...
}

DRB-To-Setup-Mod-List-EUTRAN	::= SEQUENCE (SIZE(1.. maxnoofDRBs)) OF DRB-To-Setup-Mod-Item-EUTRAN

DRB-To-Setup-Mod-Item-EUTRAN	::=	SEQUENCE {
	dRB-ID										DRB-ID,
	pDCP-Configuration							PDCP-Configuration,
	eUTRAN-QoS									EUTRAN-QoS,
	s1-UL-UP-TNL-Information					UP-TNL-Information,
	data-Forwarding-Information-Request			Data-Forwarding-Information-Request		OPTIONAL,
	cell-Group-Information						Cell-Group-Information,
	dL-UP-Parameters							UP-Parameters							OPTIONAL,
	dRB-Inactivity-Timer						Inactivity-Timer						OPTIONAL,
	iE-Extensions								ProtocolExtensionContainer { { DRB-To-Setup-Mod-Item-EUTRAN-ExtIEs } }	OPTIONAL,
	...
}

DRB-To-Setup-Mod-Item-EUTRAN-ExtIEs		E1AP-PROTOCOL-EXTENSION ::= {
	{ID id-SecurityIndication					CRITICALITY reject	EXTENSION SecurityIndication			PRESENCE optional}|
	{ID id-DataForwardingSourceIPAddress			CRITICALITY ignore	EXTENSION TransportLayerAddress		PRESENCE optional},
	...
}

DRB-To-Setup-List-NG-RAN	::= SEQUENCE (SIZE(1.. maxnoofDRBs)) OF DRB-To-Setup-Item-NG-RAN

DRB-To-Setup-Item-NG-RAN	::=	SEQUENCE {
	dRB-ID										DRB-ID,
	sDAP-Configuration							SDAP-Configuration,
	pDCP-Configuration							PDCP-Configuration,
	cell-Group-Information						Cell-Group-Information,
	qos-flow-Information-To-Be-Setup					QoS-Flow-QoS-Parameter-List,
	dRB-Data-Forwarding-Information-Request		Data-Forwarding-Information-Request		OPTIONAL,
	dRB-Inactivity-Timer						Inactivity-Timer	OPTIONAL,
	pDCP-SN-Status-Information								PDCP-SN-Status-Information								OPTIONAL,
	iE-Extensions							ProtocolExtensionContainer { { DRB-To-Setup-Item-NG-RAN-ExtIEs } }	OPTIONAL,
	...
}

DRB-To-Setup-Item-NG-RAN-ExtIEs		E1AP-PROTOCOL-EXTENSION ::= {
	{ID id-DRB-QoS						CRITICALITY ignore	EXTENSION QoSFlowLevelQoSParameters		PRESENCE optional}|
	{ID id-DAPSRequestInfo				CRITICALITY ignore	EXTENSION DAPSRequestInfo					PRESENCE optional}|
	{ID id-ignoreMappingRuleIndication	CRITICALITY reject	EXTENSION IgnoreMappingRuleIndication	PRESENCE optional}|
	{ID id-QoSFlowsDRBRemapping			CRITICALITY reject	EXTENSION QoS-Flows-DRB-Remapping			PRESENCE optional}|
	{ID id-SDTindicatorSetup			CRITICALITY reject	EXTENSION SDTindicatorSetup					PRESENCE optional}|
	{ID id-SpecialTriggeringPurpose		CRITICALITY ignore	EXTENSION SpecialTriggeringPurpose			PRESENCE optional},
	...
}

DRB-To-Setup-Mod-List-NG-RAN	::= SEQUENCE (SIZE(1.. maxnoofDRBs)) OF DRB-To-Setup-Mod-Item-NG-RAN

DRB-To-Setup-Mod-Item-NG-RAN	::=	SEQUENCE {
	dRB-ID										DRB-ID,
	sDAP-Configuration							SDAP-Configuration,
	pDCP-Configuration							PDCP-Configuration,
	cell-Group-Information						Cell-Group-Information,
	flow-Mapping-Information					QoS-Flow-QoS-Parameter-List,
	dRB-Data-Forwarding-Information-Request		Data-Forwarding-Information-Request		OPTIONAL,
	dRB-Inactivity-Timer						Inactivity-Timer					OPTIONAL,
	pDCP-SN-Status-Information				PDCP-SN-Status-Information					OPTIONAL,
	iE-Extensions								ProtocolExtensionContainer { { DRB-To-Setup-Mod-Item-NG-RAN-ExtIEs } }	OPTIONAL,
	...
}

DRB-To-Setup-Mod-Item-NG-RAN-ExtIEs		E1AP-PROTOCOL-EXTENSION ::= {
	{ID id-DRB-QoS						CRITICALITY ignore	EXTENSION QoSFlowLevelQoSParameters		PRESENCE optional}|
	{ID id-ignoreMappingRuleIndication	CRITICALITY reject	EXTENSION IgnoreMappingRuleIndication	PRESENCE optional}|
	{ID id-DAPSRequestInfo				CRITICALITY ignore	EXTENSION DAPSRequestInfo				PRESENCE optional}|
	{ID id-SDTindicatorSetup			CRITICALITY reject	EXTENSION SDTindicatorSetup				PRESENCE optional}|
	{ID id-SpecialTriggeringPurpose		CRITICALITY ignore	EXTENSION SpecialTriggeringPurpose		PRESENCE optional},
	...
}

DRB-Usage-Report-List ::= SEQUENCE (SIZE(1..maxnooftimeperiods)) OF DRB-Usage-Report-Item

DRB-Usage-Report-Item	::= SEQUENCE {
	startTimeStamp					OCTET STRING (SIZE(4)),
	endTimeStamp					OCTET STRING (SIZE(4)),
	usageCountUL					INTEGER (0..18446744073709551615),
	usageCountDL					INTEGER (0..18446744073709551615),
	iE-Extensions					ProtocolExtensionContainer { { DRB-Usage-Report-Item-ExtIEs} } OPTIONAL,
	...
}

DRB-Usage-Report-Item-ExtIEs E1AP-PROTOCOL-EXTENSION ::= {
	...
}

Duplication-Activation	::=		ENUMERATED {
	active,
	inactive,
	...
}


Dynamic5QIDescriptor	::= SEQUENCE {
	qoSPriorityLevel					QoSPriorityLevel,
	packetDelayBudget					PacketDelayBudget,
	packetErrorRate						PacketErrorRate,
	fiveQI								INTEGER (0..255, ...)								OPTIONAL,
	delayCritical						ENUMERATED {delay-critical, non-delay-critical}		OPTIONAL,
-- This IE shall be present if the GBR QoS Flow Information IE is present in the QoS Flow Level QoS Parameters IE.--
	averagingWindow 					AveragingWindow										OPTIONAL,
-- This IE shall be present if the GBR QoS Flow Information IE is present in the QoS Flow Level QoS Parameters IE.--
	maxDataBurstVolume					MaxDataBurstVolume									OPTIONAL,
	iE-Extensions					ProtocolExtensionContainer { { Dynamic5QIDescriptor-ExtIEs } } OPTIONAL
}

Dynamic5QIDescriptor-ExtIEs E1AP-PROTOCOL-EXTENSION ::= {
	{ ID id-ExtendedPacketDelayBudget			CRITICALITY ignore	EXTENSION 	ExtendedPacketDelayBudget		PRESENCE optional	}|
	{ ID id-CNPacketDelayBudgetDownlink			CRITICALITY ignore	EXTENSION 	ExtendedPacketDelayBudget		PRESENCE optional	}|
	{ ID id-CNPacketDelayBudgetUplink			CRITICALITY ignore	EXTENSION 	ExtendedPacketDelayBudget		PRESENCE optional	},
	...
}

DataDiscardRequired	::= 	ENUMERATED {
	required,
	...
}

-- E

EarlyDataForwardingIndicator ::= ENUMERATED {stop, ...}

EarlyForwardingCOUNTInfo ::= CHOICE {
	firstDLCount					FirstDLCount,
	dLDiscardingCount				DLDiscarding,
	choice-Extension				ProtocolIE-SingleContainer { { EarlyForwardingCOUNTInfo-ExtIEs} }
}

EarlyForwardingCOUNTInfo-ExtIEs E1AP-PROTOCOL-IES ::= {
	...
}

EarlyForwardingCOUNTReq ::= ENUMERATED { first-dl-count, dl-discarding, ...}

ECNMarkingorCongestionInformationReportingRequest ::= CHOICE {
	eCNMarkingatNGRAN						ENUMERATED { ul, dl, both, stop, ...},
	eCNMarkingatUPF							ENUMERATED { ul, dl, both, stop, ...},
	congestionInformation					ENUMERATED { ul, dl, both, stop, ...},
	choice-extension	ProtocolIE-SingleContainer	{{ECNMarkingorCongestionInformationReportingRequest-ExtIEs}}
}

ECNMarkingorCongestionInformationReportingRequest-ExtIEs E1AP-PROTOCOL-IES ::= {
	...
}


ECNMarkingorCongestionInformationReportingStatus ::= ENUMERATED { active, not-active, ...}


EHC-Common-Parameters ::= SEQUENCE {
	ehc-CID-Length						ENUMERATED { bits7, bits15, ...},
	iE-Extensions						ProtocolExtensionContainer { { EHC-Common-Parameters-ExtIEs } } 		OPTIONAL
}

EHC-Common-Parameters-ExtIEs E1AP-PROTOCOL-EXTENSION ::= {
	...
}

EHC-Downlink-Parameters ::= SEQUENCE {
	drb-ContinueEHC-DL					ENUMERATED {true, ..., false},
	iE-Extensions						ProtocolExtensionContainer { { EHC-Downlink-Parameters-ExtIEs } } 		OPTIONAL
}

EHC-Downlink-Parameters-ExtIEs E1AP-PROTOCOL-EXTENSION ::= {
{ID id-MaxCIDEHCDL			CRITICALITY ignore	EXTENSION	MaxCIDEHCDL		PRESENCE optional	},
	...
}

EHC-Uplink-Parameters ::= SEQUENCE {
	drb-ContinueEHC-UL					ENUMERATED {true, ... , false},
	iE-Extensions						ProtocolExtensionContainer { { EHC-Uplink-Parameters-ExtIEs } } 		OPTIONAL
}

EHC-Uplink-Parameters-ExtIEs E1AP-PROTOCOL-EXTENSION ::= {
	...
}

EHC-Parameters ::= SEQUENCE {
	ehc-Common							EHC-Common-Parameters,
	ehc-Downlink						EHC-Downlink-Parameters					OPTIONAL,
	ehc-Uplink							EHC-Uplink-Parameters					OPTIONAL,
	iE-Extensions						ProtocolExtensionContainer { { EHC-Parameters-ExtIEs } } 		OPTIONAL
}

EHC-Parameters-ExtIEs E1AP-PROTOCOL-EXTENSION ::= {
	...
}

EncryptionKey	::=	OCTET STRING

Endpoint-IP-address-and-port::= SEQUENCE {
	endpoint-IP-Address			TransportLayerAddress,
	portNumber					PortNumber,
	iE-Extensions							ProtocolExtensionContainer { { Endpoint-IP-address-and-port-ExtIEs} } OPTIONAL
}

Endpoint-IP-address-and-port-ExtIEs E1AP-PROTOCOL-EXTENSION ::= {
	...
}

EUTRANAllocationAndRetentionPriority ::= SEQUENCE {
	priorityLevel				PriorityLevel,
	pre-emptionCapability		Pre-emptionCapability,
	pre-emptionVulnerability	Pre-emptionVulnerability,
	iE-Extensions				ProtocolExtensionContainer { {EUTRANAllocationAndRetentionPriority-ExtIEs} } OPTIONAL,
	...
}

ExtendedPacketDelayBudget ::= INTEGER (1..65535, ..., 65536..109999)

EUTRANAllocationAndRetentionPriority-ExtIEs E1AP-PROTOCOL-EXTENSION ::= {
	...
}


E-UTRAN-Cell-Identity	::=		BIT STRING (SIZE(28))

ECGI ::= SEQUENCE {
	pLMN-Identity			PLMN-Identity,
	eUTRAN-Cell-Identity	E-UTRAN-Cell-Identity,
	iE-Extensions			ProtocolExtensionContainer { { ECGI-ExtIEs } }	OPTIONAL
}

ECGI-ExtIEs	E1AP-PROTOCOL-EXTENSION ::= {
	...
}

ECGI-Support-List ::= SEQUENCE (SIZE(1.. maxnoofECGI)) OF ECGI-Support-Item

ECGI-Support-Item ::= SEQUENCE {
	eCGI	ECGI,
	iE-Extensions				ProtocolExtensionContainer { { ECGI-Support-Item-ExtIEs } }	OPTIONAL
}

ECGI-Support-Item-ExtIEs	E1AP-PROTOCOL-EXTENSION ::= {
	...
}

EUTRAN-QoS-Support-List ::= SEQUENCE (SIZE(1.. maxnoofEUTRANQOSParameters)) OF EUTRAN-QoS-Support-Item

EUTRAN-QoS-Support-Item ::= SEQUENCE {
	eUTRAN-QoS	EUTRAN-QoS,
	iE-Extensions			ProtocolExtensionContainer { { EUTRAN-QoS-Support-Item-ExtIEs } }	OPTIONAL
}

EUTRAN-QoS-Support-Item-ExtIEs	E1AP-PROTOCOL-EXTENSION ::= {
	...
}

EUTRAN-QoS	::= SEQUENCE {
	qCI										QCI,
	eUTRANallocationAndRetentionPriority	EUTRANAllocationAndRetentionPriority,
	gbrQosInformation						GBR-QosInformation										OPTIONAL,
	iE-Extensions							ProtocolExtensionContainer { { EUTRAN-QoS-ExtIEs } }	OPTIONAL,
	...
}

EUTRAN-QoS-ExtIEs E1AP-PROTOCOL-EXTENSION ::= {
	...
}

ExtendedSliceSupportList ::= SEQUENCE (SIZE(1.. maxnoofExtSliceItems)) OF Slice-Support-Item

-- F

FirstDLCount ::= SEQUENCE {
	firstDLCountVal					PDCP-Count,
	iE-Extensions					ProtocolExtensionContainer { { FirstDLCount-ExtIEs } } 		OPTIONAL
}

FirstDLCount-ExtIEs E1AP-PROTOCOL-EXTENSION ::= {
	...
}

FiveGS-TAC ::= OCTET STRING (SIZE(3))

F1U-TNL-InfoAdded-List ::= SEQUENCE (SIZE(1..maxnoofDUs)) OF F1U-TNL-InfoAdded-Item

F1U-TNL-InfoAdded-Item ::= SEQUENCE {
	broadcastF1U-ContextReferenceE1				BroadcastF1U-ContextReferenceE1,
	bcBearerContextF1U-TNLInfoatCU				BCBearerContextF1U-TNLInfoatCU,
	iE-Extensions		ProtocolExtensionContainer { {F1U-TNL-InfoAdded-Item-ExtIEs} }	OPTIONAL,
	...
}

F1U-TNL-InfoAdded-Item-ExtIEs E1AP-PROTOCOL-EXTENSION ::= {
	...
}

F1U-TNL-InfoToAdd-List ::= SEQUENCE (SIZE(1..maxnoofDUs)) OF F1U-TNL-InfoToAdd-Item

F1U-TNL-InfoToAdd-Item ::= SEQUENCE {
	broadcastF1U-ContextReferenceE1				BroadcastF1U-ContextReferenceE1,
	iE-Extensions		ProtocolExtensionContainer { {F1U-TNL-InfoToAdd-Item-ExtIEs} }	OPTIONAL,
	...
}

F1U-TNL-InfoToAdd-Item-ExtIEs E1AP-PROTOCOL-EXTENSION ::= {
	...
}

F1U-TNL-InfoAddedOrModified-List ::= SEQUENCE (SIZE(1..maxnoofDUs)) OF F1U-TNL-InfoAddedOrModified-Item

F1U-TNL-InfoAddedOrModified-Item ::= SEQUENCE {
	broadcastF1U-ContextReferenceE1				BroadcastF1U-ContextReferenceE1,
	bcBearerContextF1U-TNLInfoatCU				BCBearerContextF1U-TNLInfoatCU					OPTIONAL,
	iE-Extensions		ProtocolExtensionContainer { {F1U-TNL-InfoAddedOrModified-Item-ExtIEs} }	OPTIONAL,
	...
}

F1U-TNL-InfoAddedOrModified-Item-ExtIEs E1AP-PROTOCOL-EXTENSION ::= {
	...
}

F1U-TNL-InfoToAddOrModify-List ::= SEQUENCE (SIZE(1..maxnoofDUs)) OF F1U-TNL-InfoToAddOrModify-Item

F1U-TNL-InfoToAddOrModify-Item ::= SEQUENCE {
	broadcastF1U-ContextReferenceE1				BroadcastF1U-ContextReferenceE1,
	bcBearerContextF1U-TNLInfoatDU				BCBearerContextF1U-TNLInfoatDU					OPTIONAL,
	iE-Extensions		ProtocolExtensionContainer { {F1U-TNL-InfoToAddOrModify-Item-ExtIEs} }	OPTIONAL,
	...
}

F1U-TNL-InfoToAddOrModify-Item-ExtIEs E1AP-PROTOCOL-EXTENSION ::= {
	...
}

F1U-TNL-InfoToRelease-List ::= SEQUENCE (SIZE(1..maxnoofDUs)) OF F1U-TNL-InfoToRelease-Item

F1U-TNL-InfoToRelease-Item ::= SEQUENCE {
	broadcastF1U-ContextReferenceE1				BroadcastF1U-ContextReferenceE1,
	iE-Extensions		ProtocolExtensionContainer { {F1U-TNL-InfoToRelease-Item-ExtIEs} }	OPTIONAL,
	...
}

F1U-TNL-InfoToRelease-Item-ExtIEs E1AP-PROTOCOL-EXTENSION ::= {
	...
}


-- G

GlobalMBSSessionID ::= SEQUENCE {
	tmgi	OCTET STRING (SIZE(6)),
	nid		NID						OPTIONAL,
	iE-Extensions						ProtocolExtensionContainer { { GlobalMBSSessionID-ExtIEs } } OPTIONAL,
	...
}

GlobalMBSSessionID-ExtIEs E1AP-PROTOCOL-EXTENSION ::= {
	...
}

GNB-CU-CP-Name 				::= PrintableString(SIZE(1..150,...))

Extended-GNB-CU-CP-Name	 ::= SEQUENCE {
	gNB-CU-CP-NameVisibleString			GNB-CU-CP-NameVisibleString				OPTIONAL,
	gNB-CU-CP-NameUTF8String			GNB-CU-CP-NameUTF8String				OPTIONAL,
	iE-Extensions						ProtocolExtensionContainer { { Extended-GNB-CU-CP-Name-ExtIEs } } OPTIONAL,
	...
}

Extended-GNB-CU-CP-Name-ExtIEs E1AP-PROTOCOL-EXTENSION ::= {
	...
}

GNB-CU-CP-MBS-E1AP-ID		::= INTEGER (0..16777215)

GNB-CU-CP-NameVisibleString ::= VisibleString(SIZE(1..150,...))

GNB-CU-CP-NameUTF8String ::= UTF8String(SIZE(1..150,...))

GNB-CU-CP-UE-E1AP-ID		::= INTEGER (0..4294967295)

GNB-CU-UP-Capacity				::= INTEGER (0..255)

GNB-CU-UP-CellGroupRelatedConfiguration	 ::= SEQUENCE (SIZE(1.. maxnoofUPParameters)) OF GNB-CU-UP-CellGroupRelatedConfiguration-Item

GNB-CU-UP-CellGroupRelatedConfiguration-Item ::= SEQUENCE {
	cell-Group-ID				Cell-Group-ID,
	uP-TNL-Information			UP-TNL-Information,
	uL-Configuration			UL-Configuration		OPTIONAL,
	iE-Extensions				ProtocolExtensionContainer { {GNB-CU-UP-CellGroupRelatedConfiguration-Item-ExtIEs } }	OPTIONAL
}

GNB-CU-UP-CellGroupRelatedConfiguration-Item-ExtIEs	E1AP-PROTOCOL-EXTENSION ::= {
	...
}

GNB-CU-UP-ID				::= INTEGER (0..68719476735)

GNB-CU-UP-MBS-Support-Info ::= SEQUENCE {
	mbs-Support-Info-ToAdd-List			MBS-Support-Info-ToAdd-List				OPTIONAL,
	mbs-Support-Info-ToRemove-List		MBS-Support-Info-ToRemove-List			OPTIONAL,
	iE-Extensions						ProtocolExtensionContainer { { GNB-CU-UP-MBS-Support-Info-ExtIEs } } OPTIONAL,
	...
}

GNB-CU-UP-MBS-Support-Info-ExtIEs E1AP-PROTOCOL-EXTENSION ::= {
	...
}

GNB-CU-UP-Name 				::= PrintableString(SIZE(1..150,...))

Extended-GNB-CU-UP-Name	 ::= SEQUENCE {
	gNB-CU-UP-NameVisibleString			GNB-CU-UP-NameVisibleString				OPTIONAL,
	gNB-CU-UP-NameUTF8String			GNB-CU-UP-NameUTF8String				OPTIONAL,
	iE-Extensions						ProtocolExtensionContainer { { Extended-GNB-CU-UP-Name-ExtIEs } } OPTIONAL,
	...
}

Extended-GNB-CU-UP-Name-ExtIEs E1AP-PROTOCOL-EXTENSION ::= {
	...
}

GNB-CU-UP-MBS-E1AP-ID		::= INTEGER (0..65535)

GNB-CU-UP-NameVisibleString ::= VisibleString(SIZE(1..150,...))

GNB-CU-UP-NameUTF8String ::= UTF8String(SIZE(1..150,...))

GNB-CU-UP-UE-E1AP-ID		::= INTEGER (0..4294967295)

GNB-CU-CP-TNLA-Setup-Item::= SEQUENCE {
	tNLAssociationTransportLayerAddress		CP-TNL-Information,
	iE-Extensions							ProtocolExtensionContainer { { GNB-CU-CP-TNLA-Setup-Item-ExtIEs} } OPTIONAL,
	...
}

GNB-CU-CP-TNLA-Setup-Item-ExtIEs E1AP-PROTOCOL-EXTENSION ::= {
	...
}

GNB-CU-CP-TNLA-Failed-To-Setup-Item ::= SEQUENCE {
	tNLAssociationTransportLayerAddress		CP-TNL-Information,
	cause									Cause,
	iE-Extensions							ProtocolExtensionContainer { { GNB-CU-CP-TNLA-Failed-To-Setup-Item-ExtIEs} } OPTIONAL
}

GNB-CU-CP-TNLA-Failed-To-Setup-Item-ExtIEs E1AP-PROTOCOL-EXTENSION ::= {
	...
}

GNB-CU-CP-TNLA-To-Add-Item ::= SEQUENCE {
	tNLAssociationTransportLayerAddress		CP-TNL-Information,
	tNLAssociationUsage						TNLAssociationUsage,
	iE-Extensions							ProtocolExtensionContainer { { GNB-CU-CP-TNLA-To-Add-Item-ExtIEs} } OPTIONAL
}

GNB-CU-CP-TNLA-To-Add-Item-ExtIEs E1AP-PROTOCOL-EXTENSION ::= {
	...
}

GNB-CU-CP-TNLA-To-Remove-Item::= SEQUENCE {
	tNLAssociationTransportLayerAddress		CP-TNL-Information,
	iE-Extensions							ProtocolExtensionContainer { { GNB-CU-CP-TNLA-To-Remove-Item-ExtIEs} } OPTIONAL
}

GNB-CU-CP-TNLA-To-Remove-Item-ExtIEs E1AP-PROTOCOL-EXTENSION ::= {
	{ID id-TNLAssociationTransportLayerAddressgNBCUUP	CRITICALITY reject	EXTENSION CP-TNL-Information	PRESENCE optional},
	...
}

GNB-CU-CP-TNLA-To-Update-Item::= SEQUENCE {
	tNLAssociationTransportLayerAddress		CP-TNL-Information,
	tNLAssociationUsage						TNLAssociationUsage 	OPTIONAL,
	iE-Extensions							ProtocolExtensionContainer { { GNB-CU-CP-TNLA-To-Update-Item-ExtIEs} } OPTIONAL
}

GNB-CU-CP-TNLA-To-Update-Item-ExtIEs E1AP-PROTOCOL-EXTENSION ::= {
	...
}

GNB-CU-UP-TNLA-To-Remove-Item::= SEQUENCE {
	tNLAssociationTransportLayerAddress			CP-TNL-Information,
	tNLAssociationTransportLayerAddressgNBCUCP	CP-TNL-Information		OPTIONAL,
	iE-Extensions							ProtocolExtensionContainer { { GNB-CU-UP-TNLA-To-Remove-Item-ExtIEs} } OPTIONAL
}

GNB-CU-UP-TNLA-To-Remove-Item-ExtIEs E1AP-PROTOCOL-EXTENSION ::= {
	...
}

GBR-QosInformation ::= SEQUENCE {
	e-RAB-MaximumBitrateDL			BitRate,
	e-RAB-MaximumBitrateUL			BitRate,
	e-RAB-GuaranteedBitrateDL		BitRate,
	e-RAB-GuaranteedBitrateUL		BitRate,
	iE-Extensions					ProtocolExtensionContainer { { GBR-QosInformation-ExtIEs} } OPTIONAL,
	...
}

GBR-QosInformation-ExtIEs E1AP-PROTOCOL-EXTENSION ::= {
	...
}

GBR-QoSFlowInformation::= SEQUENCE {
	maxFlowBitRateDownlink			BitRate,
	maxFlowBitRateUplink			BitRate,
	guaranteedFlowBitRateDownlink	BitRate,
	guaranteedFlowBitRateUplink		BitRate,
	maxPacketLossRateDownlink		MaxPacketLossRate		OPTIONAL,
	maxPacketLossRateUplink			MaxPacketLossRate		OPTIONAL,
	iE-Extensions					ProtocolExtensionContainer { { GBR-QosFlowInformation-ExtIEs} } OPTIONAL,
	...
}

GBR-QosFlowInformation-ExtIEs E1AP-PROTOCOL-EXTENSION ::= {
	{ID id-AlternativeQoSParaSetList	CRITICALITY ignore	EXTENSION AlternativeQoSParaSetList	PRESENCE optional}|
	{ID id-MonitoringRequestonAvailableBitrate			CRITICALITY ignore	EXTENSION MonitoringRequestonAvailableBitrate		PRESENCE optional},
	...
}

GTP-TEID				::= OCTET STRING (SIZE (4))

GTPTLAs	::= SEQUENCE (SIZE(1.. maxnoofGTPTLAs)) OF	GTPTLA-Item

GTPTLA-Item	::= SEQUENCE {
	gTPTransportLayerAddresses				TransportLayerAddress,
	iE-Extensions	ProtocolExtensionContainer { { GTPTLA-Item-ExtIEs } }         OPTIONAL,
	...
}

GTPTLA-Item-ExtIEs E1AP-PROTOCOL-EXTENSION ::= {
	...
}

GTPTunnel				::= SEQUENCE {
	transportLayerAddress				TransportLayerAddress,
	gTP-TEID							GTP-TEID,
	iE-Extensions						ProtocolExtensionContainer { { GTPTunnel-ExtIEs} } OPTIONAL,
	...
}

GTPTunnel-ExtIEs E1AP-PROTOCOL-EXTENSION ::= {
	...
}

GNB-CU-UP-OverloadInformation ::= ENUMERATED {overloaded, not-overloaded}

GNB-DU-ID	::= INTEGER (0..68719476735)


-- H

HFN		::=		INTEGER	(0..4294967295)

HW-CapacityIndicator ::= SEQUENCE {
	offeredThroughput				INTEGER (1..16777216, ...),
	availableThroughput				INTEGER (0..100, ...),
	iE-Extensions		ProtocolExtensionContainer { { HW-CapacityIndicator-ExtIEs } } OPTIONAL,
	...
}

HW-CapacityIndicator-ExtIEs	E1AP-PROTOCOL-EXTENSION ::= {
	...
}

-- I


IndirectPathIndication	::=	ENUMERATED	{
	true,
	...
}

IgnoreMappingRuleIndication	::=	ENUMERATED	{
	true,
	...
}

IntegrityProtectionIndication ::= ENUMERATED {
	required,
	preferred,
	not-needed,
	...
}

IntegrityProtectionAlgorithm	::=	ENUMERATED {
	nIA0,
	i-128-NIA1,
	i-128-NIA2,
	i-128-NIA3,
	...
}

IntegrityProtectionKey	::= OCTET STRING

IntegrityProtectionResult ::= ENUMERATED {
	performed,
	not-performed,
	...
}

Inactivity-Timer	::=	INTEGER (1..7200, ...)

InterfacesToTrace ::= BIT STRING (SIZE(8))

ImmediateMDT ::= SEQUENCE {
measurementsToActivate		MeasurementsToActivate,
	measurementFour 	M4Configuration		OPTIONAL,
-- This IE shall be present if the Measurements to Activate IE has the fourth bit set to “1”.--
	measurementSix 				M6Configuration		OPTIONAL,
-- This IE shall be present if the Measurements to Activate IE has the seventh bit set to “1”.--
	measurementSeven 			M7Configuration	    OPTIONAL,
-- This IE shall be present if the Measurements to Activate IE has the eighth bit set to “1”.--
	iE-Extensions				ProtocolExtensionContainer { { ImmediateMDT-ExtIEs} } OPTIONAL,
	...
}
ImmediateMDT-ExtIEs E1AP-PROTOCOL-EXTENSION ::= {
	...
}

IAB-Donor-CU-UPPSKInfo-Item ::= SEQUENCE {
	iAB-donor-CU-UPPSK			IAB-donor-CU-UPPSK,
	iAB-donor-CU-UPIPAddress		TransportLayerAddress,
	iAB-DUIPAddress				TransportLayerAddress,
	iE-Extensions	ProtocolExtensionContainer { { IAB-donor-CU-UPPSKInfoItemExtIEs } }	OPTIONAL,
	...
}
IAB-donor-CU-UPPSKInfoItemExtIEs 	E1AP-PROTOCOL-EXTENSION ::= {
	...
}
IAB-donor-CU-UPPSK	::= OCTET STRING

InactivityInformationRequest ::= ENUMERATED {true, ...}

InactivityMonitoring ::= ENUMERATED { disabled, ...}


-- J

-- K

-- L

Links-to-log ::= ENUMERATED {
	uplink,
	downlink,
	both-uplink-and-downlink,
	...
}


LocationDependentMBSNGUInformationAt5GC ::= SEQUENCE (SIZE(1..maxnoofMBSAreaSessionIDs)) OF LocationDependentMBSNGUInformationAt5GC-Item

LocationDependentMBSNGUInformationAt5GC-Item ::= SEQUENCE {
	mbsAreaSession-ID							MBSAreaSessionID,
	mbsNGUInformationAt5GC						MBSNGUInformationAt5GC,
	iE-Extensions							ProtocolExtensionContainer	{ { LocationDependentMBSNGUInformationAt5GC-Item-ExtIEs } }	OPTIONAL,
	...
}

LocationDependentMBSNGUInformationAt5GC-Item-ExtIEs		E1AP-PROTOCOL-EXTENSION ::= {
	...
}

LocationDependentMBSF1UInformationAtCU ::= SEQUENCE (SIZE(1..maxnoofMBSAreaSessionIDs)) OF LocationDependentMBSF1UInformationAtCU-Item

LocationDependentMBSF1UInformationAtCU-Item ::= SEQUENCE {
	mbsAreaSession-ID				MBSAreaSessionID,
	mbs-f1u-info-at-CU				UP-TNL-Information,
	iE-Extensions					ProtocolExtensionContainer	{ { LocationDependentMBSF1UInformationAtCU-Item-ExtIEs } }	OPTIONAL,
	...
}

LocationDependentMBSF1UInformationAtCU-Item-ExtIEs		E1AP-PROTOCOL-EXTENSION ::= {
	...
}

LocationDependentMBSF1UInformationAtDU ::= SEQUENCE (SIZE(1..maxnoofMBSAreaSessionIDs)) OF LocationDependentMBSF1UInformationAtDU-Item

LocationDependentMBSF1UInformationAtDU-Item ::= SEQUENCE {
	mbsAreaSession-ID				MBSAreaSessionID,
	mbs-f1u-info-at-DU				UP-TNL-Information,
	iE-Extensions					ProtocolExtensionContainer	{ { LocationDependentMBSF1UInformationAtDU-Item-ExtIEs } }	OPTIONAL,
	...
}

LocationDependentMBSF1UInformationAtDU-Item-ExtIEs		E1AP-PROTOCOL-EXTENSION ::= {
	{ ID id-F1UTunnelNotEstablished		CRITICALITY		ignore		EXTENSION		F1UTunnelNotEstablished		PRESENCE		optional	},
	...
}

LocationDependentMBSNGUInformationAtNGRAN ::= SEQUENCE (SIZE(1..maxnoofMBSAreaSessionIDs)) OF LocationDependentMBSNGUInformationAtNGRAN-Item

LocationDependentMBSNGUInformationAtNGRAN-Item ::= SEQUENCE {
	mbsAreaSession-ID							MBSAreaSessionID,
	mbsNGUInformationAtNGRAN						MBSNGUInformationAtNGRAN,
	iE-Extensions							ProtocolExtensionContainer	{ { LocationDependentMBSNGUInformationAtNGRAN-Item-ExtIEs } }	OPTIONAL,
	...
}

LocationDependentMBSNGUInformationAtNGRAN-Item-ExtIEs		E1AP-PROTOCOL-EXTENSION ::= {
	...
}

LTMInitiation	::=		ENUMERATED {true, ...}


-- M

MaxDataBurstVolume  ::= INTEGER (0..4095, ..., 4096.. 2000000)

MaximumIPdatarate ::= SEQUENCE {
	maxIPrate			MaxIPrate,
	iE-Extensions		ProtocolExtensionContainer { {MaximumIPdatarate-ExtIEs} }	OPTIONAL,
	...
}

MaximumIPdatarate-ExtIEs E1AP-PROTOCOL-EXTENSION ::= {
	...
}

MaxIPrate ::= ENUMERATED {
	bitrate64kbs,
	max-UErate,
	...
}

MaxPacketLossRate ::= INTEGER (0..1000, ...)

MaxCIDEHCDL ::= INTEGER (1..32767, ...)

MBSAreaSessionID ::= INTEGER (0..65535, ...)

MBSF1UInformationAtCU ::= SEQUENCE {
	mbs-f1u-info-at-CU				UP-TNL-Information,
	iE-Extensions					ProtocolExtensionContainer	{ { MBSF1UInformationAtCU-ExtIEs } }	OPTIONAL,
	...
}

MBSF1UInformationAtCU-ExtIEs		E1AP-PROTOCOL-EXTENSION ::= {
	...
}

MBSF1UInformationAtDU ::= SEQUENCE {
	mbs-f1u-info-at-DU				UP-TNL-Information,
	iE-Extensions					ProtocolExtensionContainer	{ { MBSF1UInformationAtDU-ExtIEs } }	OPTIONAL,
	...
}

MBSF1UInformationAtDU-ExtIEs		E1AP-PROTOCOL-EXTENSION ::= {
	{ ID id-F1UTunnelNotEstablished		CRITICALITY		ignore		EXTENSION		F1UTunnelNotEstablished		PRESENCE		optional	},
	...
}

MBSNGUInformationAt5GC ::= CHOICE {
	multicast 				MBSNGUInformationAt5GC-Multicast,
	choice-extension	ProtocolIE-SingleContainer	{{MBSNGUInformationAt5GC-ExtIEs}}
}

MBSNGUInformationAt5GC-ExtIEs E1AP-PROTOCOL-IES ::= {
	...
}

MBSNGUInformationAt5GC-Multicast ::= SEQUENCE {
	ipmcAddress		TransportLayerAddress,
	ipsourceAddress	TransportLayerAddress,
	gtpDLTEID		GTP-TEID,
	iE-Extensions		ProtocolExtensionContainer { {MBSNGUInformationAt5GC-Multicast-ExtIEs} }	OPTIONAL,
	...
}

MBSNGUInformationAt5GC-Multicast-ExtIEs E1AP-PROTOCOL-EXTENSION ::= {
	...
}

MBSNGUInformationAtNGRAN ::= CHOICE {
	unicast					UP-TNL-Information,
	choice-extension	ProtocolIE-SingleContainer	{{MBSNGUInformationAtNGRAN-ExtIEs}}
}

MBSNGUInformationAtNGRAN-ExtIEs E1AP-PROTOCOL-IES ::= {
	...
}

MBSNGUInformationAtNGRAN-Request ::=	ENUMERATED {true, ... }

MBSNGUInformationAtNGRAN-Request-List ::= SEQUENCE (SIZE(1..maxnoofMBSAreaSessionIDs)) OF MBSNGUInformationAtNGRAN-Request-Item

MBSNGUInformationAtNGRAN-Request-Item ::= SEQUENCE {
	mbsAreaSession-ID							MBSAreaSessionID,
	mbsNGUInformationAtNGRAN-Request			MBSNGUInformationAtNGRAN-Request,
	iE-Extensions							ProtocolExtensionContainer	{ { MBSNGUInformationAtNGRAN-Request-Item-ExtIEs } }	OPTIONAL,
	...
}

MBSNGUInformationAtNGRAN-Request-Item-ExtIEs		E1AP-PROTOCOL-EXTENSION ::= {
	...
}

MBSSessionAssociatedInfoNonSupportToSupport ::= SEQUENCE {
	ue-Reference-ID						GNB-CU-CP-UE-E1AP-ID,
	pDU-Session-ID						PDU-Session-ID,
	associatedQoSFlowInformationList	MBSSessionAssociatedInformationList,
	iE-Extensions		ProtocolExtensionContainer { {MBSSessionAssociatedInfoNonSupportToSupport-ExtIEs} }	OPTIONAL,
	...
}

MBSSessionAssociatedInfoNonSupportToSupport-ExtIEs E1AP-PROTOCOL-EXTENSION ::= {
	...
}

MBSSessionAssociatedInformation ::= SEQUENCE {
	mbsSessionAssociatedInformationList		MBSSessionAssociatedInformationList,
	mbsSessionForwardingAddress				UP-TNL-Information,
	iE-Extensions		ProtocolExtensionContainer { {MBSSessionAssociatedInformation-ExtIEs} }	OPTIONAL,
	...
}

MBSSessionAssociatedInformation-ExtIEs E1AP-PROTOCOL-EXTENSION ::= {
	...
}

MBSSessionAssociatedInformationList	::= SEQUENCE (SIZE(1.. maxnoofQoSFlows)) OF MBSSessionAssociatedInformation-Item

MBSSessionAssociatedInformation-Item	::=	SEQUENCE {
	mbs-QoS-Flow-Identifier					QoS-Flow-Identifier,
	associated-unicast-QoS-Flow-Identifier	QoS-Flow-Identifier,
	iE-Extensions							ProtocolExtensionContainer	{ { MBSSessionAssociatedInformation-Item-ExtIEs } }	OPTIONAL,
	...
}

MBSSessionAssociatedInformation-Item-ExtIEs		E1AP-PROTOCOL-EXTENSION ::= {
	...
}

MBS-Support-Info-ToAdd-List ::= SEQUENCE (SIZE(1..maxnoofMBSSessionIDs)) OF MBS-Support-Info-ToAdd-Item

MBS-Support-Info-ToAdd-Item ::= SEQUENCE {
	globalMBSSessionID					GlobalMBSSessionID,
	iE-Extensions		ProtocolExtensionContainer { { MBS-Support-Info-ToAdd-Item-ExtIEs} }	OPTIONAL,
	...
}

MBS-Support-Info-ToAdd-Item-ExtIEs E1AP-PROTOCOL-EXTENSION ::= {
	...
}

MBS-Support-Info-ToRemove-List ::= SEQUENCE (SIZE(1..maxnoofMBSSessionIDs)) OF MBS-Support-Info-ToRemove-Item

MBSSessionResourceNotification ::= CHOICE {
	mbs-DL-Data-Arrival				MBS-DL-Data-Arrival,
	inactivity						MCBearerContext-Inactivity,
	choice-extension				ProtocolIE-SingleContainer	{{ MBSSessionResourceNotification-ExtIEs}}
}

MBSSessionResourceNotification-ExtIEs E1AP-PROTOCOL-IES ::= {
	...
}

MBS-DL-Data-Arrival ::= SEQUENCE {
	dlDataArrival					ENUMERATED {true, ...},
	ppi								PPI							OPTIONAL,
	iE-Extensions					ProtocolExtensionContainer { { MBS-DL-Data-Arrival-ExtIEs} }	OPTIONAL,
	...
}

MBS-DL-Data-Arrival-ExtIEs E1AP-PROTOCOL-EXTENSION ::= {
	...
}


MCBearerContext-Inactivity ::= SEQUENCE {
	mcBearerContext-Inactivity-Indication						ENUMERATED {true, ...},
	iE-Extensions		ProtocolExtensionContainer { {MCBearerContext-Inactivity-ExtIEs} }	OPTIONAL,
	...
}

MCBearerContext-Inactivity-ExtIEs E1AP-PROTOCOL-EXTENSION ::= {
	...
}

MBS-Support-Info-ToRemove-Item ::= SEQUENCE {
	globalMBSSessionID					GlobalMBSSessionID,
	iE-Extensions		ProtocolExtensionContainer { { MBS-Support-Info-ToRemove-Item-ExtIEs} }	OPTIONAL,
	...
}

MBS-Support-Info-ToRemove-Item-ExtIEs E1AP-PROTOCOL-EXTENSION ::= {
	...
}

-- MCBearerContextToSetup

MCBearerContextToSetup ::= SEQUENCE {
	snssai								SNSSAI,
	mcMRBToSetupList					MCMRBSetupConfiguration					OPTIONAL,
	requestedAction						RequestedAction4AvailNGUTermination		OPTIONAL,
	iE-Extensions		ProtocolExtensionContainer { {MCBearerContextToSetup-ExtIEs} }	OPTIONAL,
	...
}

MCBearerContextToSetup-ExtIEs E1AP-PROTOCOL-EXTENSION ::= {
	{ID id-MBSSessionAssociatedInfoNonSupportToSupport	CRITICALITY ignore	EXTENSION MBSSessionAssociatedInfoNonSupportToSupport	PRESENCE optional}|
	{ID id-MBSAreaSessionID					CRITICALITY ignore	EXTENSION MBSAreaSessionID					PRESENCE optional}|
	{ID id-MCBearerContextInactivityTimer		CRITICALITY ignore	EXTENSION Inactivity-Timer					PRESENCE optional}|
	{ID id-MCBearerContextStatusChange		CRITICALITY ignore	EXTENSION MCBearerContextStatusChange		PRESENCE optional},
	...
}

MCMRBSetupConfiguration ::= SEQUENCE (SIZE(1..maxnoofMRBs)) OF MCMRBSetupConfiguration-Item

MCMRBSetupConfiguration-Item ::= SEQUENCE {
	mrb-ID							MRB-ID,
	mbs-pdcp-config					PDCP-Configuration,
	qoS-Flow-QoS-Parameter-List		QoS-Flow-QoS-Parameter-List,
	qoSFlowLevelQoSParameters		QoSFlowLevelQoSParameters		OPTIONAL,
	iE-Extensions		ProtocolExtensionContainer { {MCMRBSetupConfiguration-Item-ExtIEs} }	OPTIONAL,
	...
}

MCMRBSetupConfiguration-Item-ExtIEs E1AP-PROTOCOL-EXTENSION ::= {
	...
}

MCBearerContextStatusChange	::=	ENUMERATED {suspend, resume, ...}


-- MCBearerContextToSetupResponse

MCBearerContextToSetupResponse ::= SEQUENCE {
	mcBearerContextNGU-TNLInfoatNGRAN		MCBearerContextNGU-TNLInfoatNGRAN		OPTIONAL,
	mcMRBSetupResponseList					MCMRBSetupResponseList					OPTIONAL,
	mcMRBFailedList							MCMRBFailedList							OPTIONAL,
	availableMCMRBConfig					MCMRBSetupConfiguration					OPTIONAL,
	iE-Extensions		ProtocolExtensionContainer { {MCBearerContextToSetupResponse-ExtIEs} }	OPTIONAL,
	...
}

MCBearerContextToSetupResponse-ExtIEs E1AP-PROTOCOL-EXTENSION ::= {
	...
}

MCBearerContextNGU-TNLInfoatNGRAN::= CHOICE {
	locationindependent				MBSNGUInformationAtNGRAN,
	locationdependent				LocationDependentMBSNGUInformationAtNGRAN,
	choice-extension	ProtocolIE-SingleContainer	{{MCBearerContextNGU-TNLInfoatNGRAN-ExtIEs}}
}

MCBearerContextNGU-TNLInfoatNGRAN-ExtIEs E1AP-PROTOCOL-IES ::= {
	...
}

MCMRBSetupResponseList ::= SEQUENCE (SIZE(1..maxnoofMRBs)) OF MCMRBSetupResponseList-Item

MCMRBSetupResponseList-Item ::= SEQUENCE {
	mrb-ID								MRB-ID,
	qosflow-setup						QoS-Flow-List,
	qosflow-failed						QoS-Flow-Failed-List		OPTIONAL,
	mBS-PDCP-COUNT						MBS-PDCP-COUNT				OPTIONAL,
	iE-Extensions		ProtocolExtensionContainer { {MCMRBSetupResponseList-Item-ExtIEs} }	OPTIONAL,
	...
}

MCMRBSetupResponseList-Item-ExtIEs E1AP-PROTOCOL-EXTENSION ::= {
	...
}

MBS-PDCP-COUNT	::= BIT STRING (SIZE (32))

MCMRBFailedList ::= SEQUENCE (SIZE(1..maxnoofMRBs)) OF MCMRBFailedList-Item

MCMRBFailedList-Item ::= SEQUENCE {
	mrb-ID								MRB-ID,
	cause								Cause,
	iE-Extensions		ProtocolExtensionContainer { {MCMRBFailedList-Item-ExtIEs} }	OPTIONAL,
	...
}

MCMRBFailedList-Item-ExtIEs E1AP-PROTOCOL-EXTENSION ::= {
	...
}


-- MCBearerContextToModify

MCBearerContextToModify ::= SEQUENCE {
	mcBearerContextNGUTNLInfoat5GC					MCBearerContextNGUTNLInfoat5GC				OPTIONAL,
	mcBearerContextNGUTnlInfoatNGRANRequest			MCBearerContextNGUTnlInfoatNGRANRequest		OPTIONAL,
	mbsMulticastF1UContextDescriptor				MBSMulticastF1UContextDescriptor			OPTIONAL,
-- This IE shall be present if either the MC MRB To Setup or Modify List IE or the MC MRB To Remove List IE or both IEs are included.
	requestedAction									RequestedAction4AvailNGUTermination			OPTIONAL,
	mcMRBToSetupModifyList							MCMRBSetupModifyConfiguration				OPTIONAL,
	mcMRBToRemoveList								MCMRBRemoveConfiguration					OPTIONAL,
	iE-Extensions		ProtocolExtensionContainer { {MCBearerContextToModify-ExtIEs} }	OPTIONAL,
	...
}

MCBearerContextToModify-ExtIEs E1AP-PROTOCOL-EXTENSION ::= {
	{ID id-MCForwardingResourceRequest					CRITICALITY ignore	EXTENSION MCForwardingResourceRequest						PRESENCE optional}|
	{ID id-MCForwardingResourceIndication				CRITICALITY ignore	EXTENSION MCForwardingResourceIndication					PRESENCE optional}|
	{ID id-MCForwardingResourceRelease					CRITICALITY ignore	EXTENSION MCForwardingResourceRelease						PRESENCE optional}|
	{ID id-MBSSessionAssociatedInfoNonSupportToSupport	CRITICALITY ignore	EXTENSION MBSSessionAssociatedInfoNonSupportToSupport	PRESENCE optional}|
	{ID id-MCBearerContextInactivityTimer					CRITICALITY ignore	EXTENSION Inactivity-Timer										PRESENCE optional}|
	{ID id-MCBearerContextStatusChange					CRITICALITY ignore	EXTENSION MCBearerContextStatusChange						PRESENCE optional}|
	{ID id-MCBearerContextNGUTnlInfoatNGRANReplaceRequest	CRITICALITY reject	EXTENSION MCBearerContextNGUTnlInfoatNGRANRequest					PRESENCE optional},
	...
}

MCBearerContextNGUTNLInfoat5GC ::= SEQUENCE {
	mbsNGUInformationAt5GC			MBSNGUInformationAt5GC,
	mbsAreaSession-ID				MBSAreaSessionID		OPTIONAL,
	iE-Extensions		ProtocolExtensionContainer { {MCBearerContextNGUTNLInfoat5GC-ExtIEs} }	OPTIONAL,
	...
}

MCBearerContextNGUTNLInfoat5GC-ExtIEs E1AP-PROTOCOL-EXTENSION ::= {
	...
}


MCBearerContextNGUTnlInfoatNGRANRequest ::= SEQUENCE {
	ngRANNGUTNLRequested				ENUMERATED {requested, ...},
	mbsAreaSession-ID				MBSAreaSessionID		OPTIONAL,
	iE-Extensions		ProtocolExtensionContainer { {MCBearerContextNGUTnlInfoatNGRANRequest-ExtIEs} }	OPTIONAL,
	...
}

MCBearerContextNGUTnlInfoatNGRANRequest-ExtIEs E1AP-PROTOCOL-EXTENSION ::= {
	...
}


MCMRBSetupModifyConfiguration ::= SEQUENCE (SIZE(1..maxnoofMRBs)) OF MCMRBSetupModifyConfiguration-Item

MCMRBSetupModifyConfiguration-Item ::= SEQUENCE {
	mrb-ID							MRB-ID,
	f1uTNLatDU						MCBearerContextF1UTNLInfoatDU		OPTIONAL,
	mbs-pdcp-config					PDCP-Configuration				OPTIONAL,
	qoS-Flow-QoS-Parameter-List		QoS-Flow-QoS-Parameter-List		OPTIONAL,
	mrbQoS							QoSFlowLevelQoSParameters		OPTIONAL,
	mbs-PDCP-COUNT-Req				MBS-PDCP-COUNT-Req				OPTIONAL,
	iE-Extensions		ProtocolExtensionContainer { {MCMRBSetupModifyConfiguration-Item-ExtIEs} }	OPTIONAL,
	...
}

MCMRBSetupModifyConfiguration-Item-ExtIEs E1AP-PROTOCOL-EXTENSION ::= {
	...
}

MCBearerContextF1UTNLInfoatDU ::= SEQUENCE {
	mbsF1UInfoatDU						UP-TNL-Information,
	mbsMulticastF1UContextDescriptor	MBSMulticastF1UContextDescriptor,
	iE-Extensions		ProtocolExtensionContainer { {MCBearerContextF1UTNLInfoatDU-ExtIEs} }	OPTIONAL,
	...
}

MCBearerContextF1UTNLInfoatDU-ExtIEs E1AP-PROTOCOL-EXTENSION ::= {
	...
}

MulticastF1UContextReferenceE1 ::= OCTET STRING (SIZE(4))

MBSMulticastF1UContextDescriptor ::= SEQUENCE {
	multicastF1UContextReferenceE1	MulticastF1UContextReferenceE1,
	mc-F1UCtxtusage 	ENUMERATED {ptm, ptp, ptp-retransmission, ptp-forwarding, ...},
	mbsAreaSession					MBSAreaSessionID					OPTIONAL,
	iE-Extensions		ProtocolExtensionContainer { { MBSMulticastF1UContextDescriptor-ExtIEs } }	OPTIONAL,
	...
}

MBSMulticastF1UContextDescriptor-ExtIEs E1AP-PROTOCOL-EXTENSION ::= {
	...
}



MCMRBRemoveConfiguration ::= SEQUENCE (SIZE(1..maxnoofMRBs)) OF MRB-ID

MBS-PDCP-COUNT-Req ::=	ENUMERATED {true, ... }


-- MCBearerContextToModifyResponse

MCBearerContextToModifyResponse ::= SEQUENCE {
	mcBearerContextNGU-TNLInfoatNGRANModifyResponse	MCBearerContextNGU-TNLInfoatNGRANModifyResponse		OPTIONAL,
	mbsMulticastF1UContextDescriptor					MBSMulticastF1UContextDescriptor				OPTIONAL,
-- This IE shall be present if either the MC MRB Setup or Modify Response List IE or the MC MRB Failed List IE or both IEs are included.
	mcMRBModifySetupResponseList						MCMRBSetupModifyResponseList							OPTIONAL,
	mcMRBFailedList									MCMRBFailedList										OPTIONAL,
	availableMCMRBConfig								MCMRBSetupConfiguration								OPTIONAL,
	iE-Extensions		ProtocolExtensionContainer { {MCBearerContextToModifyResponse-ExtIEs} }	OPTIONAL,
	...
}

MCBearerContextToModifyResponse-ExtIEs E1AP-PROTOCOL-EXTENSION ::= {
	{ID id-MCForwardingResourceResponse	CRITICALITY ignore	EXTENSION MCForwardingResourceResponse		PRESENCE optional},
	...
}

MCBearerContextNGU-TNLInfoatNGRANModifyResponse ::= SEQUENCE {
	mbs-NGU-InfoatNGRAN	MBSNGUInformationAtNGRAN,
	mbsAreaSession		MBSAreaSessionID					OPTIONAL,
	iE-Extensions		ProtocolExtensionContainer { {MCBearerContextNGU-TNLInfoatNGRANModifyResponse-ExtIEs} }	OPTIONAL,
	...
}

MCBearerContextNGU-TNLInfoatNGRANModifyResponse-ExtIEs E1AP-PROTOCOL-EXTENSION ::= {
	...
}

MCMRBSetupModifyResponseList ::= SEQUENCE (SIZE(1..maxnoofMRBs)) OF MCMRBSetupModifyResponseList-Item

MCMRBSetupModifyResponseList-Item ::= SEQUENCE {
	mrb-ID								MRB-ID,
	qosflow-setup						QoS-Flow-List			OPTIONAL,
	qosflow-failed						QoS-Flow-Failed-List		OPTIONAL,
	mcBearerContextF1UTNLInfoatCU		UP-TNL-Information		OPTIONAL,
	mBS-PDCP-COUNT						MBS-PDCP-COUNT			OPTIONAL,
	iE-Extensions		ProtocolExtensionContainer { {MCMRBSetupModifyResponseList-Item-ExtIEs} }	OPTIONAL,
	...
}

MCMRBSetupModifyResponseList-Item-ExtIEs E1AP-PROTOCOL-EXTENSION ::= {
	...
}

-- MCBearerContextToModifyRequired

MCBearerContextToModifyRequired ::= SEQUENCE {
	mbsMulticastF1UContextDescriptor					MBSMulticastF1UContextDescriptor				OPTIONAL,
-- This IE shall be present if either the MC MRB To Remove List Required IE is included.
	mcMRBToRemoveRequiredList						MCMRBRemoveConfiguration						OPTIONAL,
	mcMRBToModifyRequiredList						MCMRBModifyRequiredConfiguration				OPTIONAL,
	iE-Extensions		ProtocolExtensionContainer { {MCBearerContextToModifyRequired-ExtIEs} }	OPTIONAL,
	...
}

MCBearerContextToModifyRequired-ExtIEs E1AP-PROTOCOL-EXTENSION ::= {
	{ID id-MCForwardingResourceReleaseIndication	CRITICALITY ignore	EXTENSION MCForwardingResourceReleaseIndication		PRESENCE optional},
	...
}

MCMRBModifyRequiredConfiguration ::= SEQUENCE (SIZE(1..maxnoofMRBs)) OF MCMRBModifyRequiredConfiguration-Item

MCMRBModifyRequiredConfiguration-Item ::= SEQUENCE {
	mrb-ID							MRB-ID,
	mBS-PDCP-COUNT					MBS-PDCP-COUNT															OPTIONAL,
	iE-Extensions		ProtocolExtensionContainer { { MCMRBModifyRequiredConfiguration-Item-ExtIEs} }	OPTIONAL,
	...
}

MCMRBModifyRequiredConfiguration-Item-ExtIEs E1AP-PROTOCOL-EXTENSION ::= {
	...
}

-- MCBearerContextToModifyConfirm

MCBearerContextToModifyConfirm ::= SEQUENCE {
	mbsMulticastF1UContextDescriptor					MBSMulticastF1UContextDescriptor				OPTIONAL,
	mcMRBModifyConfirmList								MCMRBModifyConfirmList					OPTIONAL,
	iE-Extensions		ProtocolExtensionContainer { {MCBearerContextToModifyConfirm-ExtIEs} }	OPTIONAL,
	...
}

MCMRBModifyConfirmList ::= SEQUENCE (SIZE(1..maxnoofMRBs)) OF MCMRBModifyConfirmList-Item

MCMRBModifyConfirmList-Item ::= SEQUENCE {
	mrb-ID								MRB-ID,
	iE-Extensions		ProtocolExtensionContainer { { MCMRBModifyConfirmList-Item-ExtIEs} }	OPTIONAL,
	...
}

MCMRBModifyConfirmList-Item-ExtIEs E1AP-PROTOCOL-EXTENSION ::= {
	...
}

MCBearerContextToModifyConfirm-ExtIEs E1AP-PROTOCOL-EXTENSION ::= {
	...
}

-- MCForwardingResourceRequest

MCForwardingResourceRequest ::= SEQUENCE {
	mcForwardingResourceID				MCForwardingResourceID,
	mbsAreaSession-ID					MBSAreaSessionID					OPTIONAL,
	mrbForwardingResourceRequestList	MRBForwardingResourceRequestList	OPTIONAL,
	iE-Extensions		ProtocolExtensionContainer { {MCForwardingResourceRequest-ExtIEs} }	OPTIONAL,
	...
}

MCForwardingResourceRequest-ExtIEs E1AP-PROTOCOL-EXTENSION ::= {
	...
}

MRBForwardingResourceRequestList ::= SEQUENCE (SIZE(1.. maxnoofQoSFlows)) OF MRBForwardingResourceRequest-Item

MRBForwardingResourceRequest-Item	::=	SEQUENCE {
	mrb-ID								MRB-ID,
	mrbProgressRequestType				MRB-ProgressInformationType	OPTIONAL,
	mrbForwardingAddressRequest			ENUMERATED {request, ...}	OPTIONAL,
	iE-Extensions							ProtocolExtensionContainer	{ {MRBForwardingResourceRequest-Item-ExtIEs} }	OPTIONAL,
	...
}

MRBForwardingResourceRequest-Item-ExtIEs		E1AP-PROTOCOL-EXTENSION ::= {
	...
}


-- MCForwardingResourceIndication

MCForwardingResourceIndication ::= SEQUENCE {
	mcForwardingResourceID				MCForwardingResourceID,
	mrbForwardingResourceIndicationList	MRBForwardingResourceIndicationList		OPTIONAL,
	mbsSessionAssociatedInformation		MBSSessionAssociatedInformation			OPTIONAL,
	iE-Extensions		ProtocolExtensionContainer { {MCForwardingResourceIndication-ExtIEs} }	OPTIONAL,
	...
}

MCForwardingResourceIndication-ExtIEs E1AP-PROTOCOL-EXTENSION ::= {
	...
}

MRBForwardingResourceIndicationList ::= SEQUENCE (SIZE(1.. maxnoofQoSFlows)) OF MRBForwardingResourceIndication-Item

MRBForwardingResourceIndication-Item	::=	SEQUENCE {
	mrb-ID								MRB-ID,
	mrb-ProgressInformation				MRB-ProgressInformation		OPTIONAL,
	mrbForwardingAddress				UP-TNL-Information			OPTIONAL,
	iE-Extensions						ProtocolExtensionContainer	{ {MRBForwardingResourceIndication-Item-ExtIEs} }	OPTIONAL,
	...
}

MRBForwardingResourceIndication-Item-ExtIEs		E1AP-PROTOCOL-EXTENSION ::= {
	...
}


-- MCForwardingResourceResponse

MCForwardingResourceResponse ::= SEQUENCE {
	mcForwardingResourceID			MCForwardingResourceID,
	mrbForwardingResourceResponseList	MRBForwardingResourceResponseList		OPTIONAL,
	iE-Extensions		ProtocolExtensionContainer { {MCForwardingResourceResponse-ExtIEs} }	OPTIONAL,
	...
}

MCForwardingResourceResponse-ExtIEs E1AP-PROTOCOL-EXTENSION ::= {
	...
}

MRBForwardingResourceResponseList ::= SEQUENCE (SIZE(1.. maxnoofQoSFlows)) OF MRBForwardingResourceResponse-Item

MRBForwardingResourceResponse-Item	::=	SEQUENCE {
	mrb-ID								MRB-ID,
	mrb-ProgressInformation				MRB-ProgressInformation		OPTIONAL,
	mrbForwardingAddress				UP-TNL-Information			OPTIONAL,
	iE-Extensions						ProtocolExtensionContainer	{ {MRBForwardingResourceResponse-Item-ExtIEs} }	OPTIONAL,
	...
}

MRBForwardingResourceResponse-Item-ExtIEs		E1AP-PROTOCOL-EXTENSION ::= {
	...
}

-- MCForwardingResourceRelease

MCForwardingResourceRelease ::= SEQUENCE {
	mcForwardingResourceID			MCForwardingResourceID,
	iE-Extensions		ProtocolExtensionContainer { {MCForwardingResourceRelease-ExtIEs} }	OPTIONAL,
	...
}

MCForwardingResourceRelease-ExtIEs E1AP-PROTOCOL-EXTENSION ::= {
	...
}

-- MCForwardingResourceReleaseIndication

MCForwardingResourceReleaseIndication ::= SEQUENCE {
	mcForwardingResourceID			MCForwardingResourceID,
	iE-Extensions		ProtocolExtensionContainer { {MCForwardingResourceReleaseIndication-ExtIEs} }	OPTIONAL,
	...
}

MCForwardingResourceReleaseIndication-ExtIEs E1AP-PROTOCOL-EXTENSION ::= {
	...
}

MCForwardingResourceID ::= OCTET STRING (SIZE(2))


MDTPollutedMeasurementIndicator ::= ENUMERATED {
	iDC,
	no-IDC,
	...
}

MRB-ID	::=	INTEGER (1..512, ...)

MRB-ProgressInformation ::= SEQUENCE {
	mrb-ProgressInformationSNs	MRB-ProgressInformationSNs,
	mrb-ProgressInformationType	MRB-ProgressInformationType,
	iE-Extensions				ProtocolExtensionContainer { {MRB-ProgressInformation-ExtIEs} } OPTIONAL,
...
}

MRB-ProgressInformation-ExtIEs E1AP-PROTOCOL-EXTENSION ::= {
	...
}

MRB-ProgressInformationSNs ::= CHOICE {
	pdcp-SN12			INTEGER (0..4095),
	pdcp-SN18			INTEGER (0..262143),
	choice-extension		ProtocolIE-SingleContainer { { MRB-ProgressInformationSNs-ExtIEs} }
}

MRB-ProgressInformationSNs-ExtIEs E1AP-PROTOCOL-IES ::= {
	...
}

MRB-ProgressInformationType ::= ENUMERATED {oldest-available, last-delivered, ...}

MRDC-Data-Usage-Report-Item ::= SEQUENCE {
	startTimeStamp				OCTET STRING (SIZE(4)),
	endTimeStamp				OCTET STRING (SIZE(4)),
	usageCountUL				INTEGER (0..18446744073709551615),
	usageCountDL				INTEGER (0..18446744073709551615),
	iE-Extensions				ProtocolExtensionContainer { { MRDC-Data-Usage-Report-Item-ExtIEs} } OPTIONAL,
...
}

MRDC-Data-Usage-Report-Item-ExtIEs E1AP-PROTOCOL-EXTENSION ::= {
	...
}

MRDC-Usage-Information ::= SEQUENCE {
	data-Usage-per-PDU-Session-Report		Data-Usage-per-PDU-Session-Report			OPTIONAL,
	data-Usage-per-QoS-Flow-List			Data-Usage-per-QoS-Flow-List				OPTIONAL,
	iE-Extensions				ProtocolExtensionContainer { { MRDC-Usage-Information-ExtIEs} } OPTIONAL,
...
}

MRDC-Usage-Information-ExtIEs E1AP-PROTOCOL-EXTENSION ::= {
	...
}

M4Configuration ::= SEQUENCE {
	m4period			M4period,
	m4-links-to-log		Links-to-log,
	iE-Extensions		ProtocolExtensionContainer { { M4Configuration-ExtIEs} } OPTIONAL,
	...
}

M4Configuration-ExtIEs E1AP-PROTOCOL-EXTENSION ::= {
	{ ID id-M4ReportAmount		CRITICALITY ignore	EXTENSION M4ReportAmount		PRESENCE optional		},
	...
}

M4period ::= ENUMERATED {ms1024, ms2048, ms5120, ms10240, min1, ... }

M4ReportAmount	::= ENUMERATED { r1, r2, r4, r8, r16, r32, r64, infinity, ... }

M6Configuration ::= SEQUENCE {
	m6report-Interval	M6report-Interval,
	m6-links-to-log		Links-to-log,
	iE-Extensions		ProtocolExtensionContainer { { M6Configuration-ExtIEs} } OPTIONAL,
	...
}

M6Configuration-ExtIEs E1AP-PROTOCOL-EXTENSION ::= {
	{ ID id-M6ReportAmount		CRITICALITY ignore	EXTENSION M6ReportAmount		PRESENCE optional		},
	...
}

M6ReportAmount	::= ENUMERATED { r1, r2, r4, r8, r16, r32, r64, infinity, ... }

M6report-Interval ::= ENUMERATED { ms120, ms240, ms480, ms640, ms1024, ms2048, ms5120, ms10240, ms20480 ,ms40960, min1, min6, min12, min30, ... }

M7Configuration ::= SEQUENCE {
	m7period			M7period,
	m7-links-to-log		Links-to-log,
	iE-Extensions		ProtocolExtensionContainer { { M7Configuration-ExtIEs} } OPTIONAL,
	...
}

M7Configuration-ExtIEs E1AP-PROTOCOL-EXTENSION ::= {
	{ ID id-M7ReportAmount		CRITICALITY ignore	EXTENSION M7ReportAmount		PRESENCE optional		},
	...
}

M7period ::= INTEGER(1..60, ...)

M7ReportAmount	::= ENUMERATED { r1, r2, r4, r8, r16, r32, r64, infinity, ... }

MDT-Activation 	::= ENUMERATED {
	immediate-MDT-only,
	immediate-MDT-and-Trace,
		...
}

MDT-Configuration ::= SEQUENCE {
	mdt-Activation				MDT-Activation,
	mDTMode			MDTMode,
	iE-Extensions				ProtocolExtensionContainer { { MDT-Configuration-ExtIEs} } OPTIONAL,
	...
}
MDT-Configuration-ExtIEs E1AP-PROTOCOL-EXTENSION ::= {
	...
}

MDTMode ::= CHOICE {
	immediateMDT 				ImmediateMDT,
	choice-extension	ProtocolIE-SingleContainer	{{MDTMode-ExtIEs}}
}

MDTMode-ExtIEs E1AP-PROTOCOL-IES ::= {
	...
}

MeasurementsToActivate ::= BIT STRING (SIZE (8))

MDTPLMNList ::= SEQUENCE (SIZE(1..maxnoofMDTPLMNs)) OF PLMN-Identity

MDTPLMNModificationList ::= SEQUENCE (SIZE(0..maxnoofMDTPLMNs)) OF PLMN-Identity

MT-SDT-Information ::= SEQUENCE {
	mT-SDT-Data-Size			MT-SDT-Data-Size,
	iE-Extensions				ProtocolExtensionContainer { {MT-SDT-Information-ExtIEs} } OPTIONAL
}

MT-SDT-Information-ExtIEs E1AP-PROTOCOL-EXTENSION ::= {
	...
}

MT-SDT-Information-Request ::=	ENUMERATED {true, ...}

MT-SDT-Data-Size::= INTEGER (1..96000, ...)




MBS-ServiceArea ::= SEQUENCE {
	mBS-ServiceAreaInformationList		MBS-ServiceAreaInformationList				OPTIONAL,
	iE-Extensions					ProtocolExtensionContainer { {MBS-ServiceArea-ExtIEs} }	OPTIONAL,
	...
}

MBS-ServiceArea-ExtIEs E1AP-PROTOCOL-EXTENSION ::= {
	...
}


MBS-ServiceAreaInformation ::= SEQUENCE {
	mBS-ServiceAreaCellList		MBS-ServiceAreaCellList																OPTIONAL,
	mBS-ServiceAreaTAIList		MBS-ServiceAreaTAIList																OPTIONAL,
	iE-Extensions					ProtocolExtensionContainer { {MBS-ServiceAreaInformation-ExtIEs} }	OPTIONAL,
	...
}

MBS-ServiceAreaInformation-ExtIEs E1AP-PROTOCOL-EXTENSION ::= {
	...
}

MBS-ServiceAreaCellList ::= SEQUENCE (SIZE(1.. maxnoofCellsforMBS)) OF NR-CGI

MBS-ServiceAreaTAIList ::= SEQUENCE (SIZE(1.. maxnoofTAIforMBS)) OF MBS-ServiceAreaTAIList-Item
MBS-ServiceAreaTAIList-Item ::= SEQUENCE {
	plmn-ID							PLMN-Identity,
	fiveGS-TAC						FiveGS-TAC,
	iE-Extensions					ProtocolExtensionContainer { {MBS-ServiceAreaTAIList-Item-ExtIEs} }	OPTIONAL,
	...
}

MBS-ServiceAreaTAIList-Item-ExtIEs E1AP-PROTOCOL-EXTENSION ::= {
	...
}


MBS-ServiceAreaInformationList ::= SEQUENCE (SIZE(1..maxnoofMBSServiceAreaInformation)) OF MBS-ServiceAreaInformationItem

MBS-ServiceAreaInformationItem ::= SEQUENCE {
	mBS-AreaSessionID					MBSAreaSessionID,
	mBS-ServiceAreaInformation 			MBS-ServiceAreaInformation,
	iE-Extensions						ProtocolExtensionContainer { { MBS-ServiceAreaInformationItem-ExtIEs} }	OPTIONAL,
	...
}
MBS-ServiceAreaInformationItem-ExtIEs E1AP-PROTOCOL-EXTENSION ::= {
	...
}

Measurement-ID	::= INTEGER (1..4095,...)

MonitoringRequestonAvailableBitrate	::= SEQUENCE{
	monitoringRequest						MonitoringRequest,
	dlAvailableBitrateReportThresholds		AvailableBitrateReportThresholdList		OPTIONAL,
-- The above IE shall be present if the Monitoring Request IE is set to the value “dl” or “both”
	ulAvailableBitrateReportThresholds		AvailableBitrateReportThresholdList		OPTIONAL,
-- The above IE shall be present if the Monitoring Request IE is set to the value “ul” or “both”
	iE-Extensions							ProtocolExtensionContainer { { MonitoringRequestonAvailableBitrate-ExtIEs} }	OPTIONAL,
	...
}

MonitoringRequestonAvailableBitrate-ExtIEs E1AP-PROTOCOL-EXTENSION ::= {
	...
}

MonitoringRequest ::= ENUMERATED {ul, dl, both, stop,...}

MMSID ::= OCTET STRING (SIZE (1))

-- N

NetworkInstance ::= INTEGER (1..256, ...)

New-UL-TNL-Information-Required::= 	ENUMERATED {
	required,
	...
}
NGRANAllocationAndRetentionPriority ::= SEQUENCE {
	priorityLevel				PriorityLevel,
	pre-emptionCapability		Pre-emptionCapability,
	pre-emptionVulnerability	Pre-emptionVulnerability,
	iE-Extensions				ProtocolExtensionContainer { {NGRANAllocationAndRetentionPriority-ExtIEs} } OPTIONAL
}

NGRANAllocationAndRetentionPriority-ExtIEs E1AP-PROTOCOL-EXTENSION ::= {
	...
}

NG-RAN-QoS-Support-List ::= SEQUENCE (SIZE(1.. maxnoofNGRANQOSParameters)) OF NG-RAN-QoS-Support-Item

NG-RAN-QoS-Support-Item ::= SEQUENCE {
	non-Dynamic5QIDescriptor	Non-Dynamic5QIDescriptor,
	iE-Extensions				ProtocolExtensionContainer { { NG-RAN-QoS-Support-Item-ExtIEs } }	OPTIONAL
}

NG-RAN-QoS-Support-Item-ExtIEs	E1AP-PROTOCOL-EXTENSION ::= {
	...
}

NID	::= BIT STRING (SIZE (44))

Non-Dynamic5QIDescriptor	::= SEQUENCE {
	fiveQI						INTEGER (0..255, ...),
	qoSPriorityLevel			QoSPriorityLevel				OPTIONAL,
	averagingWindow 			AveragingWindow					OPTIONAL,
	maxDataBurstVolume			MaxDataBurstVolume				OPTIONAL,
	iE-Extensions	ProtocolExtensionContainer { { Non-Dynamic5QIDescriptor-ExtIEs } } OPTIONAL
}

Non-Dynamic5QIDescriptor-ExtIEs E1AP-PROTOCOL-EXTENSION ::= {
	{ ID id-CNPacketDelayBudgetDownlink			CRITICALITY ignore	EXTENSION 	ExtendedPacketDelayBudget		PRESENCE optional	}|
	{ ID id-CNPacketDelayBudgetUplink			CRITICALITY ignore	EXTENSION 	ExtendedPacketDelayBudget		PRESENCE optional	},
	...
}

NPNSupportInfo ::= CHOICE {
	sNPN				NPNSupportInfo-SNPN,
	choice-extension	ProtocolIE-SingleContainer	{{NPNSupportInfo-ExtIEs}}
}

NPNSupportInfo-ExtIEs E1AP-PROTOCOL-IES ::= {
	...
}

NPNSupportInfo-SNPN ::= SEQUENCE {
	nID						NID,
	iE-Extensions			ProtocolExtensionContainer { { NPNSupportInfo-SNPN-ExtIEs } }	OPTIONAL
}


NPNSupportInfo-SNPN-ExtIEs	E1AP-PROTOCOL-EXTENSION ::= {
	...
}

NPNContextInfo ::= CHOICE {
	sNPN				NPNContextInfo-SNPN,
	choice-extension	ProtocolIE-SingleContainer	{{NPNContextInfo-ExtIEs}}
}

NPNContextInfo-ExtIEs E1AP-PROTOCOL-IES ::= {
	...
}

NPNContextInfo-SNPN ::= SEQUENCE {
	nID						NID,
	iE-Extensions			ProtocolExtensionContainer { {NPNContextInfo-SNPN-ExtIEs } }	OPTIONAL
}

NPNContextInfo-SNPN-ExtIEs	E1AP-PROTOCOL-EXTENSION ::= {
	...
}

NR-Cell-Identity	::=		BIT STRING (SIZE(36))

NR-CGI ::= SEQUENCE {
	pLMN-Identity			PLMN-Identity,
	nR-Cell-Identity		NR-Cell-Identity,
	iE-Extensions			ProtocolExtensionContainer { { NR-CGI-ExtIEs } }	OPTIONAL
}

NR-CGI-ExtIEs	E1AP-PROTOCOL-EXTENSION ::= {
	...
}

NR-CGI-Support-List ::= SEQUENCE (SIZE(1.. maxnoofNRCGI)) OF NR-CGI-Support-Item

NR-CGI-Support-Item ::= SEQUENCE {
	nR-CGI	NR-CGI,
	iE-Extensions				ProtocolExtensionContainer { { NR-CGI-Support-Item-ExtIEs } }	OPTIONAL
}

NR-CGI-Support-Item-ExtIEs	E1AP-PROTOCOL-EXTENSION ::= {
	...
}

Extended-NR-CGI-Support-List ::= SEQUENCE (SIZE(1.. maxnoofExtNRCGI)) OF Extended-NR-CGI-Support-Item

Extended-NR-CGI-Support-Item ::= SEQUENCE {
	nR-CGI	NR-CGI,
	iE-Extensions				ProtocolExtensionContainer { { Extended-NR-CGI-Support-Item-ExtIEs } }	OPTIONAL
}

Extended-NR-CGI-Support-Item-ExtIEs	E1AP-PROTOCOL-EXTENSION ::= {
	...
}

N6JitterInformation ::= SEQUENCE {
	n6JitterLowerBound		INTEGER (-127..127),
	n6JitterUpperBound		INTEGER (-127..127),
	iE-Extensions	ProtocolExtensionContainer { { N6JitterInformationExtIEs } }	OPTIONAL,
	...
}

N6JitterInformationExtIEs 	E1AP-PROTOCOL-EXTENSION ::= {
	...
}

NodeMeasurementInitiationResult-List ::= SEQUENCE (SIZE(1..maxFailedMeasPerNode)) OF NodeMeasurementInitiationResult-Item

NodeMeasurementInitiationResult-Item ::= SEQUENCE {
	nodemeasurementFailedReportCharacteristics		BIT STRING(SIZE(32)),
	cause											Cause,
	iE-Extensions									ProtocolExtensionContainer { { NodeMeasurementInitiationResult-Item-ExtIEs} } OPTIONAL,
	...
}

NodeMeasurementInitiationResult-Item-ExtIEs E1AP-PROTOCOL-EXTENSION ::= {
	...
}


-- O

OutOfOrderDelivery	::=	ENUMERATED	{
	true,
	...
}


-- P

PacketDelayBudget ::= INTEGER (0..1023, ...)

PacketErrorRate ::= SEQUENCE {
	pER-Scalar			PER-Scalar,
	pER-Exponent		PER-Exponent,
	iE-Extensions		ProtocolExtensionContainer { {PacketErrorRate-ExtIEs} }	OPTIONAL,
	...
}

PacketErrorRate-ExtIEs E1AP-PROTOCOL-EXTENSION ::= {
	...
}

PER-Scalar ::= INTEGER (0..9, ...)
PER-Exponent ::= INTEGER (0..9, ...)

PDCP-Configuration	::=	SEQUENCE {

	pDCP-SN-Size-UL							PDCP-SN-Size,
	pDCP-SN-Size-DL							PDCP-SN-Size,
	rLC-Mode								RLC-Mode,
	rOHC-Parameters							ROHC-Parameters			OPTIONAL,
	t-ReorderingTimer						T-ReorderingTimer		OPTIONAL,
	discardTimer							DiscardTimer			OPTIONAL,
	uLDataSplitThreshold					ULDataSplitThreshold	OPTIONAL,
	pDCP-Duplication						PDCP-Duplication		OPTIONAL,
	pDCP-Reestablishment					PDCP-Reestablishment	OPTIONAL,
	pDCP-DataRecovery						PDCP-DataRecovery		OPTIONAL,
	duplication-Activation				Duplication-Activation		OPTIONAL,
	outOfOrderDelivery						OutOfOrderDelivery		OPTIONAL,
	iE-Extensions							ProtocolExtensionContainer	{ { PDCP-Configuration-ExtIEs } }	OPTIONAL,
	...
}

PDCP-Configuration-ExtIEs		E1AP-PROTOCOL-EXTENSION ::= {
	{ID id-PDCP-StatusReportIndication					CRITICALITY ignore	EXTENSION PDCP-StatusReportIndication					PRESENCE	optional}|
	{ ID id-AdditionalPDCPduplicationInformation		CRITICALITY ignore	EXTENSION AdditionalPDCPduplicationInformation	PRESENCE optional	}|
	{ ID id-EHC-Parameters								CRITICALITY ignore	EXTENSION EHC-Parameters									PRESENCE optional}|
	{ ID id-UDC-Parameters								CRITICALITY ignore	EXTENSION UDC-Parameters									PRESENCE optional}|
	{ ID id-DiscardTimerExtended								CRITICALITY reject	EXTENSION DiscardTimerExtended									PRESENCE optional}|
	{ ID id-PSIbasedDiscardTimer						CRITICALITY ignore	EXTENSION PSIbasedDiscardTimer								PRESENCE optional}|
	{ ID id-PDCPSNGapReport						CRITICALITY ignore	EXTENSION PDCPSNGapReport														PRESENCE optional}|
	{ ID id-Remaining-time-based-rLC-retransmission-threshold	CRITICALITY ignore	EXTENSION Remaining-time-based-rLC-threshold		PRESENCE optional}|
	{ ID id-Remaining-time-based-rLC-polling-threshold	CRITICALITY ignore	EXTENSION Remaining-time-based-rLC-threshold		PRESENCE optional},
	...
}

PDCPSNGapReport	::=	ENUMERATED {true, ...}

PDCP-COUNT-Reset	::=	ENUMERATED	{
	true,
	...
}

PDCP-Count	::=	SEQUENCE {
	pDCP-SN				PDCP-SN,
	hFN					HFN,
	iE-Extensions							ProtocolExtensionContainer	{ { PDCP-Count-ExtIEs } }	OPTIONAL,
	...
}

PDCP-Count-ExtIEs		E1AP-PROTOCOL-EXTENSION ::= {
	...
}

PDCP-SN-Status-Request	::=		ENUMERATED {
	requested,
	...
}

PDCP-DataRecovery	::=	ENUMERATED	{
	true,
	...
}

PDCP-Duplication	::=	ENUMERATED	{
	true,
	...
}

PDCP-Reestablishment	::=	ENUMERATED	{
	true,
	...
}

PDU-Session-Resource-Data-Usage-List	::= SEQUENCE (SIZE(1.. maxnoofPDUSessionResource)) OF PDU-Session-Resource-Data-Usage-Item

PDU-Session-Resource-Data-Usage-Item	::= SEQUENCE {
	pDU-Session-ID							PDU-Session-ID,
	mRDC-Usage-Information						MRDC-Usage-Information,
	iE-Extensions							ProtocolExtensionContainer	{ { PDU-Session-Resource-Data-Usage-Item-ExtIEs } }	OPTIONAL,
	...
}

PDU-Session-Resource-Data-Usage-Item-ExtIEs		E1AP-PROTOCOL-EXTENSION ::= {
	...
}

PDCP-SN		::=		INTEGER	(0..262143)

PDCP-SN-Size	::=	ENUMERATED	{
	s-12,
	s-18,
	...,
	s-7,
	s-15,
	s-16
}

PDCP-SN-Status-Information ::= SEQUENCE {
	pdcpStatusTransfer-UL	DRBBStatusTransfer,
	pdcpStatusTransfer-DL	PDCP-Count,
	iE-Extension		ProtocolExtensionContainer { { PDCP-SN-Status-Information-ExtIEs} }	OPTIONAL,
	...
}

PDCP-StatusReportIndication	::=	ENUMERATED	{
	downlink,
	uplink,
	both,
	...
}

PDCP-SN-Status-Information-ExtIEs E1AP-PROTOCOL-EXTENSION ::= {
	...
}

DRBBStatusTransfer ::= SEQUENCE {
	receiveStatusofPDCPSDU	BIT STRING (SIZE(1..131072))										OPTIONAL,
	countValue				PDCP-Count,
	iE-Extension			ProtocolExtensionContainer { {DRBBStatusTransfer-ExtIEs} }	OPTIONAL,
	...
}

DRBBStatusTransfer-ExtIEs E1AP-PROTOCOL-EXTENSION ::= {
	...
}

PDU-Session-ID	::=	INTEGER (0..255)

PDUSession-PairID ::= INTEGER (0..255, ...)

PDU-Session-Resource-Activity	::= ENUMERATED {
	active,
	not-active,
	...
}

PDU-Session-Resource-Activity-List ::= SEQUENCE (SIZE(1.. maxnoofPDUSessionResource)) OF PDU-Session-Resource-Activity-Item

PDU-Session-Resource-Activity-Item	::= SEQUENCE {
	pDU-Session-ID									PDU-Session-ID,
	pDU-Session-Resource-Activity					PDU-Session-Resource-Activity,
	iE-Extensions	ProtocolExtensionContainer 		{ { PDU-Session-Resource-Activity-ItemExtIEs } }	OPTIONAL,
	...
}

PDU-Session-Resource-Activity-ItemExtIEs 	E1AP-PROTOCOL-EXTENSION ::= {
	...
}


PDU-Session-Resource-Confirm-Modified-List	::= SEQUENCE (SIZE(1.. maxnoofPDUSessionResource)) OF PDU-Session-Resource-Confirm-Modified-Item

PDU-Session-Resource-Confirm-Modified-Item	::=	SEQUENCE {
	pDU-Session-ID							PDU-Session-ID,
	dRB-Confirm-Modified-List-NG-RAN		DRB-Confirm-Modified-List-NG-RAN	OPTIONAL,
	iE-Extensions							ProtocolExtensionContainer	{ { PDU-Session-Resource-Confirm-Modified-Item-ExtIEs } }	OPTIONAL,
	...
}

PDU-Session-Resource-Confirm-Modified-Item-ExtIEs		E1AP-PROTOCOL-EXTENSION ::= {
	...
}

PDU-Session-Resource-Failed-List	::= SEQUENCE (SIZE(1.. maxnoofPDUSessionResource)) OF PDU-Session-Resource-Failed-Item

PDU-Session-Resource-Failed-Item	::=	SEQUENCE {
	pDU-Session-ID							PDU-Session-ID,
	cause									Cause,
	iE-Extensions							ProtocolExtensionContainer	{ { PDU-Session-Resource-Failed-Item-ExtIEs } }	OPTIONAL,
	...
}

PDU-Session-Resource-Failed-Item-ExtIEs		E1AP-PROTOCOL-EXTENSION ::= {
	...
}

PDU-Session-Resource-Failed-Mod-List	::= SEQUENCE (SIZE(1.. maxnoofPDUSessionResource)) OF PDU-Session-Resource-Failed-Mod-Item

PDU-Session-Resource-Failed-Mod-Item	::=	SEQUENCE {
	pDU-Session-ID							PDU-Session-ID,
	cause									Cause,
	iE-Extensions							ProtocolExtensionContainer	{ { PDU-Session-Resource-Failed-Mod-Item-ExtIEs } }	OPTIONAL,
	...
}

PDU-Session-Resource-Failed-Mod-Item-ExtIEs		E1AP-PROTOCOL-EXTENSION ::= {
	...
}

PDU-Session-Resource-Failed-To-Modify-List	::= SEQUENCE (SIZE(1.. maxnoofPDUSessionResource)) OF PDU-Session-Resource-Failed-To-Modify-Item

PDU-Session-Resource-Failed-To-Modify-Item	::=	SEQUENCE {
	pDU-Session-ID							PDU-Session-ID,
	cause									Cause,
	iE-Extensions							ProtocolExtensionContainer	{ { PDU-Session-Resource-Failed-To-Modify-Item-ExtIEs } }	OPTIONAL,
	...
}

PDU-Session-Resource-Failed-To-Modify-Item-ExtIEs		E1AP-PROTOCOL-EXTENSION ::= {
	...
}

PDU-Session-Resource-Modified-List	::= SEQUENCE (SIZE(1.. maxnoofPDUSessionResource)) OF PDU-Session-Resource-Modified-Item

PDU-Session-Resource-Modified-Item	::=	SEQUENCE {
	pDU-Session-ID							PDU-Session-ID,
	nG-DL-UP-TNL-Information				UP-TNL-Information						OPTIONAL,
	securityResult							SecurityResult							OPTIONAL,
	pDU-Session-Data-Forwarding-Information-Response		Data-Forwarding-Information		OPTIONAL,
	dRB-Setup-List-NG-RAN					DRB-Setup-List-NG-RAN					OPTIONAL,
	dRB-Failed-List-NG-RAN				DRB-Failed-List-NG-RAN				OPTIONAL,
	dRB-Modified-List-NG-RAN				DRB-Modified-List-NG-RAN				OPTIONAL,
	dRB-Failed-To-Modify-List-NG-RAN		DRB-Failed-To-Modify-List-NG-RAN		OPTIONAL,
	iE-Extensions							ProtocolExtensionContainer	{ { PDU-Session-Resource-Modified-Item-ExtIEs } }	OPTIONAL,
	...
}

PDU-Session-Resource-Modified-Item-ExtIEs		E1AP-PROTOCOL-EXTENSION ::= {
	{ ID id-redundant-nG-DL-UP-TNL-Information		CRITICALITY ignore	EXTENSION 	UP-TNL-Information	PRESENCE optional	},
	...
}

PDU-Session-Resource-Required-To-Modify-List	::= SEQUENCE (SIZE(1.. maxnoofPDUSessionResource)) OF PDU-Session-Resource-Required-To-Modify-Item

PDU-Session-Resource-Required-To-Modify-Item	::=	SEQUENCE {
	pDU-Session-ID							PDU-Session-ID,
	nG-DL-UP-TNL-Information				UP-TNL-Information						OPTIONAL,
	dRB-Required-To-Modify-List-NG-RAN		DRB-Required-To-Modify-List-NG-RAN		OPTIONAL,
	dRB-Required-To-Remove-List-NG-RAN				DRB-Required-To-Remove-List-NG-RAN				OPTIONAL,
	iE-Extensions							ProtocolExtensionContainer	{ { PDU-Session-Resource-Required-To-Modify-Item-ExtIEs } }	OPTIONAL,
	...
}

PDU-Session-Resource-Required-To-Modify-Item-ExtIEs		E1AP-PROTOCOL-EXTENSION ::= {
	{ ID id-redundant-nG-DL-UP-TNL-Information		CRITICALITY ignore	EXTENSION 	UP-TNL-Information	PRESENCE optional	},
	...
}

PDU-Session-Resource-Setup-List	::= SEQUENCE (SIZE(1.. maxnoofPDUSessionResource)) OF PDU-Session-Resource-Setup-Item

PDU-Session-Resource-Setup-Item	::=	SEQUENCE {
	pDU-Session-ID							PDU-Session-ID,
	securityResult							SecurityResult				OPTIONAL,
	nG-DL-UP-TNL-Information				UP-TNL-Information,
	pDU-Session-Data-Forwarding-Information-Response		Data-Forwarding-Information		OPTIONAL,
	nG-DL-UP-Unchanged						ENUMERATED {true, ...}		OPTIONAL,
	dRB-Setup-List-NG-RAN					DRB-Setup-List-NG-RAN,
	dRB-Failed-List-NG-RAN					DRB-Failed-List-NG-RAN		OPTIONAL,
	iE-Extensions							ProtocolExtensionContainer	{ { PDU-Session-Resource-Setup-Item-ExtIEs } }	OPTIONAL,
	...
}

PDU-Session-Resource-Setup-Item-ExtIEs		E1AP-PROTOCOL-EXTENSION ::= {
	{ ID id-redundant-nG-DL-UP-TNL-Information		CRITICALITY ignore	EXTENSION 	UP-TNL-Information	PRESENCE optional	}|
	{ ID id-RedundantPDUSessionInformation-used		CRITICALITY ignore	EXTENSION 	RedundantPDUSessionInformation	PRESENCE optional	},
	...
}

PDU-Session-Resource-Setup-Mod-List	::= SEQUENCE (SIZE(1.. maxnoofPDUSessionResource)) OF PDU-Session-Resource-Setup-Mod-Item

PDU-Session-Resource-Setup-Mod-Item	::=	SEQUENCE {
	pDU-Session-ID											PDU-Session-ID,
	securityResult											SecurityResult								OPTIONAL,
	nG-DL-UP-TNL-Information								UP-TNL-Information,
	pDU-Session-Data-Forwarding-Information-Response		Data-Forwarding-Information		OPTIONAL,
	dRB-Setup-Mod-List-NG-RAN								DRB-Setup-Mod-List-NG-RAN,
	dRB-Failed-Mod-List-NG-RAN								DRB-Failed-Mod-List-NG-RAN					OPTIONAL,
	iE-Extensions											ProtocolExtensionContainer	{ { PDU-Session-Resource-Setup-Mod-Item-ExtIEs } }	OPTIONAL,
	...
}

PDU-Session-Resource-Setup-Mod-Item-ExtIEs		E1AP-PROTOCOL-EXTENSION ::= {
	{ ID id-redundant-nG-DL-UP-TNL-Information		CRITICALITY ignore	EXTENSION 	UP-TNL-Information	PRESENCE optional	},
	...
}

PDU-Session-Resource-To-Modify-List	::= SEQUENCE (SIZE(1.. maxnoofPDUSessionResource)) OF PDU-Session-Resource-To-Modify-Item

PDU-Session-Resource-To-Modify-Item	::=	SEQUENCE {
	pDU-Session-ID										PDU-Session-ID,
	securityIndication									SecurityIndication						OPTIONAL,
	pDU-Session-Resource-DL-AMBR						BitRate									OPTIONAL,
	nG-UL-UP-TNL-Information							UP-TNL-Information						OPTIONAL,
	pDU-Session-Data-Forwarding-Information-Request		Data-Forwarding-Information-Request		OPTIONAL,
	pDU-Session-Data-Forwarding-Information	Data-Forwarding-Information	OPTIONAL,
	pDU-Session-Inactivity-Timer						Inactivity-Timer						OPTIONAL,
	networkInstance										NetworkInstance							OPTIONAL,
	dRB-To-Setup-List-NG-RAN							DRB-To-Setup-List-NG-RAN				OPTIONAL,
	dRB-To-Modify-List-NG-RAN							DRB-To-Modify-List-NG-RAN				OPTIONAL,
	dRB-To-Remove-List-NG-RAN					DRB-To-Remove-List-NG-RAN		OPTIONAL,
	iE-Extensions										ProtocolExtensionContainer	{ { PDU-Session-Resource-To-Modify-Item-ExtIEs } }	OPTIONAL,
	...
}

PDU-Session-Resource-To-Modify-Item-ExtIEs		E1AP-PROTOCOL-EXTENSION ::= {
	{ID id-SNSSAI										CRITICALITY reject	EXTENSION SNSSAI												PRESENCE optional}|
	{ID id-CommonNetworkInstance						CRITICALITY ignore	EXTENSION CommonNetworkInstance								PRESENCE optional	}|
	{ID id-redundant-nG-UL-UP-TNL-Information			CRITICALITY ignore	EXTENSION 	UP-TNL-Information								PRESENCE optional	}|
	{ID id-RedundantCommonNetworkInstance				CRITICALITY ignore	EXTENSION 	CommonNetworkInstance							PRESENCE optional	}|
	{ID id-DataForwardingtoE-UTRANInformationList		CRITICALITY ignore	EXTENSION 	DataForwardingtoE-UTRANInformationList	PRESENCE optional	}|
	{ID id-SecurityIndicationModify						CRITICALITY ignore	EXTENSION 	SecurityIndication								PRESENCE optional	}|
	{ID id-Secondary-PDU-Session-Data-Forwarding-Information	CRITICALITY ignore	EXTENSION 	Data-Forwarding-Information		PRESENCE optional	}|
	{ID id-UserPlaneFailureIndication					CRITICALITY ignore	EXTENSION 	UserPlaneFailureIndication						PRESENCE optional	}|
	{ID id-SpecialTriggeringPurpose						CRITICALITY ignore	EXTENSION 	SpecialTriggeringPurpose						PRESENCE optional},
	...
}

PDU-Session-Resource-To-Remove-List	::= SEQUENCE (SIZE(1.. maxnoofPDUSessionResource)) OF PDU-Session-Resource-To-Remove-Item

PDU-Session-Resource-To-Remove-Item	::=	SEQUENCE {
	pDU-Session-ID							PDU-Session-ID,
	iE-Extensions							ProtocolExtensionContainer	{ { PDU-Session-Resource-To-Remove-Item-ExtIEs } }	OPTIONAL,
	...
}

PDU-Session-Resource-To-Remove-Item-ExtIEs		E1AP-PROTOCOL-EXTENSION ::= {
	{ID id-Cause		CRITICALITY ignore	EXTENSION Cause		PRESENCE optional}|
	{ID id-UserPlaneErrorIndicator		CRITICALITY ignore	EXTENSION UserPlaneErrorIndicator		PRESENCE optional},
	...
}

PDU-Session-Resource-To-Setup-List	::= SEQUENCE (SIZE(1.. maxnoofPDUSessionResource)) OF PDU-Session-Resource-To-Setup-Item

PDU-Session-Resource-To-Setup-Item	::=	SEQUENCE {
	pDU-Session-ID							PDU-Session-ID,
	pDU-Session-Type						PDU-Session-Type,
	sNSSAI									SNSSAI,
	securityIndication						SecurityIndication,
	pDU-Session-Resource-DL-AMBR			BitRate						OPTIONAL,
	nG-UL-UP-TNL-Information				UP-TNL-Information,
	pDU-Session-Data-Forwarding-Information-Request		Data-Forwarding-Information-Request		OPTIONAL,
	pDU-Session-Inactivity-Timer			Inactivity-Timer	OPTIONAL,
	existing-Allocated-NG-DL-UP-TNL-Info	UP-TNL-Information		OPTIONAL,
	networkInstance							NetworkInstance		OPTIONAL,
	dRB-To-Setup-List-NG-RAN				DRB-To-Setup-List-NG-RAN,
	iE-Extensions							ProtocolExtensionContainer	{ { PDU-Session-Resource-To-Setup-Item-ExtIEs } }	OPTIONAL,
	...
}

PDU-Session-Resource-To-Setup-Item-ExtIEs		E1AP-PROTOCOL-EXTENSION ::= {
	{ ID id-CommonNetworkInstance						CRITICALITY ignore	EXTENSION CommonNetworkInstance								PRESENCE optional	}|
	{ ID id-redundant-nG-UL-UP-TNL-Information		CRITICALITY ignore	EXTENSION 	UP-TNL-Information					PRESENCE optional	}|
	{ ID id-RedundantCommonNetworkInstance			CRITICALITY ignore	EXTENSION 	CommonNetworkInstance				PRESENCE optional	}|
	{ ID id-RedundantPDUSessionInformation			CRITICALITY ignore	EXTENSION 	RedundantPDUSessionInformation	PRESENCE optional	}|
	{ID id-SpecialTriggeringPurpose			CRITICALITY ignore	EXTENSION SpecialTriggeringPurpose					PRESENCE optional},
	...
}

PDU-Session-Resource-To-Setup-Mod-List	::= SEQUENCE (SIZE(1.. maxnoofPDUSessionResource)) OF PDU-Session-Resource-To-Setup-Mod-Item

PDU-Session-Resource-To-Setup-Mod-Item	::=	SEQUENCE {
	pDU-Session-ID										PDU-Session-ID,
	pDU-Session-Type									PDU-Session-Type,
	sNSSAI												SNSSAI,
	securityIndication									SecurityIndication,
	pDU-Session-Resource-AMBR							BitRate									OPTIONAL,
	nG-UL-UP-TNL-Information							UP-TNL-Information,
	pDU-Session-Data-Forwarding-Information-Request		Data-Forwarding-Information-Request		OPTIONAL,
	pDU-Session-Inactivity-Timer						Inactivity-Timer						OPTIONAL,
	dRB-To-Setup-Mod-List-NG-RAN						DRB-To-Setup-Mod-List-NG-RAN,
	iE-Extensions										ProtocolExtensionContainer	{ { PDU-Session-Resource-To-Setup-Mod-Item-ExtIEs } }	OPTIONAL,
	...
}

PDU-Session-Resource-To-Setup-Mod-Item-ExtIEs		E1AP-PROTOCOL-EXTENSION ::= {
	{ID id-NetworkInstance		CRITICALITY ignore	EXTENSION NetworkInstance		PRESENCE optional}|
	{ID id-CommonNetworkInstance	CRITICALITY ignore	EXTENSION CommonNetworkInstance	PRESENCE optional}|
	{ID id-redundant-nG-UL-UP-TNL-Information		CRITICALITY ignore	EXTENSION 	UP-TNL-Information		PRESENCE optional	}|
	{ID id-RedundantCommonNetworkInstance			CRITICALITY ignore	EXTENSION 	CommonNetworkInstance	PRESENCE optional	}|
	{ID id-SpecialTriggeringPurpose			CRITICALITY ignore	EXTENSION SpecialTriggeringPurpose					PRESENCE optional},
	...
}

PDU-Session-To-Notify-List	::= SEQUENCE (SIZE(1.. maxnoofPDUSessionResource)) OF PDU-Session-To-Notify-Item

PDU-Session-To-Notify-Item	::=	SEQUENCE {
	pDU-Session-ID							PDU-Session-ID,
	qoS-Flow-List							QoS-Flow-List,
	iE-Extensions							ProtocolExtensionContainer	{ { PDU-Session-To-Notify-Item-ExtIEs } }	OPTIONAL,
	...
}

PDU-Session-To-Notify-Item-ExtIEs		E1AP-PROTOCOL-EXTENSION ::= {
	...
}

PDU-Session-Type ::= ENUMERATED {
	ipv4,
	ipv6,
	ipv4v6,
	ethernet,
	unstructured,
	...
}

PDUSetbasedHandlingIndicator ::= ENUMERATED {supported, ...}

PLMN-Identity ::= OCTET STRING (SIZE(3))

PortNumber ::= BIT STRING (SIZE(16))

PPI ::= INTEGER (0..7, ...)

PriorityLevel	::= INTEGER { spare (0), highest (1), lowest (14), no-priority (15) } (0..15)

Pre-emptionCapability ::= ENUMERATED {
	shall-not-trigger-pre-emption,
	may-trigger-pre-emption
}

Pre-emptionVulnerability ::= ENUMERATED {
	not-pre-emptable,
	pre-emptable
}

PrivacyIndicator ::= ENUMERATED {
	immediate-MDT,
	logged-MDT,
	...
}

PDUSetQoSParameters	::= SEQUENCE {
	ulPDUSetQoSInformation	PDUSetQoSInformation	OPTIONAL,
	dlPDUSetQoSInformation	PDUSetQoSInformation	OPTIONAL,
	iE-Extensions			ProtocolExtensionContainer { { PDUSetQoSParameters-ExtIEs } }	OPTIONAL
}

PDUSetQoSParameters-ExtIEs E1AP-PROTOCOL-EXTENSION ::= {
	...
	}

PDUSetQoSInformation ::= SEQUENCE {
	pduSetDelayBudget						ExtendedPacketDelayBudget						OPTIONAL,
	pduSetErrorRate							PacketErrorRate									OPTIONAL,
	pduSetIntegratedHandlingInformation		ENUMERATED {true, false, ...}					OPTIONAL,
	iE-Extensions			ProtocolExtensionContainer { { PDUSetQoSInformation-ExtIEs } }	OPTIONAL
}

PDUSetQoSInformation-ExtIEs E1AP-PROTOCOL-EXTENSION ::= {
	...
}

-- Q

QCI ::= INTEGER (0..255)

QoS-Characteristics ::= CHOICE {
	non-Dynamic-5QI				Non-Dynamic5QIDescriptor,
	dynamic-5QI					Dynamic5QIDescriptor,
	choice-extension			ProtocolIE-SingleContainer	{{QoS-Characteristics-ExtIEs}}
}

QoS-Characteristics-ExtIEs E1AP-PROTOCOL-IES ::= {
	...
}

QoS-Flow-Identifier	::=	INTEGER (0..63)

QoS-Flow-List	::= SEQUENCE (SIZE(1.. maxnoofQoSFlows)) OF QoS-Flow-Item

QoS-Flow-Item	::=	SEQUENCE {
	qoS-Flow-Identifier						QoS-Flow-Identifier,
	iE-Extensions							ProtocolExtensionContainer	{ { QoS-Flow-Item-ExtIEs } }	OPTIONAL,
	...
}

QoS-Flow-Item-ExtIEs		E1AP-PROTOCOL-EXTENSION ::= {
	{ID id-QoSFlowMappingIndication		CRITICALITY ignore	EXTENSION QoS-Flow-Mapping-Indication		PRESENCE optional}|
	{ID id-DataForwardingSourceIPAddress	CRITICALITY ignore	EXTENSION TransportLayerAddress					PRESENCE optional}|
	{ID id-ECNMarkingorCongestionInformationReportingStatus	CRITICALITY ignore	EXTENSION ECNMarkingorCongestionInformationReportingStatus					PRESENCE optional},
	...
}

QoS-Flow-Failed-List	::= SEQUENCE (SIZE(1.. maxnoofQoSFlows)) OF QoS-Flow-Failed-Item

QoS-Flow-Failed-Item	::=	SEQUENCE {
	qoS-Flow-Identifier						QoS-Flow-Identifier,
	cause									Cause,
	iE-Extensions							ProtocolExtensionContainer	{ { QoS-Flow-Failed-Item-ExtIEs } }	OPTIONAL,
	...
}

QoS-Flow-Failed-Item-ExtIEs		E1AP-PROTOCOL-EXTENSION ::= {
	...
}

QoS-Flow-Mapping-List	::= SEQUENCE (SIZE(1.. maxnoofQoSFlows)) OF QoS-Flow-Mapping-Item

QoS-Flow-Mapping-Item	::=	SEQUENCE {
	qoS-Flow-Identifier						QoS-Flow-Identifier,
	qoSFlowMappingIndication						QoS-Flow-Mapping-Indication		OPTIONAL,
	iE-Extensions							ProtocolExtensionContainer	{ { QoS-Flow-Mapping-Item-ExtIEs } }	OPTIONAL,
	...
}

QoS-Flow-Mapping-Item-ExtIEs		E1AP-PROTOCOL-EXTENSION ::= {
	...
}

QoS-Flow-Mapping-Indication ::= ENUMERATED {ul, dl, ...}

QoS-Flows-DRB-Remapping ::= ENUMERATED {update, source-configuration, ...}

QoS-Parameters-Support-List	::= SEQUENCE {
	eUTRAN-QoS-Support-List			EUTRAN-QoS-Support-List			OPTIONAL,
	nG-RAN-QoS-Support-List			NG-RAN-QoS-Support-List			OPTIONAL,
	iE-Extensions					ProtocolExtensionContainer { { QoS-Parameters-Support-List-ItemExtIEs} } OPTIONAL,
	...
}

QoS-Parameters-Support-List-ItemExtIEs E1AP-PROTOCOL-EXTENSION ::= {
	...
}

QoSPriorityLevel ::= INTEGER (0..127, ...)


QoS-Flow-QoS-Parameter-List	::= SEQUENCE (SIZE(1.. maxnoofQoSFlows)) OF QoS-Flow-QoS-Parameter-Item

QoS-Flow-QoS-Parameter-Item	::=	SEQUENCE {
	qoS-Flow-Identifier						QoS-Flow-Identifier,
	qoSFlowLevelQoSParameters				QoSFlowLevelQoSParameters,
	qoSFlowMappingIndication				QoS-Flow-Mapping-Indication		OPTIONAL,
	iE-Extensions							ProtocolExtensionContainer	{ { QoS-Flow-QoS-Parameter-Item-ExtIEs } }	OPTIONAL,
	...
}

QoS-Flow-QoS-Parameter-Item-ExtIEs		E1AP-PROTOCOL-EXTENSION ::= {
	{ID id-RedundantQosFlowIndicator		CRITICALITY ignore 	EXTENSION RedundantQoSFlowIndicator			PRESENCE optional}|
	{ID id-TSCTrafficCharacteristics 		CRITICALITY ignore 	EXTENSION TSCTrafficCharacteristics 			PRESENCE optional}|
	{ID id-ECNMarkingorCongestionInformationReportingRequest 		CRITICALITY ignore 	EXTENSION ECNMarkingorCongestionInformationReportingRequest 			PRESENCE optional},
	...
}

QoSFlowLevelQoSParameters	::= SEQUENCE {
	qoS-Characteristics						QoS-Characteristics,
	nGRANallocationRetentionPriority		NGRANAllocationAndRetentionPriority,
	gBR-QoS-Flow-Information				GBR-QoSFlowInformation						OPTIONAL,
	reflective-QoS-Attribute				ENUMERATED {subject-to, ...}				OPTIONAL,
	additional-QoS-Information				ENUMERATED {more-likely, ...}				OPTIONAL,
	paging-Policy-Index					INTEGER	(1..8,	...)						OPTIONAL,
-- The paging-Policy-Index IE is not used in this version of the specification.
	reflective-QoS-Indicator				ENUMERATED {enabled, ...}					OPTIONAL,
	iE-Extensions							ProtocolExtensionContainer { { QoSFlowLevelQoSParameters-ExtIEs } }	OPTIONAL
}

QoSFlowLevelQoSParameters-ExtIEs 	E1AP-PROTOCOL-EXTENSION ::= {
	{ID id-QoSMonitoringRequest				CRITICALITY ignore	EXTENSION QosMonitoringRequest					PRESENCE optional}|
	{ID id-MCG-OfferedGBRQoSFlowInfo		CRITICALITY ignore	EXTENSION GBR-QoSFlowInformation				PRESENCE optional}|
	{ID id-QosMonitoringReportingFrequency	CRITICALITY ignore	EXTENSION QosMonitoringReportingFrequency	PRESENCE optional}|
	{ID id-QoSMonitoringDisabled			CRITICALITY ignore	EXTENSION QosMonitoringDisabled					PRESENCE optional}|
	{ID id-DataForwardingSourceIPAddress	CRITICALITY ignore	EXTENSION TransportLayerAddress					PRESENCE optional}|
	{ID id-PDUSetQoSParameters				CRITICALITY ignore	EXTENSION PDUSetQoSParameters 					PRESENCE optional}|
	{ID id-MMSID							CRITICALITY ignore	EXTENSION MMSID									PRESENCE optional}|
	{ID id-DL-PDU-Set-Info-Marking-Support-Ind			CRITICALITY ignore	EXTENSION DL-PDU-Set-Info-Marking-Support-Ind				PRESENCE optional},
	...
}

QosMonitoringRequest ::= ENUMERATED {ul, dl, both}

QosMonitoringReportingFrequency ::= INTEGER (1..1800, ...)

QosMonitoringDisabled ::= ENUMERATED {true, ...}

QoS-Flow-Removed-Item	::=	SEQUENCE {
	qoS-Flow-Identifier						QoS-Flow-Identifier,
	qoS-Flow-Released-In-Session			ENUMERATED {released-in-session, not-released-in-session, ...}			OPTIONAL,
	qoS-Flow-Accumulated-Session-Time		OCTET STRING (SIZE(5))														OPTIONAL,
	iE-Extensions							ProtocolExtensionContainer { { QoS-Flow-Removed-Item-ExtIEs } }		OPTIONAL,
	...
}

QoS-Flow-Removed-Item-ExtIEs		E1AP-PROTOCOL-EXTENSION ::= {
	...
}

QoS-Flows-to-be-forwarded-List ::= SEQUENCE (SIZE(1.. maxnoofQoSFlows)) OF QoS-Flows-to-be-forwarded-Item

QoS-Flows-to-be-forwarded-Item ::=	SEQUENCE {
	qoS-Flow-Identifier						QoS-Flow-Identifier,
	iE-Extensions							ProtocolExtensionContainer { { QoS-Flows-to-be-forwarded-Item-ExtIEs } }	OPTIONAL,
	...
}

QoS-Flows-to-be-forwarded-Item-ExtIEs E1AP-PROTOCOL-EXTENSION ::= {
	...
}

QoS-Mapping-Information ::= SEQUENCE {
dscp							BIT STRING (SIZE(6))		OPTIONAL,
flow-label						BIT STRING (SIZE(20))	OPTIONAL,
...
}

DataForwardingtoNG-RANQoSFlowInformationList		::= SEQUENCE (SIZE(1.. maxnoofQoSFlows)) OF DataForwardingtoNG-RANQoSFlowInformationList-Item

DataForwardingtoNG-RANQoSFlowInformationList-Item	::=	SEQUENCE {
	qoS-Flow-Identifier					QoS-Flow-Identifier,
	iE-Extensions						ProtocolExtensionContainer	{ { DataForwardingtoNG-RANQoSFlowInformationList-Item-ExtIEs} }	OPTIONAL,
	...
}

DataForwardingtoNG-RANQoSFlowInformationList-Item-ExtIEs E1AP-PROTOCOL-EXTENSION ::= {
	...
}

-- R

RANUEID ::= OCTET STRING (SIZE (8))

RAT-Type	::=	ENUMERATED	{
	e-UTRA,
	nR,
	...
}

RedundantQoSFlowIndicator::= ENUMERATED {true,false}

RedundantPDUSessionInformation ::= SEQUENCE {
	rSN					RSN,
	iE-Extensions		ProtocolExtensionContainer { {RedundantPDUSessionInformation-ExtIEs} }	OPTIONAL,
	...
}

RedundantPDUSessionInformation-ExtIEs E1AP-PROTOCOL-EXTENSION ::= {
	{ID id-PDUSession-PairID	CRITICALITY ignore	EXTENSION PDUSession-PairID	PRESENCE optional	},
	...
}

RSN ::= ENUMERATED {v1, v2, ...}

RetainabilityMeasurementsInfo	::= SEQUENCE (SIZE(1.. maxnoofDRBs)) OF DRB-Removed-Item

RegistrationRequest	::=	ENUMERATED	{
	start,
	stop,
	...
}

RegistrationRequestForDataCollection ::= ENUMERATED {start, stop, ... }

ReportCharacteristics	::=	BIT STRING (SIZE(36))

ReportCharacteristicsForDataCollection ::= BIT STRING(SIZE(32))

ReportingPeriodicity	::=	ENUMERATED	{
	ms500, ms1000, ms2000, ms5000, ms10000, ms20000, ms30000, ms40000, ms50000, ms60000, ms70000, ms80000, ms90000, ms100000, ms110000, ms120000,
	...
}

ReportingPeriodicityForDataCollection ::= ENUMERATED {
	ms500, ms1000, ms2000, ms5000, ms10000,
	...
}

ReportingThreshold ::= INTEGER(0.. 4000000000, ...)

RequestedAction4AvailNGUTermination ::= ENUMERATED {
	apply-available-configuration,
	apply-requested-configuration,
	...,
	apply-available-configuration-if-same-as-requested

}

RLC-Mode	::=	ENUMERATED	{
	rlc-tm,
	rlc-am,
	rlc-um-bidirectional,
	rlc-um-unidirectional-ul,
	rlc-um-unidirectional-dl,
	...
}


ROHC-Parameters	::= CHOICE {
	rOHC					ROHC,
	uPlinkOnlyROHC			UplinkOnlyROHC,
	choice-Extension		ProtocolIE-SingleContainer { { ROHC-Parameters-ExtIEs} }
}

ROHC-Parameters-ExtIEs E1AP-PROTOCOL-IES ::= {
	...
}

ROHC	::= SEQUENCE {
	maxCID							INTEGER (0..16383, ...),
	rOHC-Profiles					INTEGER (0..511, ...),
	continueROHC					ENUMERATED {true, ...}								OPTIONAL,
	iE-Extensions					ProtocolExtensionContainer { { ROHC-ExtIEs } } 		OPTIONAL
}

ROHC-ExtIEs E1AP-PROTOCOL-EXTENSION ::= {
	...
}

Remaining-time-based-rLC-threshold	::= INTEGER(1..64, ...)

-- S

SDT-data-size-threshold ::= INTEGER (1.. 192000, ...)

SDT-data-size-threshold-Crossed ::=	ENUMERATED {true, ...}

SCGActivationStatus	::=		ENUMERATED { scg-activated, scg-deactivated, ...}

SecurityAlgorithm	::= SEQUENCE {
	cipheringAlgorithm				CipheringAlgorithm,
	integrityProtectionAlgorithm	IntegrityProtectionAlgorithm	OPTIONAL,
	iE-Extensions					ProtocolExtensionContainer { { SecurityAlgorithm-ExtIEs } }	OPTIONAL,
	...
}

SecurityAlgorithm-ExtIEs	E1AP-PROTOCOL-EXTENSION ::= {
	...
}

SecurityIndication ::= SEQUENCE {
	integrityProtectionIndication			IntegrityProtectionIndication,
	confidentialityProtectionIndication		ConfidentialityProtectionIndication,
	maximumIPdatarate							MaximumIPdatarate							OPTIONAL,
-- This IE shall be present if the Integrity Protection Indication IE within the Security Indication IE is set to “required” or “preferred”.--
	iE-Extensions		ProtocolExtensionContainer { {SecurityIndication-ExtIEs} }	OPTIONAL,
	...
}

SecurityIndication-ExtIEs E1AP-PROTOCOL-EXTENSION ::= {
	...
}

SecurityInformation ::= SEQUENCE {
	securityAlgorithm			SecurityAlgorithm,
	uPSecuritykey				UPSecuritykey,
	iE-Extensions				ProtocolExtensionContainer { { SecurityInformation-ExtIEs } }	OPTIONAL,
	...
}

SecurityInformation-ExtIEs	E1AP-PROTOCOL-EXTENSION ::= {
	...
}

SecurityResult ::= SEQUENCE {
	integrityProtectionResult			IntegrityProtectionResult,
	confidentialityProtectionResult		ConfidentialityProtectionResult,
	iE-Extensions						ProtocolExtensionContainer { {SecurityResult-ExtIEs} }	OPTIONAL,
	...
}

SecurityResult-ExtIEs E1AP-PROTOCOL-EXTENSION ::= {
	...
}

Slice-Support-List ::= SEQUENCE (SIZE(1.. maxnoofSliceItems)) OF Slice-Support-Item

Slice-Support-Item ::= SEQUENCE {
	sNSSAI	SNSSAI,
	iE-Extensions				ProtocolExtensionContainer { { Slice-Support-Item-ExtIEs } }	OPTIONAL
}

Slice-Support-Item-ExtIEs	E1AP-PROTOCOL-EXTENSION ::= {
	...
}

SNSSAI ::= SEQUENCE {
	sST			OCTET STRING (SIZE(1)),
	sD			OCTET STRING (SIZE(3)) 	OPTIONAL,
	iE-Extensions				ProtocolExtensionContainer { { SNSSAI-ExtIEs } }	OPTIONAL,
	...
}

SNSSAI-ExtIEs	E1AP-PROTOCOL-EXTENSION ::= {
	...
}

SDAP-Configuration ::= SEQUENCE {
	defaultDRB				DefaultDRB,
	sDAP-Header-UL			SDAP-Header-UL,
	sDAP-Header-DL			SDAP-Header-DL,
	iE-Extensions			ProtocolExtensionContainer { { SDAP-Configuration-ExtIEs } }	OPTIONAL,
	...
}

SDAP-Configuration-ExtIEs	E1AP-PROTOCOL-EXTENSION ::= {
	...
}

SDAP-Header-DL	::=	ENUMERATED	{
	present,
	absent,
	...
}

SDAP-Header-UL	::=	ENUMERATED	{
	present,
	absent,
	...
}

SDTContinueROHC	::=	ENUMERATED {true, ...}

SDTindicatorSetup ::= ENUMERATED {true, ...}

SDTindicatorMod ::= ENUMERATED {true, false, ...}

SubscriberProfileIDforRFP ::= INTEGER (1..256, ...)

SurvivalTime ::= INTEGER (0..1920000, ...)

SpecialTriggeringPurpose ::= ENUMERATED {
	indirect-data-forwarding,
	...
}

F1UTunnelNotEstablished::= ENUMERATED {
	true,
	...
}

-- T

TimeToWait ::= ENUMERATED {v1s, v2s, v5s, v10s, v20s, v60s, ...}

TNLAssociationUsage ::= ENUMERATED {
	ue,
	non-ue,
	both,
...
}

TNL-AvailableCapacityIndicator ::= SEQUENCE {
	dL-TNL-OfferedCapacity				INTEGER (0..16777216, ...),
	dL-TNL-AvailableCapacity			INTEGER (0..100, ...),
	uL-TNL-OfferedCapacity				INTEGER (0..16777216, ...),
	uL-TNL-AvailableCapacity			INTEGER (0..100, ...),
	iE-Extensions		ProtocolExtensionContainer { { TNL-AvailableCapacityIndicator-ExtIEs } } OPTIONAL,
	...
}

TNL-AvailableCapacityIndicator-ExtIEs	E1AP-PROTOCOL-EXTENSION ::= {
	...
}

TSCTrafficCharacteristics		::= SEQUENCE {
	tSCTrafficCharacteristicsUL				TSCAssistanceInformation			OPTIONAL,
	tSCTrafficCharacteristicsDL				TSCAssistanceInformation			OPTIONAL,
	iE-Extensions							ProtocolExtensionContainer { { TSCTrafficCharacteristics-ExtIEs } }	OPTIONAL
}

TSCTrafficCharacteristics-ExtIEs 	E1AP-PROTOCOL-EXTENSION ::= {
	...
}

TSCAssistanceInformation			::= SEQUENCE {
	periodicity						Periodicity,
	burstArrivalTime						BurstArrivalTime				OPTIONAL,
	iE-Extensions							ProtocolExtensionContainer { { TSCAssistanceInformation-ExtIEs } }	OPTIONAL
}

TSCAssistanceInformation-ExtIEs 	E1AP-PROTOCOL-EXTENSION ::= {
	{ID id-SurvivalTime				CRITICALITY ignore		EXTENSION SurvivalTime				PRESENCE optional}|
	{ID id-N6JitterInformation		CRITICALITY ignore		EXTENSION N6JitterInformation		PRESENCE optional},
	...
}

Periodicity					::= INTEGER	(0..640000,	...)

BurstArrivalTime			::= OCTET STRING

TraceActivation ::= SEQUENCE {
	traceID								TraceID,
	interfacesToTrace					InterfacesToTrace,
	traceDepth							TraceDepth,
	traceCollectionEntityIPAddress		TransportLayerAddress,
	iE-Extensions		ProtocolExtensionContainer { {TraceActivation-ExtIEs} }	OPTIONAL,
	...
}

TraceActivation-ExtIEs E1AP-PROTOCOL-EXTENSION ::= {
	{ ID id-MDTConfiguration	CRITICALITY ignore	EXTENSION MDT-Configuration		PRESENCE 	optional }|
	{ ID id-TraceCollectionEntityURI	CRITICALITY ignore	EXTENSION URIaddress	PRESENCE    optional},
	...
}

TraceDepth ::= ENUMERATED {
	minimum,
	medium,
	maximum,
	minimumWithoutVendorSpecificExtension,
	mediumWithoutVendorSpecificExtension,
	maximumWithoutVendorSpecificExtension,
	...,
	minimumOnlyVendorSpecificTraceRecord,
	mediumOnlyVendorSpecificTraceRecord,
	maximumOnlyVendorSpecificTraceRecord

}

TraceID ::= OCTET STRING (SIZE(8))

TransportLayerAddress		::= 	BIT STRING (SIZE(1..160, ...))

TransactionID				::= INTEGER (0..255, ...)

T-Reordering	::=	ENUMERATED	{ms0, ms1, ms2, ms4, ms5, ms8, ms10, ms15, ms20, ms30, ms40, ms50, ms60, ms80, ms100, ms120, ms140, ms160, ms180, ms200, ms220, ms240, ms260, ms280, ms300, ms500, ms750, ms1000, ms1250, ms1500, ms1750, ms2000, ms2250, ms2500, ms2750, ms3000, ...}

T-ReorderingTimer ::= SEQUENCE {
	t-Reordering				T-Reordering,
		iE-Extensions				ProtocolExtensionContainer { { T-ReorderingTimer-ExtIEs } }	OPTIONAL,
	...
}

T-ReorderingTimer-ExtIEs	E1AP-PROTOCOL-EXTENSION ::= {
	...
}

TypeOfError ::= ENUMERATED {
	not-understood,
	missing,
	...
}

Transport-Layer-Address-Info ::= SEQUENCE {
	transport-UP-Layer-Addresses-Info-To-Add-List	Transport-UP-Layer-Addresses-Info-To-Add-List	OPTIONAL,
	transport-UP-Layer-Addresses-Info-To-Remove-List	Transport-UP-Layer-Addresses-Info-To-Remove-List	OPTIONAL,
	iE-Extensions		ProtocolExtensionContainer { { Transport-Layer-Address-Info-ExtIEs} }	OPTIONAL,
	...
	}

Transport-Layer-Address-Info-ExtIEs	E1AP-PROTOCOL-EXTENSION	::=	{
	...
}

Transport-UP-Layer-Addresses-Info-To-Add-List	::= SEQUENCE (SIZE(1.. maxnoofTLAs)) OF Transport-UP-Layer-Addresses-Info-To-Add-Item

Transport-UP-Layer-Addresses-Info-To-Add-Item ::= SEQUENCE {
	iP-SecTransportLayerAddress		TransportLayerAddress,
	gTPTransportLayerAddressesToAdd			GTPTLAs							OPTIONAL,
	iE-Extensions					ProtocolExtensionContainer { { Transport-UP-Layer-Addresses-Info-To-Add-ItemExtIEs } }    OPTIONAL,
	...
}

Transport-UP-Layer-Addresses-Info-To-Add-ItemExtIEs E1AP-PROTOCOL-EXTENSION ::= {
	...
}

Transport-UP-Layer-Addresses-Info-To-Remove-List	::= SEQUENCE (SIZE(1.. maxnoofTLAs)) OF Transport-UP-Layer-Addresses-Info-To-Remove-Item

Transport-UP-Layer-Addresses-Info-To-Remove-Item ::= SEQUENCE {
	iP-SecTransportLayerAddress		TransportLayerAddress,
	gTPTransportLayerAddressesToRemove			GTPTLAs							OPTIONAL,
	iE-Extensions					ProtocolExtensionContainer { { Transport-UP-Layer-Addresses-Info-To-Remove-ItemExtIEs } }    OPTIONAL,
	...
}

Transport-UP-Layer-Addresses-Info-To-Remove-ItemExtIEs E1AP-PROTOCOL-EXTENSION ::= {
	...
}
-- U

UDC-Parameters	::= SEQUENCE {
	bufferSize					BufferSize,
	dictionary					Dictionary											OPTIONAL,
	continueUDC					ENUMERATED {true, ...}								OPTIONAL,
	iE-Extensions					ProtocolExtensionContainer { { UDC-Parameters-ExtIEs } } 		OPTIONAL
}

-- WS modification: define a dedicated type
VersionID ::= INTEGER (0..15)

UDC-Parameters-ExtIEs E1AP-PROTOCOL-EXTENSION ::= {
-- WS modification: define a dedicated type
--	{ ID id-VersionID CRITICALITY ignore EXTENSION INTEGER (0..15) PRESENCE optional},
	{ ID id-VersionID CRITICALITY ignore EXTENSION VersionID PRESENCE optional},
	...
}

UE-Activity	::=	ENUMERATED	{
	active,
	not-active,
	...
}

UEAssociatedInfoResult-List ::= SEQUENCE (SIZE(1..maxnoofUEReports)) OF UEAssociatedInfoResult-Item

UEAssociatedInfoResult-Item ::= SEQUENCE {
	uEAssistantIdentifier						GNB-CU-CP-UE-E1AP-ID,
	dRB-To-Report-List							DRB-To-Report-List,
	iE-Extensions								ProtocolExtensionContainer { { UEAssociatedInfoResult-Item-ExtIEs} } OPTIONAL,
	...
}

UEAssociatedInfoResult-Item-ExtIEs E1AP-PROTOCOL-EXTENSION ::= {
	...
}

UE-associatedLogicalE1-ConnectionItem ::= SEQUENCE {
	gNB-CU-CP-UE-E1AP-ID		GNB-CU-CP-UE-E1AP-ID	 OPTIONAL,
	gNB-CU-UP-UE-E1AP-ID		GNB-CU-UP-UE-E1AP-ID	 OPTIONAL,
	iE-Extensions				ProtocolExtensionContainer { { UE-associatedLogicalE1-ConnectionItemExtIEs} }	OPTIONAL,
	...
}

UE-associatedLogicalE1-ConnectionItemExtIEs E1AP-PROTOCOL-EXTENSION ::= {
	...
}

UEPerformance ::= SEQUENCE {
	uE-AveragePacketDelay						AveragePacketDelay		OPTIONAL,
	uE-AveragePacketDropDL						INTEGER (0..1000000, ...)		OPTIONAL,
	uE-AveragePacketLossUL						INTEGER (0..1000000, ...)		OPTIONAL,
	iE-Extensions								ProtocolExtensionContainer { { UEPerformance-ExtIEs} } OPTIONAL,
	...
}

UEPerformance-ExtIEs E1AP-PROTOCOL-EXTENSION ::= {
	...
}

UEPerformanceCollectionConfiguration ::= SEQUENCE {
	collectionTimeDurationForUEPerformance				INTEGER(1..5000, ...),
	iE-Extensions								ProtocolExtensionContainer { { UEPerformanceCollectionConfiguration-ExtIEs} } OPTIONAL,
	...
}

UEPerformanceCollectionConfiguration-ExtIEs E1AP-PROTOCOL-EXTENSION ::= {
	...
}

UESliceMaximumBitRateList ::= SEQUENCE (SIZE(1.. maxnoofSMBRValues)) OF UESliceMaximumBitRateItem
UESliceMaximumBitRateItem ::= SEQUENCE {
	sNSSAI		SNSSAI,
	uESliceMaximumBitRateDL		BitRate,
	iE-Extensions		ProtocolExtensionContainer { { UESliceMaximumBitRateItem-ExtIEs} } OPTIONAL,
	...
}

UESliceMaximumBitRateItem-ExtIEs E1AP-PROTOCOL-EXTENSION ::= {
	...
}

UL-Configuration	::=	ENUMERATED	{
	no-data,
	shared,
	only,
	...
}

ULUPTNLAddressToUpdateItem	::= SEQUENCE {
	oldTNLAdress						TransportLayerAddress,
	newTNLAdress						TransportLayerAddress,
	iE-Extensions	ProtocolExtensionContainer { { ULUPTNLAddressToUpdateItemExtIEs } }	OPTIONAL,
	...
}

ULUPTNLAddressToUpdateItemExtIEs 	E1AP-PROTOCOL-EXTENSION ::= {
	...
}

ULDataSplitThreshold	::=	ENUMERATED {b0, b100, b200, b400, b800, b1600, b3200, b6400, b12800, b25600, b51200, b102400, b204800, b409600, b819200, b1228800, b1638400, b2457600, b3276800, b4096000, b4915200, b5734400, b6553600, infinity, ...}

UP-Parameters ::= SEQUENCE (SIZE(1.. maxnoofUPParameters)) OF UP-Parameters-Item

UP-Parameters-Item ::= SEQUENCE {
	uP-TNL-Information			UP-TNL-Information,
	cell-Group-ID				Cell-Group-ID,
	iE-Extensions				ProtocolExtensionContainer { { UP-Parameters-Item-ExtIEs } }	OPTIONAL,
	...
}

UP-Parameters-Item-ExtIEs	E1AP-PROTOCOL-EXTENSION ::= {
	{ID id-QoS-Mapping-Information	CRITICALITY reject	EXTENSION QoS-Mapping-Information	PRESENCE optional}|
	{ID id-IndirectPathIndication 	CRITICALITY ignore	EXTENSION IndirectPathIndication 	PRESENCE optional},
	...
}

UPSecuritykey	::= SEQUENCE {
	encryptionKey				EncryptionKey,
	integrityProtectionKey		IntegrityProtectionKey		OPTIONAL,
	iE-Extensions				ProtocolExtensionContainer { { UPSecuritykey-ExtIEs } }	OPTIONAL,
	...
}

UPSecuritykey-ExtIEs	E1AP-PROTOCOL-EXTENSION ::= {
	...
}

UP-TNL-Information		::= 	CHOICE {
	gTPTunnel		GTPTunnel,
	choice-extension		ProtocolIE-SingleContainer	{{UP-TNL-Information-ExtIEs}}
}

UP-TNL-Information-ExtIEs E1AP-PROTOCOL-IES ::= {
	...
}

UplinkOnlyROHC ::= SEQUENCE {
	maxCID							INTEGER (0..16383, ...),
	rOHC-Profiles					INTEGER (0..511, ...),
	continueROHC					ENUMERATED {true, ...}	OPTIONAL,
	iE-Extensions					ProtocolExtensionContainer { { UplinkOnlyROHC-ExtIEs } } 		OPTIONAL
}

UplinkOnlyROHC-ExtIEs E1AP-PROTOCOL-EXTENSION ::= {
	...
}

URIaddress ::= VisibleString

UserPlaneErrorIndicator ::= ENUMERATED {
	gTP-U-error-indication-received,
	...
}

UEInactivityInformation ::= INTEGER (1..7200, ...)

UserPlaneFailureIndication ::= SEQUENCE {
	userPlaneFailureType			UserPlaneFailureType,
	nG-DL-UP-TNL-Information			UP-TNL-Information,
	nG-UL-UP-TNL-Information			UP-TNL-Information,

	iE-Extensions		ProtocolExtensionContainer { { UserPlaneFailureIndication-ExtIEs} }	OPTIONAL,
	...
}

UserPlaneFailureIndication-ExtIEs E1AP-PROTOCOL-EXTENSION ::= {
	...
}

UserPlaneFailureType ::= ENUMERATED {
	gtp-u-error-indication-received,
	up-path-failure,
	...
}

-- V

-- W

-- X

-- Y

-- Z

END

-- 3GPP TS 29.078 11.0.0 (2011-09)
-- 5.6	Object IDentifiers (IDs)
CAP-object-identifiers {itu-t(0) identified-organization(4) etsi(0) mobileDomain(0)
umts-network(1) modules(3) cap-object-identifiers(100) version8(7)}

DEFINITIONS ::= BEGIN

-- This module assigns object identifiers for Modules, Packages, Contracts and ACs
-- used by CAP

-- For Modules from TC, ROS,
tc-Messages										OBJECT IDENTIFIER ::=
	{itu-t recommendation q 773 modules(2) messages(1) version3(3)}

tc-NotationExtensions							OBJECT IDENTIFIER ::=
	{itu-t recommendation q 775 modules(2) notation-extension (4) version1(1)}

ros-InformationObjects							OBJECT IDENTIFIER ::=
	{joint-iso-itu-t remote-operations(4) informationObjects(5) version1(0)}


-- For CAP Modules
datatypes										OBJECT IDENTIFIER ::=
	{itu-t(0) identified-organization(4) etsi(0) mobileDomain(0) umts-network(1) modules(3)
	cap-datatypes(52) version8(7)}

errortypes										OBJECT IDENTIFIER ::=
	{itu-t(0) identified-organization(4) etsi(0) mobileDomain(0) umts-network(1) modules(3)
	cap-errortypes(51) version8(7)}

operationcodes									OBJECT IDENTIFIER ::=
	{itu-t(0) identified-organization(4) etsi(0) mobileDomain(0) umts-network(1) modules(3)
	cap-operationcodes(53) version8(7)}

errorcodes										OBJECT IDENTIFIER ::=
	{itu-t(0) identified-organization(4) etsi(0) mobileDomain(0) umts-network(1) modules(3)
	cap-errorcodes(57) version8(7)}

classes											OBJECT IDENTIFIER ::=
	{itu-t(0) identified-organization(4) etsi(0) mobileDomain(0) umts-network(1) modules(3)
	cap-classes(54) version8(7)}


gsmSSF-gsmSCF-Operations						OBJECT IDENTIFIER ::=
	{itu-t(0) identified-organization(4) etsi(0) mobileDomain(0) umts-network(1) modules(3)
	cap-gsmSSF-gsmSCF-ops-args(101) version8(7)}
-- The Object Identifier 'gsmSSF-gsmSCF-Operations' is updated to version8(7) in Rel-6, so
-- other modules can IMPORT Rel-6 Operation definitions related to call control.

gsmSSF-gsmSCF-Protocol							OBJECT IDENTIFIER ::=
	{itu-t(0) identified-organization(4) etsi(0) mobileDomain(0) umts-network(1) modules(3)
	cap-gsmSSF-gsmSCF-pkgs-contracts-acs(102) version8(7)}
-- The Object Identifier 'gsmSSF-gsmSCF-Protocol' is updated to version8(7) in Rel-6, so
-- other modules can IMPORT Rel-6 Protocol definitions related to call control.

gsmSCF-gsmSRF-Operations						OBJECT IDENTIFIER ::=
	{itu-t(0) identified-organization(4) etsi(0) mobileDomain(0) umts-network(1) modules(3)
	cap-gsmSCF-gsmSRF-ops-args(103) version8(7)}
-- The Object Identifier 'gsmSCF-gsmSRF-Operations' is updated to version8(7) in Rel-6, so
-- other modules can IMPORT Rel-6 Operation definitions related to gsmSRF control.

gsmSCF-gsmSRF-Protocol							OBJECT IDENTIFIER ::=
	{itu-t(0) identified-organization(4) etsi(0) mobileDomain(0) umts-network(1) modules(3)
	cap-gsmSCF-gsmSRF-pkgs-contracts-acs(104) version8(7)}
-- The Object Identifier 'gsmSCF-gsmSRF-Protocol' is updated to version8(7) in Rel-6, so
-- other modules can IMPORT Rel-6 Protocol definitions related to gsmSRF control.

sms-Operations									OBJECT IDENTIFIER ::=
	{itu-t(0) identified-organization(4) etsi(0) mobileDomain(0) umts-network(1) modules(3)
	cap-SMS-ops-args(105) version8(7)}
-- The Object Identifier 'sms-Operations' is updated to version8(7) in Rel-6, so other
-- modules can IMPORT Rel-6 Operation definitions related to SMS control.

smsSSF-gsmSCF-Protocol							OBJECT IDENTIFIER ::=
	{itu-t(0) identified-organization(4) etsi(0) mobileDomain(0) umts-network(1) modules(3)
	cap-smsSSF-gsmSCF-pkgs-contracts-acs(106) version8(7)}
-- The Object Identifier 'smsSSF-gsmSCF-Protocol' is updated to version8(7) in Rel-6, so
-- other modules can IMPORT Rel-6 Protocol definitions related to SMS control.

gprsSSF-gsmSCF-Operations						OBJECT IDENTIFIER ::=
	{itu-t(0) identified-organization(4) etsi(0) mobileDomain(0) umts-network(1) modules(3)
	cap-GPRS-ops-args(107) version8(7)}
-- The Object Identifier 'gprsSSF-gsmSCF-Operations' is updated to version8(7) in Rel-6, so
-- other modules can IMPORT Rel-6 Operation definitions related to GPRS control.

gprsSSF-gsmSCF-Protocol							OBJECT IDENTIFIER ::=
	{itu-t(0) identified-organization(4) etsi(0) mobileDomain(0) umts-network(1) modules(3)
	cap-gprsSSF-gsmSCF-pkgs-contracts-acs(108) version8(7)}
-- The Object Identifier 'gprsSSF-gsmSCF-Protocol' is updated to version8(7) in Rel-6, so
-- other modules can IMPORT Rel-6 Protocol definitions related to GPRS control.

id-CAP											OBJECT IDENTIFIER ::=
	{itu-t(0) identified-organization(4) etsi(0) mobileDomain(0)
	umts-network(1) cap4(22)}

id-CAP3											OBJECT IDENTIFIER ::=
	{itu-t(0) identified-organization(4) etsi(0) mobileDomain(0)
	umts-network(1) cap3(20)}

id-CAPOE										OBJECT IDENTIFIER ::=
	{itu-t(0) identified-organization(4) etsi(0) mobileDomain(0)
	umts-network(1) cap4OE(23)}

id-CAP3OE										OBJECT IDENTIFIER ::=
	{itu-t(0) identified-organization(4) etsi(0) mobileDomain(0)
	umts-network(1) cap3OE(21)}

id-ac											OBJECT IDENTIFIER ::= {id-CAP		ac(3)}
id-acE											OBJECT IDENTIFIER ::= {id-CAPOE		ac(3)}
id-ac3E											OBJECT IDENTIFIER ::= {id-CAP3OE	ac(3)}
id-as											OBJECT IDENTIFIER ::= {id-CAP		as(5)}
id-asE											OBJECT IDENTIFIER ::= {id-CAPOE		as(5)}
id-rosObject									OBJECT IDENTIFIER ::= {id-CAP		rosObject(25)}
id-contract										OBJECT IDENTIFIER ::= {id-CAP		contract(26)}
id-contract3									OBJECT IDENTIFIER ::= {id-CAP3		contract(26)}
id-contractE									OBJECT IDENTIFIER ::= {id-CAPOE		contract(26)}
id-package										OBJECT IDENTIFIER ::= {id-CAP		package(27)}
id-packageE										OBJECT IDENTIFIER ::= {id-CAPOE		package(27)}

-- for ac, as, rosObject, contract and package, the values are identical to ITU-T Recommendation
-- Q.1218 [49]


-- ROS Objects

id-rosObject-gsmSCF								OBJECT IDENTIFIER ::= {id-rosObject 4}
id-rosObject-gsmSSF								OBJECT IDENTIFIER ::= {id-rosObject 5}
id-rosObject-gsmSRF								OBJECT IDENTIFIER ::= {id-rosObject 6}
id-rosObject-gprsSSF							OBJECT IDENTIFIER ::= {id-rosObject 7}
id-rosObject-smsSSF-V3							OBJECT IDENTIFIER ::= {id-rosObject 8}
id-rosObject-smsSSF-V4							OBJECT IDENTIFIER ::= {id-rosObject 9}


-- Application Contexts

-- gsmSSF/gsmSCF AC
id-ac-CAP-gsmSSF-scfGenericAC					OBJECT IDENTIFIER ::= {id-acE 4}
id-ac-CAP-gsmSSF-scfAssistHandoffAC				OBJECT IDENTIFIER ::= {id-acE 6}
id-ac-CAP-scf-gsmSSFGenericAC					OBJECT IDENTIFIER ::= {id-acE 8}

-- gsmSRF/gsmSCF AC
id-ac-gsmSRF-gsmSCF								OBJECT IDENTIFIER ::= {id-ac 14}

-- gprsSSF/gsmSCF AC
id-ac-CAP-gprsSSF-gsmSCF-AC						OBJECT IDENTIFIER ::= {id-ac3E 50}
id-ac-CAP-gsmSCF-gprsSSF-AC						OBJECT IDENTIFIER ::= {id-ac3E 51}

-- gprsSSF/gsmSCF or gsmSSF/gsmSCF AC
id-ac-cap3-sms-AC								OBJECT IDENTIFIER ::= {id-ac3E 61}
id-ac-cap4-sms-AC								OBJECT IDENTIFIER ::= {id-acE 61}


-- Contracts

-- gsmSSF/gsmSCF Contracts
id-CAPSsfToScfGeneric							OBJECT IDENTIFIER ::= {id-contractE 3}
id-CAPAssistHandoffssfToScf						OBJECT IDENTIFIER ::= {id-contractE 5}
id-CAPScfToSsfGeneric							OBJECT IDENTIFIER ::= {id-contractE 6}

-- gsmSRF/gsmSCF Contracts
id-contract-gsmSRF-gsmSCF						OBJECT IDENTIFIER ::= {id-contract 13}

-- gprsSSF/gsmSCF Contracts
id-capGprsSsfTogsmScf							OBJECT IDENTIFIER ::= {id-contract 14}
id-capGsmScfToGprsSsf							OBJECT IDENTIFIER ::= {id-contract 15}

-- gprsSSF/gsmSCF or gsmSSF/gsmSCF Contracts
id-cap3SmsSsfTogsmScf							OBJECT IDENTIFIER ::= {id-contract3 16}
id-cap4SmsSsfTogsmScf							OBJECT IDENTIFIER ::= {id-contract 16}


-- Operation Packages

-- gsmSSF/gsmSCF Operation Packages
id-package-scfActivation						OBJECT IDENTIFIER ::= {id-package 11}
id-package-gsmSRF-scfActivationOfAssist			OBJECT IDENTIFIER ::= {id-package 15}
id-package-assistConnectionEstablishment		OBJECT IDENTIFIER ::= {id-package 16}
id-package-genericDisconnectResource			OBJECT IDENTIFIER ::= {id-package 17}
id-package-nonAssistedConnectionEstablishment	OBJECT IDENTIFIER ::= {id-package 18}
id-package-connect								OBJECT IDENTIFIER ::= {id-package 19}
id-package-callHandling							OBJECT IDENTIFIER ::= {id-packageE 20}
id-package-bcsmEventHandling					OBJECT IDENTIFIER ::= {id-package 21}
id-package-ssfCallProcessing					OBJECT IDENTIFIER ::= {id-packageE 24}
id-package-scfCallInitiation					OBJECT IDENTIFIER ::= {id-package 25}
id-package-timer								OBJECT IDENTIFIER ::= {id-package 26}
id-package-billing								OBJECT IDENTIFIER ::= {id-package 27}
id-package-charging								OBJECT IDENTIFIER ::= {id-package 28}
id-package-trafficManagement					OBJECT IDENTIFIER ::= {id-package 29}
id-package-callReport							OBJECT IDENTIFIER ::= {id-package 32}
id-package-signallingControl					OBJECT IDENTIFIER ::= {id-package 33}
id-package-activityTest							OBJECT IDENTIFIER ::= {id-package 34}
id-package-cancel								OBJECT IDENTIFIER ::= {id-packageE 36}
id-package-cphResponse							OBJECT IDENTIFIER ::= {id-package 37}
id-package-exceptionInform						OBJECT IDENTIFIER ::= {id-package 38}
id-package-playTone								OBJECT IDENTIFIER ::= {id-package 39}

-- gsmSRF/gsmSCF Operation Packages
id-package-specializedResourceControl			OBJECT IDENTIFIER ::= {id-package 42}
id-package-gsmSRF-scfCancel						OBJECT IDENTIFIER ::= {id-package 43}

-- gprsSSF/gsmSCF Operation Packages
id-package-gprsContinue							OBJECT IDENTIFIER ::= {id-package 49}
id-package-gprsExceptionInformation				OBJECT IDENTIFIER ::= {id-package 50}
id-package-gprsScfActivation					OBJECT IDENTIFIER ::= {id-package 51}
id-package-gprsConnect							OBJECT IDENTIFIER ::= {id-package 52}
id-package-gprsRelease							OBJECT IDENTIFIER ::= {id-package 53}
id-package-gprsEventHandling					OBJECT IDENTIFIER ::= {id-package 54}
id-package-gprsTimer							OBJECT IDENTIFIER ::= {id-package 55}
id-package-gprsBilling							OBJECT IDENTIFIER ::= {id-package 56}
id-package-gprsCharging							OBJECT IDENTIFIER ::= {id-package 57}
id-package-gprsActivityTest						OBJECT IDENTIFIER ::= {id-package 58}
id-package-gprsCancel							OBJECT IDENTIFIER ::= {id-package 59}
id-package-gprsChargeAdvice						OBJECT IDENTIFIER ::= {id-package 60}

-- gprsSSF/gsmSCF or gsmSSF/gsmSCF Operation Packages
id-package-smsActivation						OBJECT IDENTIFIER ::= {id-package 61}
id-package-smsConnect							OBJECT IDENTIFIER ::= {id-package 62}
id-package-smsContinue							OBJECT IDENTIFIER ::= {id-package 63}
id-package-smsRelease							OBJECT IDENTIFIER ::= {id-package 64}
id-package-smsEventHandling						OBJECT IDENTIFIER ::= {id-package 65}
id-package-smsBilling							OBJECT IDENTIFIER ::= {id-package 66}
id-package-smsTimer								OBJECT IDENTIFIER ::= {id-package 67}


-- Abstract Syntaxes

-- gsmSSF/gsmSCF Abstract Syntaxes
id-as-gsmSSF-scfGenericAS						OBJECT IDENTIFIER ::= {id-asE 4}
id-as-assistHandoff-gsmSSF-scfAS				OBJECT IDENTIFIER ::= {id-asE 6}
id-as-scf-gsmSSFGenericAS						OBJECT IDENTIFIER ::= {id-asE 7}

-- gsmSRF/gsmSCF Abstract Syntaxes
id-as-basic-gsmSRF-gsmSCF						OBJECT IDENTIFIER ::= {id-as 14}

-- gprsSSF/gsmSCF Abstract Syntaxes
id-as-gprsSSF-gsmSCF-AS							OBJECT IDENTIFIER ::= {id-as 50}
id-as-gsmSCF-gprsSSF-AS							OBJECT IDENTIFIER ::= {id-as 51}

-- gprsSSF/gsmSCF or gsmSSF/gsmSCF Abstract Syntaxes
id-as-smsSSF-gsmSCF-AS							OBJECT IDENTIFIER ::= {id-as 61}

END

--
-- 3GPP TS 29.171 v17.2.0 (2022-12-15)
-- 7.5.6	Common Definitions

-- ************************************************************** 
-- 
-- Common definitions 
-- 
-- ************************************************************** 

LCS-AP-CommonDataTypes {
itu-t (0) identified-organization (4) etsi (0) mobileDomain (0)
eps-Access (21) modules (3) lcs-AP (4) version1 (1) lcs-AP-CommonDataTypes (3)}

DEFINITIONS AUTOMATIC TAGS ::=

BEGIN

Criticality	::= ENUMERATED { reject, ignore, notify }

Presence	::= ENUMERATED { optional, conditional, mandatory }

ProcedureCode	::= INTEGER (0..255)

ProtocolExtensionID	::= INTEGER (0..65535)

ProtocolIE-ID	::= INTEGER (0..65535)

TriggeringMessage	::= ENUMERATED {initiating-message, successful-outcome, unsuccessful-outcome, outcome}

END

-- 3GPP TS 36.455 V15.2.1 (2019-04)
--

-- **************************************************************
--
-- Constant definitions
--
-- **************************************************************

LPPA-Constants {
itu-t (0) identified-organization (4) etsi (0) mobileDomain (0) 
eps-Access (21) modules (3) lppa (6) version1 (1) lppa-Constants (4) }

DEFINITIONS AUTOMATIC TAGS ::= 

BEGIN

IMPORTS
	ProcedureCode,
	ProtocolIE-ID
FROM LPPA-CommonDataTypes;

-- **************************************************************
--
-- Elementary Procedures
--
-- **************************************************************

id-errorIndication												ProcedureCode ::= 0
id-privateMessage												ProcedureCode ::= 1
id-e-CIDMeasurementInitiation									ProcedureCode ::= 2
id-e-CIDMeasurementFailureIndication							ProcedureCode ::= 3
id-e-CIDMeasurementReport										ProcedureCode ::= 4
id-e-CIDMeasurementTermination									ProcedureCode ::= 5
id-oTDOAInformationExchange										ProcedureCode ::= 6
id-uTDOAInformationExchange										ProcedureCode ::= 7
id-uTDOAInformationUpdate										ProcedureCode ::= 8
id-assistanceInformationControl									ProcedureCode ::= 9
id-assistanceInformationFeedback								ProcedureCode ::= 10

-- **************************************************************
--
-- Lists
--
-- **************************************************************

maxNrOfErrors								INTEGER ::= 256
maxCellineNB								INTEGER ::= 256
maxNoMeas									INTEGER ::= 63
maxCellReport								INTEGER ::= 9
maxnoOTDOAtypes								INTEGER ::= 63
maxServCell									INTEGER ::= 5
maxGERANMeas								INTEGER ::= 8
maxUTRANMeas								INTEGER ::= 8
maxCellineNB-ext							INTEGER ::= 3840
maxMBSFN-Allocations						INTEGER ::= 8
maxWLANchannels								INTEGER ::= 16 
maxnoFreqHoppingBandsMinusOne				INTEGER ::= 7
maxNrOfPosSImessage							INTEGER ::= 32
maxnoAssistInfoFailureListItems				INTEGER ::= 32
maxNrOfSegments								INTEGER ::= 64
maxNrOfPosSIBs								INTEGER ::= 32

-- **************************************************************
--
-- IEs
--
-- **************************************************************

id-Cause																	ProtocolIE-ID ::= 0
id-CriticalityDiagnostics													ProtocolIE-ID ::= 1
id-E-SMLC-UE-Measurement-ID													ProtocolIE-ID ::= 2
id-ReportCharacteristics													ProtocolIE-ID ::= 3
id-MeasurementPeriodicity													ProtocolIE-ID ::= 4
id-MeasurementQuantities													ProtocolIE-ID ::= 5
id-eNB-UE-Measurement-ID													ProtocolIE-ID ::= 6
id-E-CID-MeasurementResult													ProtocolIE-ID ::= 7
id-OTDOACells																ProtocolIE-ID ::= 8
id-OTDOA-Information-Type-Group												ProtocolIE-ID ::= 9
id-OTDOA-Information-Type-Item												ProtocolIE-ID ::= 10
id-MeasurementQuantities-Item												ProtocolIE-ID ::= 11
id-RequestedSRSTransmissionCharacteristics									ProtocolIE-ID ::= 12
id-ULConfiguration															ProtocolIE-ID ::= 13
id-Cell-Portion-ID															ProtocolIE-ID ::= 14
id-InterRATMeasurementQuantities											ProtocolIE-ID ::= 15
id-InterRATMeasurementQuantities-Item										ProtocolIE-ID ::= 16
id-InterRATMeasurementResult												ProtocolIE-ID ::= 17
id-AddOTDOACells															ProtocolIE-ID ::= 18
id-WLANMeasurementQuantities												ProtocolIE-ID ::= 19
id-WLANMeasurementQuantities-Item											ProtocolIE-ID ::= 20
id-WLANMeasurementResult													ProtocolIE-ID ::= 21
id-Assistance-Information													ProtocolIE-ID ::= 22
id-Broadcast																ProtocolIE-ID ::= 23
id-AssistanceInformationFailureList											ProtocolIE-ID ::= 24

END

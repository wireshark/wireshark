-- Module ManagedObjectClassesDefinitions (X.721:02/1992)
ManagedObjectClassesDefinitions {joint-iso-itu-t ms(9) smi(3) part2(2)
  asn1Module(2) 0} DEFINITIONS ::=
BEGIN

--EXPORTS everything
smi2MObjectClass OBJECT IDENTIFIER ::=
  {joint-iso-itu-t ms(9) smi(3) part2(2) managedObjectClass(3)}

smi2NameBinding OBJECT IDENTIFIER ::=
  {joint-iso-itu-t ms(9) smi(3) part2(2) nameBinding(6)}

smi2Package OBJECT IDENTIFIER ::=
  {joint-iso-itu-t ms(9) smi(3) part2(2) package(4)}

END

-- Generated by Asnp, the ASN.1 pretty-printer of France Telecom R&D

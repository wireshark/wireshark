-- Manufacturer-specific-service-extension-definition.asn
--
-- Taken from ITU ASN.1 database
-- http://www.itu.int/ITU-T/asn1/database/itu-t/h/h450.1/1998/Manufacturer-specific-service-extension-definition.asn
--

-- Module Manufacturer-specific-service-extension-definition (H.450.1:02/1998)
Manufacturer-specific-service-extension-definition {itu-t recommendation 
  h 450 1 version1(0) msi-definition(18)} DEFINITIONS AUTOMATIC TAGS ::=
BEGIN

EXTENSION ::= CLASS {&ArgumentType  ,
                     &extensionId   OBJECT IDENTIFIER
}WITH SYNTAX {ARGUMENT &ArgumentType
              IDENTIFIER &extensionId
}

Extension{EXTENSION:ExtensionSet} ::= SEQUENCE {
  extensionId        EXTENSION.&extensionId({ExtensionSet}),
  extensionArgument  EXTENSION.&ArgumentType({ExtensionSet}{@extensionId})
}

-- ExtensionSet is a set of objects of class EXTENSION.
-- Actual values of ExtensionSet are defined by the individual manufacturers. 
-- Element extensionId is constrained to be the identifier of an object from that set.
-- Element extensionArgument is constrained to be the argument type for that particular
-- object.
END -- of Manufacturer-specific-service-extension-definition

-- Generated by Asnp, the ASN.1 pretty-printer of France Telecom R&D

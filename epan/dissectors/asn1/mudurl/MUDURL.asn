--  Taken originally from draft-ietf-opsawg-mud.
--
--  Copyright (c) 2016 IETF Trust and Eliot Lear
--  All Rights Reserved.
--
-- Redistribution and use in source and binary forms, with or without
-- modification, are permitted provided that the following conditions
-- are met:
--
--  o Redistributions of source code must retain the above copyright
--    notice, this list of conditions and the following disclaimer.
--  o Redistributions in binary form must reproduce the above
--    copyright notice, this list of conditions and the following
--    disclaimer in the documentation and/or other materials provided
--    with the distribution.
--  o Neither the name of Internet Society, IETF or IETF Trust, nor
--    the names of specific contributors, may be used to endorse or
--    promote products derived from this software without specific prior
--    written permission.
--
-- THIS SOFTWARE IS PROVIDED BY THE COPYRIGHT HOLDERS AND CONTRIBUTORS
-- “AS IS” AND ANY EXPRESS OR IMPLIED WARRANTIES, INCLUDING, BUT NOT
-- LIMITED TO, THE IMPLIED WARRANTIES OF MERCHANTABILITY AND FITNESS
-- FOR A PARTICULAR PURPOSE ARE DISCLAIMED. IN NO EVENT SHALL THE
-- COPYRIGHT OWNER OR CONTRIBUTORS BE LIABLE FOR ANY DIRECT, INDIRECT,
-- INCIDENTAL, SPECIAL, EXEMPLARY, OR CONSEQUENTIAL DAMAGES
-- (INCLUDING, BUT NOT LIMITED TO, PROCUREMENT OF SUBSTITUTE GOODS OR
-- SERVICES; LOSS OF USE, DATA, OR PROFITS; OR BUSINESS INTERRUPTION)
-- HOWEVER CAUSED AND ON ANY THEORY OF LIABILITY, WHETHER IN CONTRACT,
-- STRICT LIABILITY, OR TORT (INCLUDING NEGLIGENCE OR OTHERWISE)
-- ARISING IN ANY WAY OUT OF THE USE OF THIS SOFTWARE, EVEN IF ADVISED
-- OF THE POSSIBILITY OF SUCH DAMAGE.


MUDURLExtnModule-2016 { iso(1) identified-organization(3) dod(6)
             internet(1) security(5) mechanisms(5) pkix(7) id-mod(0)
             id-mod-mudURLExtn2016(88) }

DEFINITIONS IMPLICIT TAGS ::= BEGIN

-- EXPORTS ALL --

-- EXTENSION is modified.  It would normally be taken from PKIX1Explicit-2009.
-- For reasons passing my understanding, id-pe is already understood.

IMPORTS
  EXTENSION
  FROM  AuthenticationFramework {joint-iso-itu-t ds(5) module(1)
  authenticationFramework(7) 3}
  id-pe
  FROM PKIX1Explicit-2009
          { iso(1) identified-organization(3) dod(6) internet(1)
            security(5) mechanisms(5) pkix(7) id-mod(0)
            id-mod-pkix1-explicit-02(51) };

  MUDCertExtensions EXTENSION ::= { ext-MUDURL, ... }
  ext-MUDURL EXTENSION ::= { SYNTAX MUDURLSyntax
  IDENTIFIED BY id-pe-mud-url }

  id-pe-mud-url OBJECT IDENTIFIER ::= { id-pe 25 }

  MUDURLSyntax ::= IA5String

  END

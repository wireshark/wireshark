-- ULP.asn
-- Taken from OMA UserPlane Location Protocol
-- http://member.openmobilealliance.org/ftp/Public_documents/LOC/Permanent_documents/OMA-TS-ULP-V2_0_5-20191028-A.zip

--
-- 11.1 Common Part
--
ULP DEFINITIONS AUTOMATIC TAGS ::=
BEGIN

IMPORTS
	Version, SessionID
FROM ULP-Components
  	SUPLINIT
FROM SUPL-INIT
  	SUPLSTART
FROM SUPL-START
  	SUPLRESPONSE
FROM SUPL-RESPONSE
  	SUPLPOSINIT
FROM SUPL-POS-INIT
  	SUPLPOS
FROM SUPL-POS
  	SUPLEND
FROM SUPL-END
  	SUPLAUTHREQ
FROM SUPL-AUTH-REQ
  	SUPLAUTHRESP
FROM SUPL-AUTH-RESP
  	Ver2-SUPLTRIGGEREDSTART
FROM SUPL-TRIGGERED-START
  	Ver2-SUPLTRIGGEREDRESPONSE
FROM SUPL-TRIGGERED-RESPONSE
  	Ver2-SUPLREPORT
FROM SUPL-REPORT
  	Ver2-SUPLTRIGGEREDSTOP
FROM SUPL-TRIGGERED-STOP
  	Ver2-SUPLSETINIT
FROM SUPL-SET-INIT
  	Ver2-SUPLNOTIFY
FROM SUPL-NOTIFY
  	Ver2-SUPLNOTIFYRESPONSE
FROM SUPL-NOTIFY-RESPONSE;

-- general ULP PDU layout;--
ULP-PDU ::= SEQUENCE {
  length     INTEGER(0..65535),
  version    Version,
  sessionID  SessionID,
  message    UlpMessage}

UlpMessage ::= CHOICE {
  msSUPLINIT      SUPLINIT,
  msSUPLSTART     SUPLSTART,
  msSUPLRESPONSE  SUPLRESPONSE,
  msSUPLPOSINIT   SUPLPOSINIT,
  msSUPLPOS       SUPLPOS,
  msSUPLEND       SUPLEND,
  msSUPLAUTHREQ   SUPLAUTHREQ,
  msSUPLAUTHRESP  SUPLAUTHRESP,
 ...,
  msSUPLTRIGGEREDSTART    Ver2-SUPLTRIGGEREDSTART,
  msSUPLTRIGGEREDRESPONSE Ver2-SUPLTRIGGEREDRESPONSE,
  msSUPLTRIGGEREDSTOP     Ver2-SUPLTRIGGEREDSTOP,
  msSUPLNOTIFY    	    Ver2-SUPLNOTIFY,
  msSUPLNOTIFYRESPONSE    Ver2-SUPLNOTIFYRESPONSE,
  msSUPLSETINIT   	    Ver2-SUPLSETINIT,
msSUPLREPORT    	    Ver2-SUPLREPORT}

END

-- 3GPP TS 25.331 V17.1.0 (2022-06)
--
-- 11.3	Information element definitions
--
InformationElements DEFINITIONS AUTOMATIC TAGS ::=

BEGIN

IMPORTS

	hiPDSCHidentities,
	hiPUSCHidentities,
	hiRM,
	maxAC,
	maxAdditionalMeas,
	maxAddPos,
	maxMultipleFrequencyBandsEUTRA,
	maxMultipleFrequencyBandsFDD,
	maxASC,
	maxASCmap,
	maxASCpersist,
	maxBeacons,
	maxBTs,
	maxCCTrCH,
	maxCellMeas,
	maxCellMeas-1,
	maxCellMeas-ext,
	maxCellMeas-ext2,
	maxCellMeas-ext-1,
	maxCellMeasOnSecULFreq,
	maxCellMeasOnSecULFreq-1,
	maxCNdomains,
	maxCommonHRNTI,
	maxCommonQueueID,
	maxCPCHsets,
	maxDedicatedCSGFreq,
	maxDPCH-DLchan,
	maxDPDCH-UL,
	maxDRACclasses,
	maxE-DCHMACdFlow,
	maxE-DCHMACdFlow-1,
	maxEDCHs,
	maxEDCHs-1,
	maxEDCHTxPattern-TDD128,
	maxEDCHTxPattern-TDD128-1,
	maxERNTIgroup,
	maxERNTIperGroup,
	maxERUCCH,
	maxEUTRACellPerFreq,
	maxEUTRATargetFreqs,
	maxExcludedDetectedSetCells,
	maxFACHPCH,
	maxFreq,
	maxFreqBandsEUTRA,
	maxFreqBandsEUTRA-ext,
	maxFreqBandsFDD,
	maxFreqBandsFDD2,
	maxFreqBandsFDD3,
	maxFreqBandsFDD-ext,
	maxFreqBandsFDD-ext2,
	maxFreqBandsFDD-ext3,
	maxFreqBandsIndicatorSupport,
	maxFreqBandsTDD,
	maxFreqBandsTDD-ext,
	maxFreqBandsGSM,
	maxFreqMeasWithoutCM,
	maxGANSS,
	maxGANSS-1,
	maxGANSSSat,
	maxGANSSSat-1,
	maxGERAN-SI,
	maxHNBNameSize,
	maxHProcesses,
	maxHSDSCHTBIndex,
	maxHSDSCHTBIndex-tdd384,
	maxHSSCCHs,
	maxHSSCCHs-1,
	maxHSSICH-TDD128,
	maxHSSICH-TDD128-1,
	maxHS-SCCHLessTrBlk,
	maxIGPInfo,
	maxInterSysMessages,
	maxLoCHperRLC,
	maxLoggedMeasReport,
	maxnumLoggedMeas,
	maxMAC-d-PDUsizes,
	maxMBMS-CommonCCTrCh,
	maxMBMS-CommonPhyCh,
	maxMBMS-CommonRB,
	maxMBMS-CommonTrCh,
	maxMBMS-Freq,
	maxMBMS-L1CP,
	maxMBMSservCount,
	maxMBMSservModif,
	maxMBMSservSched,
	maxMBMSservSelect,
	maxMBMSservUnmodif,
	maxMBMSTransmis,
	maxMBSFNClusters,
	maxMeasCSGRange,
	maxMeasEvent,
	maxMeasEventOnSecULFreq,
	maxMeasIdentity,
	maxMeasIntervals,
	maxMeasParEvent,
	maxNonContiguousMultiCellCombinations,
	maxMeasOccasionPattern,
	maxMeasOccasionPattern-1,
	maxNumAccessGroups,
	maxNumAcdcCategory,
	maxNumCDMA2000Freqs,
	maxNumE-AGCH,
	maxNumE-HICH,
	maxNumEUTRAFreqs,
	maxNumEUTRAFreqs-FACH,
	maxNumEUTRAFreqs-FACH-ext,
	maxNumFDDFreqs,
	maxNumGSMCellGroup,
	maxNumGSMFreqRanges,
	maxGSMTargetCells,
	maxNumMDTPLMN,
	maxNumTDDFreqs,
	maxNumANRLoggedItems,
	maxOtherRAT,
	maxOtherRAT-16,
	maxPage1,
	maxPCPCH-APsig,
	maxPCPCH-APsubCh,
	maxPCPCH-CDsig,
	maxPCPCH-CDsubCh,
	maxPCPCH-SF,
	maxPCPCHs,
	maxPDCPAlgoType,
	maxPDSCH,
	maxPDSCH-TFCIgroups,
	maxPRACH,
	maxPRACH-EUL,
	maxPRACH-FPACH,
	maxPredefConfig,
	maxOtherStateConfig,
	maxOtherStateConfig-1,
	maxPrio,
	maxPrio-1,
	maxPrio-ext,
	maxPUSCH,
	maxQueueIDs,
	maxRABsetup,
	maxRAT,
	maxRB,
	maxRBallRABs,
	maxRBperTrCh,
	maxRBMuxOptions,
	maxRBperRAB,
	maxReportedEUTRAFreqs,
	maxReportedEUTRAFreqs-ext,
	maxReportedEUTRACellPerFreq,
	maxReportedGSMCells,
	maxRetrievConfig,
	maxRetrievConfig-1,
	maxRLCPDUsizePerLogChan,
	maxRMPfrequencies,
	maxSRBsetup,
	maxRL,
	maxRL-1,
	maxEDCHRL,
	maxEDCHRL-1,
	maxROHC-PacketSizes-r4,
	maxROHC-Profile-r4,
	maxRxPatternForHSDSCH-TDD128,
	maxRxPatternForHSDSCH-TDD128-1,
	maxSat,
	maxSatClockModels,
	maxSCCPCH,
	maxSgnType,
	maxSIB,
	maxSIB2,
	maxSIB-FACH,
	maxSIrequest,
	maxSystemCapability,
	maxTDD128Carrier,
	maxTDD128Carrier-1,
	maxTbsForHSDSCH-TDD128,
	maxTbsForHSDSCH-TDD128-1,
	maxTF,
	maxTF-CPCH,
	maxTFC,
	maxTFCsub,
	maxTFCI-2-Combs,
	maxTGPS,
	maxTrCH,
	maxTrCHConcat,
	maxTrCHpreconf,
	maxTS,
	maxTS-1,
	maxTS-2,
	maxTS-LCR,
	maxTS-LCR-1,
	maxURA,
	maxURNTI-Group,
	maxWLANs,
	maxWLANID
FROM Constant-definitions;

-- ***************************************************
--
--     CORE NETWORK INFORMATION ELEMENTS (10.3.1)
--
-- ***************************************************

Ansi-41-IDNNS ::=							BIT STRING (SIZE (14))

CN-DomainIdentity ::=				ENUMERATED {
										cs-domain,
										ps-domain }

CN-DomainInformation ::=			SEQUENCE {
	cn-DomainIdentity					CN-DomainIdentity,
	cn-DomainSpecificNAS-Info			NAS-SystemInformationGSM-MAP
}

CN-DomainInformationFull ::=		SEQUENCE {
	cn-DomainIdentity					CN-DomainIdentity,
	cn-DomainSpecificNAS-Info			NAS-SystemInformationGSM-MAP,
	cn-DRX-CycleLengthCoeff				CN-DRX-CycleLengthCoefficient
}

CN-DomainInformationList ::=		SEQUENCE (SIZE (1..maxCNdomains)) OF
										CN-DomainInformation

CN-DomainInformationListFull ::=	SEQUENCE (SIZE (1..maxCNdomains)) OF
										CN-DomainInformationFull

CN-DomainSysInfo ::=				SEQUENCE {
	cn-DomainIdentity					CN-DomainIdentity,
	cn-Type								CHOICE {
		gsm-MAP								NAS-SystemInformationGSM-MAP,
		ansi-41								NAS-SystemInformationANSI-41
	},
	cn-DRX-CycleLengthCoeff				CN-DRX-CycleLengthCoefficient
}

CN-DomainSysInfoList ::=			SEQUENCE (SIZE (1..maxCNdomains)) OF
										CN-DomainSysInfo

CN-InformationInfo ::= 				SEQUENCE {
	plmn-Identity						PLMN-Identity						OPTIONAL,
	cn-CommonGSM-MAP-NAS-SysInfo		NAS-SystemInformationGSM-MAP		OPTIONAL,
	cn-DomainInformationList			CN-DomainInformationList			OPTIONAL
}

CN-InformationInfo-r6 ::= 			SEQUENCE {
	plmn-Identity						PLMN-Identity						OPTIONAL,
	cn-CommonGSM-MAP-NAS-SysInfo		NAS-SystemInformationGSM-MAP		OPTIONAL,
	cn-DomainInformationList			CN-DomainInformationList			OPTIONAL,
	primary-plmn-Identity				PLMN-Identity						OPTIONAL
}

CN-InformationInfoFull ::= 			SEQUENCE {
	plmn-Identity						PLMN-Identity						OPTIONAL,
	cn-CommonGSM-MAP-NAS-SysInfo		NAS-SystemInformationGSM-MAP		OPTIONAL,
	cn-DomainInformationListFull		CN-DomainInformationListFull		OPTIONAL
}

Digit ::=							INTEGER (0..9)

DomainSpecificEAB-Parameters ::= 	SEQUENCE {
	cs-DomainSpecificEAB-Parameters		EAB-Configuration					OPTIONAL,
	ps-DomainSpecificEAB-Parameters		EAB-Configuration					OPTIONAL,
	commonEAB-Parameters				EAB-Configuration				OPTIONAL
}

EAB-AccessClassBarredList ::=		SEQUENCE (SIZE (10)) OF
										AccessClassBarred

EAB-Configuration ::= 				SEQUENCE {
	eab-Category						ENUMERATED {a,b,c},
	eab-AccessClassBarredList			EAB-AccessClassBarredList
}

EAB-Parameters ::= 		CHOICE {
	eab-ParametersPerPLMN-List			EAB-ParametersPerPLMN-List,
	eab-ParametersForAll				DomainSpecificEAB-Parameters
}

EAB-ParametersPerPLMN ::=			SEQUENCE {
	domainSpecificEAB-Parameters		DomainSpecificEAB-Parameters		OPTIONAL
}

EAB-ParametersPerPLMN-List ::= 		SEQUENCE (SIZE (1..6)) OF EAB-ParametersPerPLMN

Ec-N0forANR ::= SEQUENCE {
	ec-N0								INTEGER (-24..0)					OPTIONAL
}

Gsm-map-IDNNS ::=							SEQUENCE {
	routingbasis									CHOICE {
		localPTMSI										SEQUENCE {
			routingparameter								RoutingParameter
		},
		tMSIofsamePLMN									SEQUENCE {
			routingparameter								RoutingParameter
		},
		tMSIofdifferentPLMN								SEQUENCE {
			routingparameter								RoutingParameter
		},
		iMSIresponsetopaging							SEQUENCE {
			routingparameter								RoutingParameter
		},
		iMSIcauseUEinitiatedEvent						SEQUENCE {
			routingparameter								RoutingParameter
		},
		iMEI											SEQUENCE {
			routingparameter								RoutingParameter
		},
		spare2											SEQUENCE {
			routingparameter								RoutingParameter
		},
		spare1											SEQUENCE {
			routingparameter								RoutingParameter
		}
	},
	-- dummy is not used in this version of the specification and
	-- it should be ignored by the receiver.
	dummy									BOOLEAN
}

IMEI ::=							SEQUENCE (SIZE (15)) OF
										IMEI-Digit

IMEI-Digit ::=						INTEGER (0..15)

IMSI-GSM-MAP ::=					SEQUENCE (SIZE (6..21)) OF
										Digit

IntraDomainNasNodeSelector ::=					SEQUENCE {
	version											CHOICE {
		release99										SEQUENCE {
			cn-Type											CHOICE {
				gsm-Map-IDNNS									Gsm-map-IDNNS,
				ansi-41-IDNNS									Ansi-41-IDNNS
			}
		},
		later											SEQUENCE {
			futurecoding									BIT STRING (SIZE (15))
		}
	}
}

LAI ::=								SEQUENCE {
	plmn-Identity						PLMN-Identity,
	lac									BIT STRING (SIZE (16))
}

LocationRegistrationAccessClassBarredList ::= SEQUENCE (SIZE (15)) OF
												AccessClassBarred

LocationRegistrationParameters ::=	CHOICE {
	noRestriction						NULL,
	restriction							LocationRegistrationAccessClassBarredList
}

MCC ::=								SEQUENCE (SIZE (3)) OF
										Digit

MNC ::=								SEQUENCE (SIZE (2..3)) OF
										Digit

MultiplePLMN-List-r6 ::=			SEQUENCE {
	mibPLMN-Identity					BOOLEAN,
	multiplePLMNs						SEQUENCE (SIZE (1..5)) OF
											PLMN-IdentityWithOptionalMCC-r6
}

NAS-Message ::=						OCTET STRING (SIZE (1..4095))

NAS-Synchronisation-Indicator ::=	BIT STRING(SIZE(4))

NAS-SystemInformationGSM-MAP ::= 	OCTET STRING (SIZE (1..8))

P-TMSI-GSM-MAP ::=					BIT STRING (SIZE (32))

PagingPermissionWithAccessControlForSharedNetwork ::= CHOICE {
	pagingPermissionWithAccessControlList	PagingPermissionWithAccessControlList,
	pagingPermissionWithAccessControlForAll	PagingPermissionWithAccessControlParameters
}

PagingPermissionWithAccessControlList ::= SEQUENCE {
	pagingPermissionWithAccessControlParametersForOperator1
									PagingPermissionWithAccessControlParameters		OPTIONAL,
	pagingPermissionWithAccessControlParametersForOperator2
									PagingPermissionWithAccessControlParameters		OPTIONAL,
	pagingPermissionWithAccessControlParametersForOperator3
									PagingPermissionWithAccessControlParameters		OPTIONAL,
	pagingPermissionWithAccessControlParametersForOperator4
									PagingPermissionWithAccessControlParameters		OPTIONAL,
	pagingPermissionWithAccessControlParametersForOperator5
									PagingPermissionWithAccessControlParameters		OPTIONAL
}

PagingPermissionWithAccessControlParameters ::= SEQUENCE {
	pagingResponseRestrictionIndicator			ENUMERATED {all, cS, pS, none},
	locationRegistrationRestrictionIndicator	ENUMERATED {all, cS, pS},
	locationRegistration						LocationRegistrationParameters
}

PagingRecordTypeID ::=				ENUMERATED {
										imsi-GSM-MAP,
										tmsi-GSM-MAP-P-TMSI,
										imsi-DS-41,
										tmsi-DS-41 }

PLMN-Identity ::=					SEQUENCE {
	mcc									MCC,
	mnc									MNC
}

PLMN-IdentityWithOptionalMCC-r6 ::=	SEQUENCE {
	mcc									MCC						OPTIONAL,
	mnc									MNC
}

PLMN-Type ::=						CHOICE {
	gsm-MAP								SEQUENCE {
		plmn-Identity						PLMN-Identity
	},
	ansi-41							SEQUENCE {
		p-REV							P-REV,
		min-P-REV						Min-P-REV,
		sid								SID,
		nid								NID
	},
	gsm-MAP-and-ANSI-41				SEQUENCE {
		plmn-Identity					PLMN-Identity,
		p-REV							P-REV,
		min-P-REV						Min-P-REV,
		sid								SID,
		nid								NID
	},
	spare							NULL
}

RAB-Identity ::=					CHOICE {
	gsm-MAP-RAB-Identity				BIT STRING (SIZE (8)),
	ansi-41-RAB-Identity				BIT STRING (SIZE (8))
}

RAI ::=								SEQUENCE {
	lai									LAI,
	rac									RoutingAreaCode
}

RoutingAreaCode ::=					BIT STRING (SIZE (8))

RoutingParameter ::=							BIT STRING (SIZE (10))

TMSI-GSM-MAP ::=					BIT STRING (SIZE (32))

-- ***************************************************
--
--     UTRAN MOBILITY INFORMATION ELEMENTS (10.3.2)
--
-- ***************************************************

AccessClassBarred ::=				ENUMERATED {
										barred, notBarred }

AccessClassBarredList ::=			SEQUENCE (SIZE (maxAC)) OF
										AccessClassBarred

AllowedIndicator ::=				ENUMERATED {
										allowed, notAllowed }

CellAccessRestriction ::=			SEQUENCE {
	cellBarred							CellBarred,
	cellReservedForOperatorUse			ReservedIndicator,
	cellReservationExtension			ReservedIndicator,
	-- NOTE: IE accessClassBarredList should not be included if the IE CellAccessRestriction
	-- is included in the IE SysInfoType4
	accessClassBarredList				AccessClassBarredList				OPTIONAL
}

CellAccessRestriction-v870ext ::=	SEQUENCE {
	cellReservedForCSG					ENUMERATED { true }				OPTIONAL
}

CellBarred ::=						CHOICE {
	barred								SEQUENCE {
		intraFreqCellReselectionInd			AllowedIndicator,
		t-Barred							T-Barred
	},
	notBarred							NULL
}

CellIdentity ::=					BIT STRING (SIZE (28))

CellIdentity-PerRL-List ::=			SEQUENCE (SIZE (1..maxRL)) OF CellIdentity

CellIDListItem ::= SEQUENCE {
	cell-Identity		CellIdentity,
	plmn-Identity 		PLMN-Identity 		OPTIONAL
}

CellSelectReselectInfoSIB-3-4 ::=	SEQUENCE {
	mappingInfo							MappingInfo							OPTIONAL,
	cellSelectQualityMeasure			CHOICE {
		cpich-Ec-N0							SEQUENCE {
			-- Default value for q-HYST-2-S is q-HYST-1-S
			q-HYST-2-S							Q-Hyst-S					OPTIONAL
		},
		cpich-RSCP							NULL
	},
	modeSpecificInfo					CHOICE {
		fdd									SEQUENCE {
			s-Intrasearch						S-SearchQual				OPTIONAL,
			s-Intersearch						S-SearchQual				OPTIONAL,
			s-SearchHCS							S-SearchRXLEV				OPTIONAL,
			rat-List							RAT-FDD-InfoList			OPTIONAL,
			q-QualMin							Q-QualMin,
			q-RxlevMin							Q-RxlevMin
		},
		tdd									SEQUENCE {
			s-Intrasearch						S-SearchRXLEV				OPTIONAL,
			s-Intersearch						S-SearchRXLEV				OPTIONAL,
			s-SearchHCS							S-SearchRXLEV				OPTIONAL,
			rat-List							RAT-TDD-InfoList			OPTIONAL,
			q-RxlevMin							Q-RxlevMin
		}
	},
	q-Hyst-l-S							Q-Hyst-S,
	t-Reselection-S						T-Reselection-S,
	hcs-ServingCellInformation			HCS-ServingCellInformation			OPTIONAL,
	maxAllowedUL-TX-Power				MaxAllowedUL-TX-Power
}

CSG-DedicatedFrequencyInfoList ::=	SEQUENCE (SIZE (1..maxDedicatedCSGFreq)) OF
										FrequencyInfo

CSG-Identity ::=					BIT STRING (SIZE (27))

CSG-PSCSplitInfo ::=				SEQUENCE {
	-- Actual value = IE value * 8
	startPSC							INTEGER (0..63),
	numberOfPSCs						ENUMERATED { psc5, psc10, psc15, psc20,
											psc30, psc40, psc50, psc64, psc80,
											psc120, psc160, psc256, alltheRest,
											spare3, spare2, spare1 },
	-- Actual value = IE value * 8
	pscRange2Offset						INTEGER (1..63)						OPTIONAL
}

DedicatedWLANOffloadInformation ::=	SEQUENCE {
	configurationInfo					CHOICE {
		continue 							NULL,
		newConfiguration					SEQUENCE {
			t-330								T-330								OPTIONAL,
			wlanOffloadInformation				WLANOffloadInformation
		}
	}
}

DomainSpecificAccessRestrictionForSharedNetwork-v670ext ::= CHOICE {
		domainSpecificAccessRestictionList			DomainSpecificAccessRestrictionList-v670ext,
		domainSpecificAccessRestictionParametersForAll
													DomainSpecificAccessRestrictionParam-v670ext
}

DomainSpecificAccessRestrictionList-v670ext ::= SEQUENCE {
		domainSpecificAccessRestrictionParametersForOperator1
									DomainSpecificAccessRestrictionParam-v670ext	OPTIONAL,
		domainSpecificAccessRestrictionParametersForOperator2
									DomainSpecificAccessRestrictionParam-v670ext	OPTIONAL,
		domainSpecificAccessRestrictionParametersForOperator3
									DomainSpecificAccessRestrictionParam-v670ext	OPTIONAL,
		domainSpecificAccessRestrictionParametersForOperator4
									DomainSpecificAccessRestrictionParam-v670ext	OPTIONAL,
		domainSpecificAccessRestrictionParametersForOperator5
									DomainSpecificAccessRestrictionParam-v670ext	OPTIONAL
}

DomainSpecificAccessRestrictionParam-v670ext ::= SEQUENCE {
		cSDomainSpecificAccessRestriction		DomainSpecificAccessRestriction-v670ext,
		pSDomainSpecificAccessRestriction		DomainSpecificAccessRestriction-v670ext
}

DomainSpecificAccessRestriction-v670ext ::= CHOICE {
		noRestriction		NULL,
		restriction			SEQUENCE {
			domainSpecficAccessClassBarredList		AccessClassBarredList	OPTIONAL
		}
}

MapParameter ::=					INTEGER (0..127)

Mapping ::=							SEQUENCE {
	rat									RAT,
	mappingFunctionParameterList		MappingFunctionParameterList
}

Mapping-LCR-r4 ::=					SEQUENCE {
	mappingFunctionParameterList		MappingFunctionParameterList
}

MappingFunctionParameter ::=		SEQUENCE {
	functionType						MappingFunctionType,
	mapParameter1						MapParameter						OPTIONAL,
	mapParameter2						MapParameter,
	-- The presence of upperLimit is conditional on the number of repetition
	upperLimit							UpperLimit							OPTIONAL
}

MappingFunctionParameterList ::= 	SEQUENCE (SIZE (1..maxMeasIntervals)) OF
										MappingFunctionParameter

MappingFunctionType ::=				ENUMERATED {
										linear,
										functionType2,
										functionType3,
										functionType4 }

-- In MappingInfo list, mapping for FDD and 3.84Mcps TDD is defined.
-- For 1.28Mcps TDD, Mapping-LCR-r4 is used instead.
MappingInfo ::=						SEQUENCE (SIZE (1..maxRAT)) OF
										Mapping

OccurrenceSequenceNumberOfPICH ::=	INTEGER (1..maxSCCPCH)

DedicatedPriorityInformation ::=	SEQUENCE {
	action								CHOICE {
		clearDedicatedPriorities			NULL,
		configureDedicatedPriorities		SEQUENCE {
			t-322								T-322							OPTIONAL,
			priorityLevelList					PriorityLevelList				OPTIONAL,
			eutraDetection						BOOLEAN
		}
	}
}

DedicatedPriorityInformation-r11 ::=	SEQUENCE {
	action								CHOICE {
		clearDedicatedPriorities			NULL,
		configureDedicatedPriorities		SEQUENCE {
			t-322								T-322							OPTIONAL,
			priorityLevelList					PriorityLevelList-r11			OPTIONAL,
			eutraDetection						BOOLEAN
		}
	}
}

DedicatedPriorityInformation-r13 ::=	SEQUENCE {
	action								CHOICE {
		clearDedicatedPriorities			NULL,
		configureDedicatedPriorities		SEQUENCE {
			t-322								T-322							OPTIONAL,
			priorityLevelList					PriorityLevelList-r13			OPTIONAL,
			eutraDetection						BOOLEAN
		}
	}
}

PriorityLevel ::=					SEQUENCE {
	priority							INTEGER (0..maxPrio-1)					OPTIONAL,
	radioAccessTechnology				CHOICE {
		utraFDD								SEQUENCE (SIZE (1..maxNumFDDFreqs)) OF SEQUENCE{
			uarfcn								UARFCN
		},
		utraTDD								SEQUENCE (SIZE (1..maxNumTDDFreqs)) OF SEQUENCE{
			uarfcn								UARFCN
		},
		eutra								SEQUENCE (SIZE (1..maxNumEUTRAFreqs)) OF SEQUENCE{
			earfcn								EARFCN
		},
		gsm									SEQUENCE {
			gsm-CellGroup						GSM-CellGroup
		}
	}
}

PriorityLevel-r11 ::=					SEQUENCE {
	priority							INTEGER (0..maxPrio-1)					OPTIONAL,
	radioAccessTechnology				CHOICE {
		utraFDD								SEQUENCE (SIZE (1..maxNumFDDFreqs)) OF SEQUENCE{
			uarfcn								UARFCN
		},
		utraTDD								SEQUENCE (SIZE (1..maxNumTDDFreqs)) OF SEQUENCE{
			uarfcn								UARFCN
		},
		eutra								SEQUENCE (SIZE (1..maxNumEUTRAFreqs)) OF
												EARFCNRange,
		gsm									SEQUENCE {
			gsm-CellGroup						GSM-CellGroup
		}
	}
}

PriorityLevel-r13 ::=					SEQUENCE {
	priority							INTEGER (0..maxPrio-1)					OPTIONAL,
	subpriority						ENUMERATED {oDot2,oDot4,oDot6,oDot8}		OPTIONAL,	radioAccessTechnology				CHOICE {
		utraFDD								SEQUENCE (SIZE (1..maxNumFDDFreqs)) OF SEQUENCE{
			uarfcn								UARFCN
		},
		utraTDD								SEQUENCE (SIZE (1..maxNumTDDFreqs)) OF SEQUENCE{
			uarfcn								UARFCN
		},
		eutra								SEQUENCE (SIZE (1..maxNumEUTRAFreqs)) OF
												EARFCNRange,
		gsm									SEQUENCE {
			gsm-CellGroup						GSM-CellGroup
		}
	}
}

PriorityLevelList ::=				SEQUENCE (SIZE (1..maxPrio)) OF
										PriorityLevel

PriorityLevelList-r11 ::=			SEQUENCE (SIZE (1..maxPrio)) OF
										PriorityLevel-r11

PriorityLevelList-r13 ::=			SEQUENCE (SIZE (1..maxPrio-ext)) OF
										PriorityLevel-r13


-- Actual value Q-Hyst-S = IE value * 2
Q-Hyst-S ::=						INTEGER (0..20)

Q-Hyst-S-Fine ::= INTEGER (0..40)

RAT ::=								ENUMERATED {
										utra-FDD,
										utra-TDD,
										gsm,
										cdma2000 }

RAT-FDD-Info ::=					SEQUENCE {
	rat-Identifier						RAT-Identifier,
	s-SearchRAT							S-SearchQual,
	s-HCS-RAT							S-SearchRXLEV							OPTIONAL,
	s-Limit-SearchRAT					S-SearchQual
}

RAT-FDD-InfoList ::=				SEQUENCE (SIZE (1..maxOtherRAT)) OF
										RAT-FDD-Info

RAT-Identifier ::=					ENUMERATED {
										gsm, cdma2000 }

RAT-TDD-Info ::=					SEQUENCE {
	rat-Identifier						RAT-Identifier,
	s-SearchRAT							S-SearchRXLEV,
	s-HCS-RAT							S-SearchRXLEV						OPTIONAL,
	s-Limit-SearchRAT					S-SearchRXLEV
}

RAT-TDD-InfoList ::=				SEQUENCE (SIZE (1..maxOtherRAT)) OF
										RAT-TDD-Info

ReservedIndicator ::=				ENUMERATED {
										reserved,
										notReserved }

-- Actual value S-SearchQual = IE value * 2
S-SearchQual ::=						INTEGER (-16..10)

-- Actual value S-SearchRXLEV = (IE value * 2) + 1
S-SearchRXLEV ::=						INTEGER (-53..45)

-- Actual value ScalingFactor = IE value * 0.1
SpeedDependentScalingFactor ::=		INTEGER (0..10)

T-Barred ::=						ENUMERATED {
										s10, s20, s40, s80,
										s160, s320, s640, s1280 }

T-Reselection-S ::=					INTEGER (0..31)

-- Actual value T-Reselection-S-Fine = IE value * 0.2
T-Reselection-S-Fine ::=			INTEGER (0..31)

-- Actual value ScalingFactor = IE value * 0.25
TreselectionScalingFactor ::=		INTEGER (4..19)

-- Actual value ScalingFactor2 = IE value * 0.25
TreselectionScalingFactor2 ::=		INTEGER (1..16)

-- For UpperLimit, the used range depends on the RAT used.
UpperLimit ::=						INTEGER (1..91)

URA-Identity ::=					BIT STRING (SIZE (16))

URA-IdentityList ::=				SEQUENCE (SIZE (1..maxURA)) OF
										URA-Identity

-- ***************************************************
--
--     USER EQUIPMENT INFORMATION ELEMENTS (10.3.3)
--
-- ***************************************************

AccessGroupIdentity ::=				INTEGER (0..15)

AccessStratumReleaseIndicator ::=	ENUMERATED {
										rel-4, rel-5, rel-6, rel-7, rel-8,
										rel-9, rel-10, rel-11, rel-12,
										rel-13, rel-14, rel-15, rel-16, spare3,
										spare2, spare1 }

-- TABULAR : for ActivationTime, value 'now' always appear as default, and is encoded
-- by absence of the field
ActivationTime ::=					INTEGER (0..255)

BackoffControlParams ::=			SEQUENCE {
	n-AP-RetransMax						N-AP-RetransMax,
	n-AccessFails						N-AccessFails,
	nf-BO-NoAICH						NF-BO-NoAICH,
	ns-BO-Busy							NS-BO-Busy,
	nf-BO-AllBusy						NF-BO-AllBusy,
	nf-BO-Mismatch						NF-BO-Mismatch,
	t-CPCH								T-CPCH
}

BandComb	::=						INTEGER (1..256)

C-RNTI ::=							BIT STRING (SIZE (16))

CapabilityUpdateRequirement ::=		SEQUENCE {
	ue-RadioCapabilityFDDUpdateRequirement	BOOLEAN,
	-- ue-RadioCapabilityTDDUpdateRequirement is for 3.84Mcps TDD update requirement
	ue-RadioCapabilityTDDUpdateRequirement	BOOLEAN,
	systemSpecificCapUpdateReqList		SystemSpecificCapUpdateReqList		OPTIONAL
}

CapabilityUpdateRequirement-r4-ext ::= SEQUENCE {
	ue-RadioCapabilityUpdateRequirement-TDD128	BOOLEAN
}

CapabilityUpdateRequirement-r4 ::=	SEQUENCE {
	ue-RadioCapabilityFDDUpdateRequirement-FDD	BOOLEAN,
	ue-RadioCapabilityTDDUpdateRequirement-TDD384	BOOLEAN,
	ue-RadioCapabilityTDDUpdateRequirement-TDD128	BOOLEAN,
	systemSpecificCapUpdateReqList		SystemSpecificCapUpdateReqList		OPTIONAL
}

CapabilityUpdateRequirement-r5 ::=	SEQUENCE {
	ue-RadioCapabilityFDDUpdateRequirement-FDD		BOOLEAN,
	ue-RadioCapabilityTDDUpdateRequirement-TDD384	BOOLEAN,
	ue-RadioCapabilityTDDUpdateRequirement-TDD128	BOOLEAN,
	systemSpecificCapUpdateReqList		SystemSpecificCapUpdateReqList-r5		OPTIONAL
}

CapabilityUpdateRequirement-v770ext ::= SEQUENCE {
	ue-RadioCapabilityTDDUpdateRequirement-TDD768	BOOLEAN
}

CapabilityUpdateRequirement-r7 ::=	SEQUENCE {
	ue-RadioCapabilityFDDUpdateRequirement-FDD		BOOLEAN,
	ue-RadioCapabilityTDDUpdateRequirement-TDD384	BOOLEAN,
	ue-RadioCapabilityTDDUpdateRequirement-TDD768	BOOLEAN,
	ue-RadioCapabilityTDDUpdateRequirement-TDD128	BOOLEAN,
	systemSpecificCapUpdateReqList		SystemSpecificCapUpdateReqList-r5		OPTIONAL
}

CapabilityUpdateRequirement-v860ext ::= SEQUENCE {
	-- If both IEs are present, the elements in the IE SystemSpecificCapUpdateReqList-r8
	-- shall be appended to the elements in the IE SystemSpecificCapUpdateReqList
	systemSpecificCapUpdateReqList		SystemSpecificCapUpdateReqList-r8		OPTIONAL
}

CapabilityUpdateRequirement-r8 ::=	SEQUENCE {
	ue-RadioCapabilityFDDUpdateRequirement-FDD		BOOLEAN,
	ue-RadioCapabilityTDDUpdateRequirement-TDD384	BOOLEAN,
	ue-RadioCapabilityTDDUpdateRequirement-TDD768	BOOLEAN,
	ue-RadioCapabilityTDDUpdateRequirement-TDD128	BOOLEAN,
	systemSpecificCapUpdateReqList		SystemSpecificCapUpdateReqList-r8		OPTIONAL
}

CapabilityUpdateRequirement-vaj0ext ::= SEQUENCE {
	eUTRAbandSpecificCapUpdateReqList	EUTRAbandSpecificCapUpdateReqList
}

CapabilityUpdateRequirement-r12 ::=	SEQUENCE {
	ue-RadioCapabilityFDDUpdateRequirement-FDD		BOOLEAN,
	ue-RadioCapabilityTDDUpdateRequirement-TDD384	BOOLEAN,
	ue-RadioCapabilityTDDUpdateRequirement-TDD768	BOOLEAN,
	ue-RadioCapabilityTDDUpdateRequirement-TDD128	BOOLEAN,
	systemSpecificCapUpdateReqList		SystemSpecificCapUpdateReqList-r8		OPTIONAL,
	eUTRAbandSpecificCapUpdateReqList	EUTRAbandSpecificCapUpdateReqList		OPTIONAL
}


-- If the IE CellUpdateCause has the value 'cellUpdateCause-ext', the actual value is
-- defined in the IE CellUpdateCause-ext.
CellUpdateCause ::=					ENUMERATED {
										cellReselection,
										periodicalCellUpdate,
										uplinkDataTransmission,
										utran-pagingResponse,
										re-enteredServiceArea,
										radiolinkFailure,
										rlc-unrecoverableError,
										cellUpdateCause-ext }

-- The IE CellUpdateCause-ext shall be present, if the IE CellUpdateCause has the
-- value 'cellUpdateCause-ext'.
-- dummy is not used in this version of the specification, it should not be sent
-- and if received it should be ignored by the receiver.
CellUpdateCause-ext ::=				ENUMERATED {
										mbms-Reception,
										mbms-PTP-RB-Request,
										dummy,
										cellUpdateCause-ext2 }

-- The IE CellUpdateCause-ext2 shall be present, if the IE CellUpdateCause-ext has the
-- value 'cellUpdateCause-ext2'.

CellUpdateCause-ext2 ::=			ENUMERATED {
										applicationLayerMeasurementReportAvailable,
										spare3,
										spare2,
										spare1 }

ChipRateCapability ::=				ENUMERATED {
										mcps3-84, mcps1-28 }

CipheringAlgorithm ::=				ENUMERATED {
										uea0, uea1 }

CipheringAlgorithm-r7 ::=			ENUMERATED {
										uea0, uea1, uea2 }

CipheringModeCommand ::=			CHOICE {
	startRestart						CipheringAlgorithm,
	dummy								NULL
}

CipheringModeCommand-r7 ::=			SEQUENCE {
	startRestart						CipheringAlgorithm-r7
}

CipheringModeInfo ::=				SEQUENCE {
	-- TABULAR: The ciphering algorithm is included in the CipheringModeCommand.
	cipheringModeCommand				CipheringModeCommand,
	activationTimeForDPCH				ActivationTime						OPTIONAL,
	rb-DL-CiphActivationTimeInfo		RB-ActivationTimeInfoList			OPTIONAL
}

CipheringModeInfo-r7 ::=			SEQUENCE {
	-- TABULAR: The ciphering algorithm is included in the CipheringModeCommand.
	cipheringModeCommand				CipheringModeCommand-r7,
	activationTimeForDPCH				ActivationTime						OPTIONAL,
	rb-DL-CiphActivationTimeInfo		RB-ActivationTimeInfoList			OPTIONAL
}

CN-DRX-CycleLengthCoefficient ::=	INTEGER (6..9)

CN-PagedUE-Identity ::=				CHOICE {
	imsi-GSM-MAP						IMSI-GSM-MAP,
	tmsi-GSM-MAP						TMSI-GSM-MAP,
	p-TMSI-GSM-MAP						P-TMSI-GSM-MAP,
	imsi-DS-41							IMSI-DS-41,
	tmsi-DS-41							TMSI-DS-41,
	spare3								NULL,
	spare2								NULL,
	spare1								NULL
}

CompressedModeMeasCapability ::=	SEQUENCE {
	fdd-Measurements					BOOLEAN,
	-- TABULAR: The IEs tdd-Measurements, gsm-Measurements and multiCarrierMeasurements
	-- are made optional since they are conditional based on another information element.
	-- Their absence corresponds to the case where the condition is not true.
	-- The IE 'tdd-Measurements' applies to either or both TDD 3.84 Mcps and TDD 7.68 Mcps,
	-- depending on the RF capability conditions.
	tdd-Measurements					BOOLEAN								OPTIONAL,
	gsm-Measurements					GSM-Measurements					OPTIONAL,
	multiCarrierMeasurements			BOOLEAN								OPTIONAL
}

CompressedModeMeasCapability-LCR-r4 ::=	SEQUENCE {
	tdd128-Measurements						BOOLEAN							OPTIONAL
}

CompressedModeMeasCapability-v860ext ::= SEQUENCE {
	adjacentFrequencyMeasurements		ENUMERATED { true }					OPTIONAL
}

CompressedModeMeasCapability-v920ext ::= SEQUENCE {
	interBandMeasurements				ENUMERATED { true }					OPTIONAL
}

CompressedModeMeasCapability-va40ext ::= SEQUENCE {
	enhancedInterFrequencyMeasurements	ENUMERATED { true }					OPTIONAL,
	freqSpecificCompressedMode			ENUMERATED { true }					OPTIONAL
}

CompressedModeMeasCapabEUTRA ::=	SEQUENCE {
	radioFrequencyBandEUTRA				RadioFrequencyBandEUTRA,
	compressedMode						BOOLEAN
}

CompressedModeMeasCapabEUTRAExt ::=SEQUENCE {
	radioFrequencyBandEUTRA				RadioFrequencyBandEUTRAExt
}

CompressedModeMeasCapabEUTRAExt2 ::=SEQUENCE {
	radioFrequencyBandEUTRA				RadioFrequencyBandEUTRAExt2,
	compressedMode						BOOLEAN
}

CompressedModeMeasCapabEUTRAList ::=	SEQUENCE (SIZE (1..maxFreqBandsEUTRA)) OF
											CompressedModeMeasCapabEUTRA

CompressedModeMeasCapabEUTRAList2 ::=	SEQUENCE (SIZE (1..maxFreqBandsEUTRA)) OF
											CompressedModeMeasCapabEUTRAExt

CompressedModeMeasCapabEUTRAList3 ::=	SEQUENCE (SIZE (1..maxFreqBandsEUTRA-ext)) OF
											CompressedModeMeasCapabEUTRAExt2

CompressedModeMeasCapabFDDList ::=	SEQUENCE (SIZE (1..maxFreqBandsFDD)) OF
										CompressedModeMeasCapabFDD

CompressedModeMeasCapabFDDList2 ::=	SEQUENCE (SIZE (1..maxFreqBandsFDD)) OF
										CompressedModeMeasCapabFDD2

CompressedModeMeasCapabFDDList3 ::=	SEQUENCE (SIZE (1..maxFreqBandsFDD-ext2)) OF
										CompressedModeMeasCapabFDD3

CompressedModeMeasCapabFDDList-ext ::= SEQUENCE (SIZE (1..maxFreqBandsFDD)) OF
											CompressedModeMeasCapabFDD-ext

CompressedModeMeasCapabFDD ::=		SEQUENCE {
	radioFrequencyBandFDD				RadioFrequencyBandFDD	OPTIONAL,
	dl-MeasurementsFDD					BOOLEAN,
	ul-MeasurementsFDD					BOOLEAN
}

CompressedModeMeasCapabFDD2 ::=		SEQUENCE {
	-- UE may omit both IEs if this IE indicates the compressed mode capability within the same
	-- frequency band. Otherwise, the UE shall include either one of the following OPTIONAL IEs.
	radioFrequencyBandFDD				RadioFrequencyBandFDD	OPTIONAL,
	radioFrequencyBandFDD2				RadioFrequencyBandFDD2	OPTIONAL,
	dl-MeasurementsFDD					BOOLEAN,
	ul-MeasurementsFDD					BOOLEAN
}

CompressedModeMeasCapabFDD3 ::=		SEQUENCE {
	-- UE may omit radioFrequencyBandFDD3 if this IE indicates the compressed mode capability within
	-- the same frequency band. Otherwise, the UE shall include the IE.
	radioFrequencyBandFDD3				RadioFrequencyBandFDD3	OPTIONAL,
	dl-MeasurementsFDD					BOOLEAN,
	ul-MeasurementsFDD					BOOLEAN
}

CompressedModeMeasCapabFDD-ext ::=		SEQUENCE {
	radioFrequencyBandFDD2				RadioFrequencyBandFDD2,
	dl-MeasurementsFDD					BOOLEAN,
	ul-MeasurementsFDD					BOOLEAN
}

CompressedModeMeasCapabTDDList ::=	SEQUENCE (SIZE (1..maxFreqBandsTDD)) OF
										CompressedModeMeasCapabTDD

CompressedModeMeasCapabTDD ::=		SEQUENCE {
	radioFrequencyBandTDD				RadioFrequencyBandTDD,
	dl-MeasurementsTDD					BOOLEAN,
	ul-MeasurementsTDD					BOOLEAN
}

CompressedModeMeasCapabGSMList ::=	SEQUENCE (SIZE (1..maxFreqBandsGSM)) OF
										CompressedModeMeasCapabGSM

CompressedModeMeasCapabGSM ::=		SEQUENCE {
	radioFrequencyBandGSM				RadioFrequencyBandGSM,
	dl-MeasurementsGSM					BOOLEAN,
	ul-MeasurementsGSM					BOOLEAN
}

CompressedModeMeasCapabMC ::=		SEQUENCE {
	dl-MeasurementsMC					BOOLEAN,
	ul-MeasurementsMC					BOOLEAN
}

CPCH-Parameters ::=					SEQUENCE {
	initialPriorityDelayList			InitialPriorityDelayList			OPTIONAL,
	backoffControlParams				BackoffControlParams,
	-- TABULAR: TPC step size nested inside PowerControlAlgorithm
	powerControlAlgorithm				PowerControlAlgorithm,
	dl-DPCCH-BER						DL-DPCCH-BER
}

CSG-ProximityIndicationCapability ::= SEQUENCE {
	supportOfIntraFreqProximityIndication	ENUMERATED { true }						OPTIONAL,
	supportOfInterFreqProximityIndication	ENUMERATED { true }						OPTIONAL,
	supportOfE-UtraProximityIndication		ENUMERATED { true }						OPTIONAL
}

DL-CapabilityWithSimultaneousHS-DSCHConfig ::=	ENUMERATED{kbps32, kbps64, kbps128, kbps384}

DL-DPCCH-BER ::=					INTEGER (0..63)

DL-InformationPerSecondaryRL-List ::=		SEQUENCE (SIZE (1..maxEDCHRL)) OF
													DL-InformationPerSecondaryRL

DL-InformationPerSecondaryRL-List-r12 ::=	SEQUENCE (SIZE (1..maxEDCHRL)) OF
													DL-InformationPerSecondaryRL-r12

DL-InformationPerSecondaryRL-List-r13 ::=	SEQUENCE (SIZE (1..maxEDCHRL)) OF
													DL-InformationPerSecondaryRL-r13

DL-InformationPerSecondaryRL ::=		SEQUENCE {
	primaryCPICH-Info						PrimaryCPICH-Info,
	cell-id									CellIdentity			OPTIONAL,
	dl-FDPCHInfoPerRL-SecULFreq				DL-FDPCH-InfoPerRL-r7,
	e-AGCH-Information						E-AGCH-Information		OPTIONAL,
	e-HICH-Information						E-HICH-Information		OPTIONAL,
	e-RGCH-Info								CHOICE	{
		e-RGCH-Information						E-RGCH-Information,
		releaseIndicator						NULL
	}	OPTIONAL
}

DL-InformationPerSecondaryRL-r12 ::=		SEQUENCE {
	primaryCPICH-Info						PrimaryCPICH-Info,
	cell-id									CellIdentity			OPTIONAL,
	dl-FDPCHInfoPerRL-SecULFreq				DL-FDPCH-InfoPerRL-r7,
	e-AGCH-Information						E-AGCH-Information		OPTIONAL,
	e-HICH-Information						E-HICH-Information		OPTIONAL,
	e-RGCH-Info								CHOICE	{
		e-RGCH-Information						E-RGCH-Information,
		releaseIndicator						NULL
	}	OPTIONAL,
	secondary-Serving-E-DCHRL-Indicator		ENUMERATED { true }		OPTIONAL,
	radioLinkswithoutDPCHFDPCHIndicator		NULL					OPTIONAL
}

DL-InformationPerSecondaryRL-r13 ::=		SEQUENCE {
	primaryCPICH-Info						PrimaryCPICH-Info,
	cell-id									CellIdentity					OPTIONAL,
	dl-FDPCHInfoPerRL-SecULFreq			DL-FDPCH-InfoPerRL-r13,
	e-AGCH-Information						E-AGCH-Information				OPTIONAL,
	e-HICH-Information						E-HICH-Information				OPTIONAL,
	e-RGCH-Info							CHOICE	{
		e-RGCH-Information						E-RGCH-Information,
		releaseIndicator						NULL
	}	OPTIONAL,
	secondary-Serving-E-DCHRL-Indicator	ENUMERATED { true }			OPTIONAL,
	radioLinkswithoutDPCHFDPCHIndicator	NULL							OPTIONAL
}

DL-PhysChCapabilityFDD ::=			SEQUENCE {
	-- The IE "maxNoDPCH-PDSCH-Codes" only gives information on the maximum number of DPCH Codes.
	maxNoDPCH-PDSCH-Codes				INTEGER (1..8),
	maxNoPhysChBitsReceived				MaxNoPhysChBitsReceived,
	supportForSF-512					BOOLEAN,
	-- dummy and dummy2 are not used in this version of the specification
	-- and if received they should be ignored.
	dummy								BOOLEAN,
	dummy2								SimultaneousSCCPCH-DPCH-Reception
}

DL-PhysChCapabilityFDD-v380ext ::=			SEQUENCE {
	-- dummy is not used in this version of the specification, it should
	-- not be sent and if received it should be ignored.
	dummy										SupportOfDedicatedPilotsForChEstimation		OPTIONAL
}

SupportOfDedicatedPilotsForChEstimation ::=			ENUMERATED { true }

DL-PhysChCapabilityFDD-v770ext ::=		SEQUENCE {
	hsdsch-physical-layer-category-ext		HSDSCH-physical-layer-category-ext	OPTIONAL,
	hsscchlessHsdschOperation				ENUMERATED { true }					OPTIONAL,
	enhancedFdpch							ENUMERATED { true }					OPTIONAL,
	hsdschReception-CellFach				ENUMERATED { true }					OPTIONAL,
	hsdschReception-CellUraPch				ENUMERATED { true }					OPTIONAL
}

DL-PhysChCapabilityFDD-v860ext ::=		SEQUENCE {
	hsdsch-physical-layer-category-ext2		HSDSCH-physical-layer-category-ext2	OPTIONAL,
	supportOfTargetCellPreConfig			ENUMERATED { true }					OPTIONAL,
	supportOfHsdschDrxOperation				ENUMERATED { true }					OPTIONAL
}

DL-PhysChCapabilityFDD-v920ext ::=		SEQUENCE {
	hsdsch-physical-layer-category-ext3		HSDSCH-physical-layer-category-ext3	OPTIONAL,
	supportOfMimoOnlySingleStream			ENUMERATED { true }					OPTIONAL
}

DL-PhysChCapabilityFDD-va40ext ::=		SEQUENCE {
	hsdsch-physical-layer-category-ext4		HSDSCH-physical-layer-category-ext4	OPTIONAL,
	hsdsch-physical-layer-category-ext5		HSDSCH-physical-layer-category-ext5	OPTIONAL
}

DL-PhysChCapabilityFDD-vb50ext ::=		SEQUENCE {
	hsdsch-physical-layer-category-ext6		HSDSCH-physical-layer-category-ext6	OPTIONAL,
	hsdsch-physical-layer-category-ext7		HSDSCH-physical-layer-category-ext7	OPTIONAL,
	hsdsch-physical-layer-category-ext8		HSDSCH-physical-layer-category-ext8	OPTIONAL,
	supportOf4x4MimoDualStreamRestriction	ENUMERATED { true }					OPTIONAL,
	supportOfHS-DSCHSecondDRXOperation		ENUMERATED { true }					OPTIONAL,
	supportOfNodeBTrigHS-DPCCHTransmission	ENUMERATED { true }					OPTIONAL
}

DL-PhysChCapabilityFDD-vb80ext ::=	SEQUENCE {
	non-ContiguousMulti-CellWithMIMO		ENUMERATED { true }					OPTIONAL
}

DL-PhysChCapabilityFDD-vc50ext ::=		SEQUENCE {
	supportforDCHEnhancements						ENUMERATED { basic, full }		OPTIONAL,
	simultaneousSupportforDCHEnhancementsAndCM	ENUMERATED { true }				OPTIONAL,
	simultaneousSupportforDCHEnhancementsAndDPCCHDiscntTx	ENUMERATED { true }	OPTIONAL,
	drx-enhancements								ENUMERATED { true }				OPTIONAL,
	hs-dpcchOverheadReduction						ENUMERATED { true }				OPTIONAL,
	supportofEnhancedServingCellChangeForEvent1C	ENUMERATED { true }			OPTIONAL,
	supportofDPCCH2								ENUMERATED { true }				OPTIONAL
}

DL-PhysChCapabilityFDD-vd20ext ::=	SEQUENCE {
	supportofPowerControlAlgorithm3			ENUMERATED { true }				OPTIONAL,
	supportofBlindHarqRetransmissionsforHsdpa		ENUMERATED { true }				OPTIONAL
}

DL-PhysChCapabilityFDD-ve30ext ::=	SEQUENCE {
	supportofHS-SCCHDrxOperation			ENUMERATED { true }				OPTIONAL
}

DL-PhysChCapabilityFDD-vf10ext ::=	SEQUENCE {
	supportofSimplifiedHS-SCCHType1Operation			     ENUMERATED { true }			OPTIONAL
}

DL-PhysChCapabilityTDD ::=		SEQUENCE {
	maxTS-PerFrame						MaxTS-PerFrame,
	maxPhysChPerFrame					MaxPhysChPerFrame,
	minimumSF							MinimumSF-DL,
	supportOfPDSCH						BOOLEAN,
	maxPhysChPerTS						MaxPhysChPerTS
}

DL-PhysChCapabilityTDD-LCR-r4 ::=	SEQUENCE {
	maxTS-PerSubFrame						MaxTS-PerSubFrame-r4,
	maxPhysChPerFrame						MaxPhysChPerSubFrame-r4,
	minimumSF								MinimumSF-DL,
	supportOfPDSCH							BOOLEAN,
	maxPhysChPerTS							MaxPhysChPerTS,
	supportOf8PSK							BOOLEAN
}

DL-PhysChCapabilityTDD-128-v770ext ::=	SEQUENCE {
	multiCarrier-physical-layer-category	MultiCarrier-HSDSCH-physical-layer-category	OPTIONAL
}

DL-PhysChCapabilityTDD-128-v860ext ::=	SEQUENCE {
	hSDSCH-physical-layer-category-extension
											HSDSCH-physical-layer-category-extension	OPTIONAL,
	multiCarrier-physical-layer-category-extension
								MultiCarrier-HSDSCH-physical-layer-category-extension	OPTIONAL,
	supportOfSFModeForHSPDSCHDualStream		ENUMERATED { sf1, sf1sf16 }		OPTIONAL
}

DL-PhysChCapabilityInfoTDD-128-va40ext::=	SEQUENCE {
	multiCarrier-physical-layer-category-extension2
								MultiCarrier-HSDSCH-physical-layer-category-extension2	OPTIONAL
}

DL-PhysChCapabilityInfoTDD-128-vc50ext::=	SEQUENCE {
	supportofNon-rectResourceAllocation			ENUMERATED { true }			OPTIONAL
}

DL-PhysChCapabilityTDD-768 ::=		SEQUENCE {
	maxTS-PerFrame							MaxTS-PerFrame,
	maxPhysChPerFrame						MaxPhysChPerFrame-768,
	minimumSF								MinimumSF-DL-768,
	supportOfPDSCH							BOOLEAN,
	tdd768-hspdsch							CHOICE {
		supported								HSDSCH-physical-layer-category,
		unsupported							NULL
	},
	maxPhysChPerTS							MaxPhysChPerTS-768
}

DL-PhysChCapabilityInfoTDD-768 ::=	SEQUENCE {
	maxTS-PerFrame							MaxTS-PerFrame,
	maxPhysChPerFrame						MaxPhysChPerFrame-768,
	minimumSF								MinimumSF-DL-768,
	supportOfPDSCH							BOOLEAN,
	maxPhysChPerTS							MaxPhysChPerTS-768
}

DL-TransChCapability ::=			SEQUENCE {
	maxNoBitsReceived					MaxNoBits,
	maxConvCodeBitsReceived			MaxNoBits,
	turboDecodingSupport				TurboSupport,
	maxSimultaneousTransChs			MaxSimultaneousTransChsDL,
	maxSimultaneousCCTrCH-Count		MaxSimultaneousCCTrCH-Count,
	maxReceivedTransportBlocks		MaxTransportBlocksDL,
	maxNumberOfTFC						MaxNumberOfTFC-DL,
	maxNumberOfTF						MaxNumberOfTF
}

DRAC-SysInfo ::=					SEQUENCE {
	transmissionProbability			TransmissionProbability,
	maximumBitRate						MaximumBitRate
}

DRAC-SysInfoList ::=				SEQUENCE (SIZE (1..maxDRACclasses)) OF
										DRAC-SysInfo

DSCH-RNTI ::=						BIT STRING (SIZE (16))

DelayRestrictionFlag ::=			ENUMERATED { true }

DynamicActivationTime ::=			SEQUENCE {
	activationOffset					INTEGER (0..15)			OPTIONAL
}

E-RNTI ::=							BIT STRING (SIZE (16))

ESN-DS-41 ::=						BIT STRING (SIZE (32))

EstablishmentCause ::=			ENUMERATED {
										originatingConversationalCall,
										originatingStreamingCall,
										originatingInteractiveCall,
										originatingBackgroundCall,
										originatingSubscribedTrafficCall,
										terminatingConversationalCall,
										terminatingStreamingCall,
										terminatingInteractiveCall,
										terminatingBackgroundCall,
										emergencyCall,
										interRAT-CellReselection,
										interRAT-CellChangeOrder,
										registration,
										detach,
										originatingHighPrioritySignalling,
										originatingLowPrioritySignalling,
										callRe-establishment,
										terminatingHighPrioritySignalling,
										terminatingLowPrioritySignalling,
										terminatingCauseUnknown,
										mbms-Reception,
										mbms-PTP-RB-Request,
										delayTolerantAccess,
										spare9,
										spare8,
										spare7,
										spare6,
										spare5,
										spare4,
										spare3,
										spare2,
										spare1 }

ExtendedWaitTime ::=				INTEGER (1..1800)

EUTRAbandSpecificCapUpdateReqList	::=	SEQUENCE (SIZE (1..16)) OF RadioFrequencyBandEUTRAExt2

FailureCauseWithProtErr ::=		CHOICE {
	configurationUnsupported			NULL,
	physicalChannelFailure			NULL,
	incompatibleSimultaneousReconfiguration
										NULL,
	compressedModeRuntimeError		TGPSI,
	protocolError						ProtocolErrorInformation,
	cellUpdateOccurred					NULL,
	invalidConfiguration				NULL,
	configurationIncomplete			NULL,
	unsupportedMeasurement			NULL,
	mbmsSessionAlreadyReceivedCorrectly	NULL,
	lowerPriorityMBMSService			NULL,
	spare5								NULL,
	spare4								NULL,
	spare3								NULL,
	spare2								NULL,
	spare1								NULL
}

FailureCauseWithProtErrTrId ::=		SEQUENCE {
	rrc-TransactionIdentifier				RRC-TransactionIdentifier,
	failureCause							FailureCauseWithProtErr
}

FrequencyBandsIndicatorSupport ::=	SEQUENCE {
	modeSpecificInfo						CHOICE {
		fdd										SEQUENCE {
			frequencyBandsSupportFDD				FrequencyBandsRedirectionFDD
		},
		tdd										SEQUENCE {
			frequencyBandsSupportTDD128			FrequencyBandsIndicatorTDD128
		}
	}
}

FrequencyBandsIndicatorTDD128 ::=	SEQUENCE (SIZE (1..maxFreqBandsIndicatorSupport)) OF
											FrequencyBandsIndicatorSupportTDD128

FrequencyBandsIndicatorSupportTDD128 ::= 	SEQUENCE {
	frequencyBandsIndicatorTDD					RadioFrequencyBandTDD-r10
}

FrequencyBandsRedirectionFDD ::= 	SEQUENCE (SIZE (1..maxFreqBandsIndicatorSupport)) OF
											FrequencyBandsIndicatorFDD

FrequencyBandsIndicatorFDD ::= 		CHOICE {
	frequencyBandsIndicator1				RadioFrequencyBandFDD,
	frequencyBandsIndicator2				RadioFrequencyBandFDD2,
	frequencyBandsIndicator3				RadioFrequencyBandFDD3
}

GANSS-Mode ::=						ENUMERATED {
										networkBased,
										uEBased,
										both,
										none }

GroupIdentityWithReleaseInformation ::=		SEQUENCE {
	rrc-ConnectionReleaseInformation				RRC-ConnectionReleaseInformation,
	groupReleaseInformation						GroupReleaseInformation
	}

GroupReleaseInformation ::=			SEQUENCE {
	uRNTI-Group							U-RNTI-Group
}

GSM-Measurements ::=				SEQUENCE {
	gsm900								BOOLEAN,
	dcs1800								BOOLEAN,
	gsm1900								BOOLEAN
}

H-RNTI ::=							BIT STRING (SIZE (16))

High-MobilityDetected ::=			ENUMERATED { high-MobilityDetected }

HSDSCH-physical-layer-category ::=		INTEGER (1..64)

HSDSCH-physical-layer-category-ext ::=	INTEGER (1..20)

HSDSCH-physical-layer-category-ext2 ::=	INTEGER (21..24)

HSDSCH-physical-layer-category-ext3 ::=	INTEGER (25..28)

HSDSCH-physical-layer-category-ext4 ::=	INTEGER (29..30)

HSDSCH-physical-layer-category-ext5 ::=	INTEGER (31..32)

HSDSCH-physical-layer-category-ext6 ::=	INTEGER (33..34)

HSDSCH-physical-layer-category-ext7 ::=	INTEGER (35..36)

HSDSCH-physical-layer-category-ext8 ::=	INTEGER (37..38)

HSDSCH-physical-layer-category-extension ::=	INTEGER (1..64)

MultiCarrier-HSDSCH-physical-layer-category ::=	INTEGER (1..64)

MultiCarrier-HSDSCH-physical-layer-category-extension ::= INTEGER (1..36)

MultiCarrier-HSDSCH-physical-layer-category-extension2 ::= INTEGER (37..64)

MultiflowCapabBandCombination ::= 		SEQUENCE {
	numberOfCellsBandA							INTEGER(1..6),
	numberOfFrequenciesBandA					INTEGER(1..3),
	numberOfCellsBandB							INTEGER(1..6),
	numberOfFrequenciesBandB					INTEGER(1..3)
}

MultiflowCapabBandCombList ::= SEQUENCE (SIZE (1..16)) OF MultiflowCapabBandCombination

MultiflowCapability ::=			SEQUENCE {
	mimoInDifferentBands				MultiflowMIMOCapability				OPTIONAL,
	longerHARQProcessing				ENUMERATED { true }					OPTIONAL
}

MultiflowPerBandCapability ::=	SEQUENCE {
	numberOfCells						INTEGER(2..8),
	numberOfFrequencies				INTEGER(1..4),
	mimo								MultiflowMIMOCapability				OPTIONAL,
	nonContiguousCapability			MultiflowNonContiguousCapability		OPTIONAL
}

MultiflowMIMOCapability ::=			ENUMERATED { single-stream, dual-stream }

MultiflowNonContiguousCapability ::= 	SEQUENCE {
	gapSize					ENUMERATED { fiveMHz, tenMHz, anyGapSize,
										 spare5, spare4, spare3, spare2, spare1 }
}

UESpecificBehaviourInformation1idle ::= BIT STRING (SIZE (4))

UESpecificBehaviourInformation1interRAT ::= BIT STRING (SIZE (8))

IdleIntervalMeasCapabEUTRA ::=		SEQUENCE {
	radioFrequencyBandEUTRA				RadioFrequencyBandEUTRA,
	idleInterval							BOOLEAN
}

IdleIntervalMeasCapabEUTRAExtension ::=		SEQUENCE {
	radioFrequencyBandEUTRA						RadioFrequencyBandEUTRAExt
}

IdleIntervalMeasCapabEUTRAList ::=	SEQUENCE (SIZE (1..maxFreqBandsEUTRA)) OF
											IdleIntervalMeasCapabEUTRA

IdleIntervalMeasCapabEUTRAExtensionList ::=	SEQUENCE (SIZE (1..maxFreqBandsEUTRA)) OF
													IdleIntervalMeasCapabEUTRAExtension

IMSI-and-ESN-DS-41 ::=			SEQUENCE {
	imsi-DS-41							IMSI-DS-41,
	esn-DS-41							ESN-DS-41
}

IMSI-DS-41 ::=						OCTET STRING (SIZE (5..7))

InitialPriorityDelayList ::=		SEQUENCE (SIZE (1..maxASC)) OF
										NS-IP

InitialUE-Identity ::=			CHOICE {
	imsi								IMSI-GSM-MAP,
	tmsi-and-LAI						TMSI-and-LAI-GSM-MAP,
	p-TMSI-and-RAI						P-TMSI-and-RAI-GSM-MAP,
	imei								IMEI,
	esn-DS-41							ESN-DS-41,
	imsi-DS-41							IMSI-DS-41,
	imsi-and-ESN-DS-41					IMSI-and-ESN-DS-41,
	tmsi-DS-41							TMSI-DS-41
}

IntegrityCheckInfo ::=			SEQUENCE {
	messageAuthenticationCode			MessageAuthenticationCode,
	rrc-MessageSequenceNumber			RRC-MessageSequenceNumber
}

IntegrityProtActivationInfo ::=		SEQUENCE {
	rrc-MessageSequenceNumberList		RRC-MessageSequenceNumberList
}

IntegrityProtectionAlgorithm ::=	ENUMERATED {
										uia1 }

IntegrityProtectionAlgorithm-r7 ::=	ENUMERATED {
											uia1, uia2 }

IntegrityProtectionModeCommand ::= 	CHOICE {
	startIntegrityProtection				SEQUENCE {
		integrityProtInitNumber				IntegrityProtInitNumber
	},
	modify									SEQUENCE {
		dl-IntegrityProtActivationInfo		IntegrityProtActivationInfo
	}
}

IntegrityProtectionModeInfo ::=		SEQUENCE {
	-- TABULAR: DL integrity protection activation info and Integrity
	-- protection intialisation number have been nested inside
	-- IntegrityProtectionModeCommand.
	integrityProtectionModeCommand		IntegrityProtectionModeCommand,
	integrityProtectionAlgorithm			IntegrityProtectionAlgorithm			OPTIONAL
}

IntegrityProtectionModeInfo-r7 ::=	SEQUENCE {
	-- TABULAR: DL integrity protection activation info and Integrity
	-- protection intialisation number have been nested inside
	-- IntegrityProtectionModeCommand.
	integrityProtectionModeCommand		IntegrityProtectionModeCommand,
	integrityProtectionAlgorithm			IntegrityProtectionAlgorithm-r7		OPTIONAL
}

IntegrityProtInitNumber ::=			BIT STRING (SIZE (32))

-- dummy is not used in this version of the specification, it should
-- not be sent and if received it should be ignored.
MaxHcContextSpace ::=					ENUMERATED	{
											dummy, by1024, by2048, by4096,
											by8192 }

MaxHcContextSpace-r5-ext ::=			ENUMERATED	{
											by16384, by32768, by65536, by131072 }


MaxROHC-ContextSessions-r4 ::=		ENUMERATED	{
											s2, s4, s8, s12, s16, s24, s32, s48,
											s64, s128, s256, s512, s1024, s16384 }

MaximumAM-EntityNumberRLC-Cap ::=	ENUMERATED {
											dummy, am4, am5, am6,
											am8, am16, am30 }

-- Actual value MaximumBitRate = IE value * 16
MaximumBitRate ::=					INTEGER (0..32)

MaximumRLC-WindowSize ::=			ENUMERATED { mws2047, mws4095 }

MaxNoDPDCH-BitsTransmitted ::=	ENUMERATED {
										b600, b1200, b2400, b4800,
										b9600, b19200, b28800, b38400,
										b48000, b57600 }

MaxNoBits ::=						ENUMERATED {
										b640, b1280, b2560, b3840, b5120,
										b6400, b7680, b8960, b10240,
										b20480, b40960, b81920, b163840 }

MaxNoPhysChBitsReceived ::=			ENUMERATED {
										dummy, b1200, b2400, b3600,
										b4800, b7200, b9600, b14400,
										b19200, b28800, b38400, b48000,
										b57600, b67200, b76800 }

MaxNoSCCPCH-RL ::=					ENUMERATED {
										rl1 }

MaxNumberOfTF ::=					ENUMERATED {
										tf32, tf64, tf128, tf256,
										tf512, tf1024 }

MaxNumberOfTFC-DL ::=				ENUMERATED {
										tfc16, tfc32, tfc48, tfc64, tfc96,
										tfc128, tfc256, tfc512, tfc1024 }

MaxNumberOfTFC-UL ::=				ENUMERATED {
										dummy1, dummy2, tfc16, tfc32, tfc48, tfc64,
										tfc96, tfc128, tfc256, tfc512, tfc1024 }

-- the values 1 to 4 for MaxPhysChPerFrame are not used in this version of the protocol
MaxPhysChPerFrame ::=				INTEGER (1..224)

MaxPhysChPerFrame-768 ::=			INTEGER (1..448)

MaxPhysChPerSubFrame-r4 ::=		INTEGER (1..96)

MaxPhysChPerTimeslot ::=			ENUMERATED {
										ts1, ts2 }

MaxPhysChPerTimeslot-LCR-r7 ::=	INTEGER (1..4)

-- the values 1 to 4 for MaxPhysChPerTS are not used in this version of the protocol
MaxPhysChPerTS ::=					INTEGER (1..16)

MaxPhysChPerTS-768 ::=			INTEGER (1..32)

MaxSimultaneousCCTrCH-Count ::=	INTEGER (1..8)

MaxSimultaneousTransChsDL ::=		ENUMERATED {
										e4, e8, e16, e32 }

MaxSimultaneousTransChsUL ::=		ENUMERATED {
										dummy, e4, e8, e16, e32 }

MaxTransportBlocksDL ::=			ENUMERATED {
										tb4, tb8, tb16, tb32, tb48,
										tb64, tb96, tb128, tb256, tb512 }

MaxTransportBlocksUL ::=			ENUMERATED {
										dummy, tb4, tb8, tb16, tb32, tb48,
										tb64, tb96, tb128, tb256, tb512 }

MaxTS-PerFrame ::=					INTEGER (1..14)

MaxTS-PerSubFrame-r4 ::=			INTEGER (1..6)

-- TABULAR: MeasurementCapability contains dependencies to UE-MultiModeRAT-Capability,
-- the conditional fields have been left mandatory for now.
MeasurementCapability ::=			SEQUENCE {
	downlinkCompressedMode			CompressedModeMeasCapability,
	uplinkCompressedMode				CompressedModeMeasCapability
}

MeasurementCapabilityExt ::= 		SEQUENCE{
	compressedModeMeasCapabFDDList		CompressedModeMeasCapabFDDList,
	compressedModeMeasCapabTDDList		CompressedModeMeasCapabTDDList		OPTIONAL,
	compressedModeMeasCapabGSMList		CompressedModeMeasCapabGSMList		OPTIONAL,
	compressedModeMeasCapabMC				CompressedModeMeasCapabMC				OPTIONAL
}

MeasurementCapabilityExt2 ::= 		SEQUENCE{
	compressedModeMeasCapabFDDList		CompressedModeMeasCapabFDDList2,
	compressedModeMeasCapabTDDList		CompressedModeMeasCapabTDDList		OPTIONAL,
	compressedModeMeasCapabGSMList		CompressedModeMeasCapabGSMList		OPTIONAL,
	compressedModeMeasCapabMC				CompressedModeMeasCapabMC				OPTIONAL
}

MeasurementCapabilityExt3 ::=		SEQUENCE {
	compressedModeMeasCapabEUTRAList		CompressedModeMeasCapabEUTRAList		OPTIONAL
}

MeasurementCapabilityExt4 ::= 		SEQUENCE{
	compressedModeMeasCapabFDDList2		CompressedModeMeasCapabFDDList2		OPTIONAL,
	compressedModeMeasCapabFDDList3		CompressedModeMeasCapabFDDList3		OPTIONAL,
	compressedModeMeasCapabTDDList		CompressedModeMeasCapabTDDList		OPTIONAL,
	compressedModeMeasCapabGSMList		CompressedModeMeasCapabGSMList		OPTIONAL,
	compressedModeMeasCapabMC				CompressedModeMeasCapabMC				OPTIONAL,
	compressedModeMeasCapabEUTRAList		CompressedModeMeasCapabEUTRAList		OPTIONAL
}

MeasurementCapabilityExt5 ::=		SEQUENCE {
	compressedModeMeasCapabEUTRAList		CompressedModeMeasCapabEUTRAList2	OPTIONAL
}

MeasurementCapabilityExt6 ::=		SEQUENCE{
	compressedModeMeasCapabEUTRAList		CompressedModeMeasCapabEUTRAList3	OPTIONAL
}

MeasurementCapability-r4-ext ::=	SEQUENCE {
	downlinkCompressedMode-LCR		CompressedModeMeasCapability-LCR-r4,
	uplinkCompressedMode-LCR			CompressedModeMeasCapability-LCR-r4
}

MeasurementCapability-v860ext ::=	SEQUENCE {
	downlinkCompressedMode				CompressedModeMeasCapability-v860ext
}

MeasurementCapability-v920ext ::=	SEQUENCE {
	downlinkCompressedMode				CompressedModeMeasCapability-v920ext
}

MeasurementCapability-va40ext ::=	SEQUENCE {
	interFrequencyDetectedSetMeasurements	ENUMERATED { true }				OPTIONAL,
	downlinkCompressedMode					CompressedModeMeasCapability-va40ext
}

MeasurementCapability-vb50ext ::=	SEQUENCE {
	interFrequencyMeasOnConfigCarriersWithoutCompMode	ENUMERATED { true }	OPTIONAL,
	cellsExcludedFromDetectedSetMeasurements			ENUMERATED { true }	OPTIONAL
}

MeasurementCapabilityTDD ::=		SEQUENCE {
	idleIntervalMeasCapabEUTRAList		IdleIntervalMeasCapabEUTRAList		OPTIONAL
}

MeasurementCapabilityTDD-vb50ext ::=	SEQUENCE {
	idleIntervalMeasCapabEUTRAList		IdleIntervalMeasCapabEUTRAExtensionList	OPTIONAL
}

MeasurementCapability-vb70ext ::=	SEQUENCE {
	widebandRSRQFDDMeasurements			ENUMERATED { true }				OPTIONAL,
	widebandRSRQTDDMeasurements			ENUMERATED { true }				OPTIONAL
}

MeasurementCapability-vc50ext ::=	SEQUENCE {
	event2gReportingOnaConfiguredSecDLFrequency	ENUMERATED { true }		OPTIONAL,
	extendedRsrqLowerValueRange					ENUMERATED { true }		OPTIONAL,
	rsrqOnAllSymbols								ENUMERATED { true }		OPTIONAL,
	increasedUECarrierMonitoringUTRA				ENUMERATED { true }		OPTIONAL,
	increasedUECarrierMonitoringE-UTRA			ENUMERATED { true }		OPTIONAL,
	enhancedUPHReporting							ENUMERATED { true }		OPTIONAL
}

MeasurementCapability-ve30ext ::=	SEQUENCE {
	rrcEventsforUPHReporting							ENUMERATED { true }			OPTIONAL,
	qoEMeasurementCollectionForStreamingServices	ENUMERATED { true }			OPTIONAL
}

MeasurementCapability-vf20ext ::=	SEQUENCE {
	qoEMeasurementCollectionForMTSIServices		ENUMERATED { true }			OPTIONAL
}

MessageAuthenticationCode ::=		BIT STRING (SIZE (32))

MinimumSF-DL ::=					ENUMERATED {
										sf1, sf16 }

MinimumSF-DL-768 ::=				ENUMERATED {
										sf1, sf32 }

MinimumSF-UL ::=					ENUMERATED {
										sf1, sf2, sf4, sf8, dummy }

NonContiguousMultiCellCombinationList ::=	SEQUENCE (SIZE (1..maxNonContiguousMultiCellCombinations)) OF
									NonContiguousMultiCell

NonContiguousMultiCell ::=	SEQUENCE {
	aggregatedCells				ENUMERATED { nc-2c, nc-3c, nc-4c },
	gapSize							ENUMERATED { fiveMHz, tenMHz, anyGapSize,
												 spare5, spare4, spare3, spare2, spare1 },
	nonContiguousMultiCellCombination22		ENUMERATED { true }					OPTIONAL,
	nonContiguousMultiCellCombination31-13	ENUMERATED { true }					OPTIONAL
}

MultiModeCapability ::=			ENUMERATED {
										tdd, fdd, fdd-tdd }

MultiRAT-Capability ::=			SEQUENCE {
	supportOfGSM						BOOLEAN,
	supportOfMulticarrier				BOOLEAN
}

MultiModeRAT-Capability-v590ext ::=	SEQUENCE {
	supportOfUTRAN-ToGERAN-NACC			BOOLEAN
}

MultiModeRAT-Capability-v680ext ::=	SEQUENCE {
	supportOfHandoverToGAN				ENUMERATED { doesSupportHandoverToGAN }		OPTIONAL
}

MultiModeRAT-Capability-v770ext ::=	SEQUENCE {
	supportOfPSHandoverToGAN			ENUMERATED { doesSupportPSHandoverToGAN }	OPTIONAL
}

MultiModeRAT-Capability-v860ext ::=	SEQUENCE {
	supportOfEUTRAFDD						ENUMERATED { doesSupportEUTRAFDD }		OPTIONAL,
	supportOfInterRATHOToEUTRAFDD		ENUMERATED { doesSupportInterRATHOToEUTRAFDD }	OPTIONAL,
	supportOfEUTRATDD						ENUMERATED { doesSupportEUTRATDD }		OPTIONAL,
	supportOfInterRATHOToEUTRATDD		ENUMERATED { doesSupportInterRATHOToEUTRATDD }	OPTIONAL,
	eutraFeatureGroupIndicators			BIT STRING (SIZE (4))						OPTIONAL
}

MultiModeRAT-Capability-vae0ext ::=			SEQUENCE {
	eutraSupportOfMFBI						ENUMERATED { true }							OPTIONAL
}

MultiModeRAT-Capability-vb50ext ::=	SEQUENCE {
	supportOfEUTRAFDDMeasurementReportingInCELLFACH		ENUMERATED { 																doesSupportOfEUTRAFDDMeasurementReportingInCELLFACH }	OPTIONAL,
	supportOfEUTRATDDMeasurementReportingInCELLFACH		ENUMERATED { 																doesSupportOfEUTRATDDMeasurementReportingInCELLFACH }	OPTIONAL
}

MultiModeRAT-Capability-vc50ext ::=	SEQUENCE {
	supportOfRAN-AssistedWLAN-Interworking-RAN-Rules		ENUMERATED { true }		OPTIONAL,
	supportOfRAN-AssistedWLAN-Interworking-ANDSF-Policies		ENUMERATED { true }		OPTIONAL
}

MultiModeRAT-Capability-vd20ext ::=	SEQUENCE {
	supportOfExtendedEUTRAFrequencyPriority		ENUMERATED { true }		OPTIONAL
}

N-300 ::=							INTEGER (0..7)

N-301 ::=							INTEGER (0..7)

N-302 ::=							INTEGER (0..7)

N-304 ::=							INTEGER (0..7)

N-308 ::=							INTEGER (1..8)

N-310 ::=							INTEGER (0..7)

N-312 ::=							ENUMERATED {
										s1, s50, s100, s200, s400,
										s600, s800, s1000 }

N-312ext ::=						ENUMERATED {
										s2, s4, s10, s20 }

N-312-r5 ::=						ENUMERATED {
										s1, s2, s4, s10, s20,
										s50, s100, s200, s400,
										s600, s800, s1000 }

N-313 ::=							ENUMERATED {
										s1, s2, s4, s10, s20,
										 s50, s100, s200 }

N-315 ::=							ENUMERATED {
										s1, s50, s100, s200, s400,
										s600, s800, s1000 }

N-315ext ::=						ENUMERATED {
										s2, s4, s10, s20 }

N-315-r5 ::=						ENUMERATED {
										s1, s2, s4, s10, s20,
										s50, s100, s200, s400,
										s600, s800, s1000 }


N-AccessFails ::=					INTEGER (1..64)

N-AP-RetransMax ::=				INTEGER (1..64)

NeighCellSI-AcquisitionCapability ::= SEQUENCE {
	supportOfIntraFreqSIAcquisitionForHO		ENUMERATED { true }					OPTIONAL,
	supportOfInterFreqSIAcquisitionForHO		ENUMERATED { true }					OPTIONAL,
	supportOfE-UtraSIAcquisitionForHO		ENUMERATED { true }					OPTIONAL
}

NetworkAssistedGANSS-Supported-List ::= SEQUENCE (SIZE (1..maxGANSS)) OF SEQUENCE {
	gANSS-Id							ENUMERATED {
											sbas, modernizedGPS, qzss, glonass, bds,
											spare3, spare2, spare1 }					OPTIONAL,
	gANSS-Mode							GANSS-Mode,
	gANSS-SignalId						GANSS-Signal-Id								OPTIONAL,
	supportForUE-GANSS-TimingOfCellFrames		BOOLEAN,
	supportForUE-GANSS-CarrierPhaseMeasurement	BOOLEAN								OPTIONAL
}

-- Each element in the NetworkAssistedGANSS-Supported-List-v860ext provides extension information
-- to the corresponding element (position) in the NetworkAssistedGANSS-Supported-List
NetworkAssistedGANSS-Supported-List-v860ext ::= SEQUENCE (SIZE (1..maxGANSS)) OF SEQUENCE {
	sbas-Ids								BIT STRING (SIZE (8))						OPTIONAL,
	gANSS-SignalIds						BIT STRING (SIZE (8))						OPTIONAL,
	non-native-AD-choices-supported		ENUMERATED { true }						OPTIONAL
}

NetworkAssistedGPS-Supported ::=	ENUMERATED {
										networkBased,
										ue-Based,
										bothNetworkAndUE-Based,
										noNetworkAssistedGPS }

NF-BO-AllBusy ::=					INTEGER (0..31)

NF-BO-NoAICH ::=					INTEGER (0..31)

NF-BO-Mismatch ::=					INTEGER (0..127)

NS-BO-Busy ::=						INTEGER (0..63)

NS-IP ::=							INTEGER (0..28)

P-TMSI-and-RAI-GSM-MAP ::=		SEQUENCE {
	p-TMSI								P-TMSI-GSM-MAP,
	rai									RAI
}

PagingCause ::=					ENUMERATED {
										terminatingConversationalCall,
										terminatingStreamingCall,
										terminatingInteractiveCall,
										terminatingBackgroundCall,
										terminatingHighPrioritySignalling,
										terminatingLowPrioritySignalling,
										terminatingCauseUnknown,
										spare
 }

PagingRecord ::=					CHOICE {
	cn-Identity							SEQUENCE {
		pagingCause							PagingCause,
		cn-DomainIdentity						CN-DomainIdentity,
		cn-pagedUE-Identity					CN-PagedUE-Identity
	},
	utran-Identity						SEQUENCE {
		u-RNTI								U-RNTI,
		cn-OriginatedPage-connectedMode-UE	SEQUENCE {
			pagingCause							PagingCause,
			cn-DomainIdentity						CN-DomainIdentity,
			pagingRecordTypeID						PagingRecordTypeID
		}																	OPTIONAL
	}
}

PagingRecord2-r5 ::=				CHOICE {
	utran-SingleUE-Identity				SEQUENCE {
		u-RNTI								U-RNTI,
		cn-OriginatedPage-connectedMode-UE	SEQUENCE {
			pagingCause							PagingCause,
			cn-DomainIdentity						CN-DomainIdentity,
			pagingRecordTypeID						PagingRecordTypeID
		}																	OPTIONAL,
		rrc-ConnectionReleaseInformation		RRC-ConnectionReleaseInformation
	},
	utran-GroupIdentity					SEQUENCE ( SIZE (1 .. maxURNTI-Group) ) OF
												GroupIdentityWithReleaseInformation
}

PagingRecordList ::=				SEQUENCE (SIZE (1..maxPage1)) OF
										PagingRecord

PagingRecord2List-r5 ::=			SEQUENCE (SIZE (1..maxPage1)) OF
										PagingRecord2-r5

PDCP-Capability ::=				SEQUENCE {
	losslessSRNS-RelocationSupport		BOOLEAN,
	-- If present, the "maxHcContextSpace" in the IE "PDCP-Capability-r5-ext" overrides the
	-- "supported" value in this IE. The value in this IE may be used by a pre-REL-5 UTRAN.
	supportForRfc2507						CHOICE {
		notSupported							NULL,
		supported								MaxHcContextSpace
	}
}

PDCP-Capability-r4-ext ::=		SEQUENCE {
	supportForRfc3095					CHOICE {
		notSupported						NULL,
		supported							SEQUENCE {
			maxROHC-ContextSessions			MaxROHC-ContextSessions-r4	DEFAULT s16,
			reverseCompressionDepth			INTEGER (0..65535)				DEFAULT 0
		}
	}
}

PDCP-Capability-r5-ext ::=			SEQUENCE {
	supportForRfc3095ContextRelocation		BOOLEAN,
	maxHcContextSpace							MaxHcContextSpace-r5-ext			OPTIONAL
}

PDCP-Capability-r5-ext2 ::=			SEQUENCE {
	losslessDLRLC-PDUSizeChange			ENUMERATED { true }					OPTIONAL
}

PDCP-Capability-v770ext ::=			SEQUENCE {
	supportForCSVoiceoverHSPA				ENUMERATED { true }					OPTIONAL
}

PhysicalChannelCapability ::=		SEQUENCE {
		fddPhysChCapability					SEQUENCE {
			downlinkPhysChCapability				DL-PhysChCapabilityFDD,
			uplinkPhysChCapability				UL-PhysChCapabilityFDD
		}											OPTIONAL,
		-- tddPhysChCapability describes the 3.84Mcps TDD physical channel capability
		tddPhysChCapability					SEQUENCE {
			downlinkPhysChCapability				DL-PhysChCapabilityTDD,
			uplinkPhysChCapability				UL-PhysChCapabilityTDD
		}											OPTIONAL
}

PhysicalChannelCapability-v770ext ::=	SEQUENCE {
	fddPhysChCapability						SEQUENCE {
		downlinkPhysChCapability					DL-PhysChCapabilityFDD-v770ext,
		uplinkPhysChCapability					UL-PhysChCapabilityFDD-v770ext
	}		OPTIONAL,
	tddPhysChCapability-384					SEQUENCE {
		-- No TDD384 DL physical channel capability extension
		uplinkPhysChCapability					UL-PhysChCapabilityTDD-384-v770ext
	}		OPTIONAL,
	tddPhysChCapability-768					SEQUENCE {
		downlinkPhysChCapability					DL-PhysChCapabilityTDD-768,
		uplinkPhysChCapability					UL-PhysChCapabilityTDD-768
	}		OPTIONAL,
	tddPhysChCapability-128					SEQUENCE {
		downlinkPhysChCapability					DL-PhysChCapabilityTDD-128-v770ext,
		uplinkPhysChCapability					UL-PhysChCapabilityTDD-128-v770ext
	}		OPTIONAL
}

PhysicalChannelCapability-v860ext ::=	SEQUENCE {
	fddPhysChCapability						SEQUENCE {
		downlinkPhysChCapability					DL-PhysChCapabilityFDD-v860ext
	}		OPTIONAL,
	tddPhysChCapability-128					SEQUENCE {
		downlinkPhysChCapability					DL-PhysChCapabilityTDD-128-v860ext
	}		OPTIONAL
}

PhysicalChannelCapability-v920ext ::=	SEQUENCE {
	fddPhysChCapability						SEQUENCE {
		downlinkPhysChCapability					DL-PhysChCapabilityFDD-v920ext,
		uplinkPhysChCapability					UL-PhysChCapabilityFDD-v920ext
	}		OPTIONAL
}

PhysicalChannelCapability-va40ext ::=	SEQUENCE {
	fddPhysChCapability						SEQUENCE {
		downlinkPhysChCapability					DL-PhysChCapabilityFDD-va40ext
	}		OPTIONAL,
	tddPhysChCapability-128					SEQUENCE {
		downlinkPhysChCapability					DL-PhysChCapabilityInfoTDD-128-va40ext,
		uplinkPhysChCapability					UL-PhysChCapabilityInfoTDD-128-va40ext
	}		OPTIONAL
}

PhysicalChannelCapability-vb50ext ::=	SEQUENCE {
	fddPhysChCapability						SEQUENCE {
		downlinkPhysChCapability					DL-PhysChCapabilityFDD-vb50ext,
		uplinkPhysChCapability					UL-PhysChCapabilityFDD-vb50ext
	}		OPTIONAL
}

PhysicalChannelCapability-vb80ext ::=	SEQUENCE {
	fddPhysChCapability						SEQUENCE {
		downlinkPhysChCapability					DL-PhysChCapabilityFDD-vb80ext
	}		OPTIONAL
}

PhysicalChannelCapability-vc50ext ::=	SEQUENCE {
	fddPhysChCapability						SEQUENCE {
		downlinkPhysChCapability					DL-PhysChCapabilityFDD-vc50ext	OPTIONAL,
		uplinkPhysChCapability					UL-PhysChCapabilityFDD-vc50ext	OPTIONAL
	}		OPTIONAL,
	tddPhysChCapability						SEQUENCE {
		downlinkPhysChCapability					DL-PhysChCapabilityInfoTDD-128-vc50ext
	}		OPTIONAL
}

PhysicalChannelCapability-vd20ext ::=	SEQUENCE {
	fddPhysChCapability						SEQUENCE {
		downlinkPhysChCapability					DL-PhysChCapabilityFDD-vd20ext	OPTIONAL,
		uplinkPhysChCapability					UL-PhysChCapabilityFDD-vd20ext	OPTIONAL
	}		OPTIONAL
}
PhysicalChannelCapability-ve30ext ::=	SEQUENCE {
	fddPhysChCapability						SEQUENCE {
		downlinkPhysChCapability					DL-PhysChCapabilityFDD-ve30ext	OPTIONAL,
		uplinkPhysChCapability					UL-PhysChCapabilityFDD-ve30ext	OPTIONAL
	}		OPTIONAL
}

PhysicalChannelCapabilityInfo-v770ext ::= SEQUENCE {
	tddPhysChCapability-768					SEQUENCE {
		downlinkPhysChCapability					DL-PhysChCapabilityInfoTDD-768,
		uplinkPhysChCapability					UL-PhysChCapabilityTDD
	}		OPTIONAL,
	tddPhysChCapability-128					SEQUENCE {
		uplinkPhysChCapability					UL-PhysChCapabilityInfoTDD-128-v770ext
	}		OPTIONAL
}

PhysicalChannelCapability-vf10ext ::=	SEQUENCE {
	fddPhysChCapability						SEQUENCE {
		downlinkPhysChCapability					DL-PhysChCapabilityFDD-vf10ext	OPTIONAL
		}
}

-- PhysicalChannelCapability-LCR-r4 describes the 1.28Mcps TDD physical channel capability
PhysicalChannelCapability-LCR-r4 ::=		SEQUENCE {
		tdd128-PhysChCapability				SEQUENCE {
			downlinkPhysChCapability				DL-PhysChCapabilityTDD-LCR-r4,
			uplinkPhysChCapability				UL-PhysChCapabilityTDD-LCR-r4
		}											OPTIONAL
}

-- PhysicalChannelCapability-hspdsch-r5 describes the HS-PDSCH physical channel capability
PhysicalChannelCapability-hspdsch-r5 ::=		SEQUENCE {
	fdd-hspdsch									CHOICE {
		supported										SEQUENCE {
			-- hsdsch-physical-layer-category values shall be restricted to the range [1..12]
			-- even if the UE physical capability category is above 12.
			hsdsch-physical-layer-category					HSDSCH-physical-layer-category,
			-- dummy and dummy2 are not used in this version of the specification
			-- and if received they should be ignored.
			dummy											BOOLEAN,
			dummy2											BOOLEAN
		},
		unsupported										NULL
	},
	tdd384-hspdsch									CHOICE {
		supported										HSDSCH-physical-layer-category,
		unsupported									NULL
	},
	tdd128-hspdsch									CHOICE {
		supported										HSDSCH-physical-layer-category,
		unsupported									NULL
	}
}

PNBSCH-Allocation-r4 ::=				SEQUENCE {
	numberOfRepetitionsPerSFNPeriod		ENUMERATED {
												c2, c3, c4, c5, c6, c7, c8, c9, c10,
												c12, c14, c16, c18, c20, c24, c28, c32,
												c36, c40, c48, c56, c64, c72, c80  }
}

Pre-RedirectionInfo ::=				SEQUENCE {
		supportEUTRA-FDD					BOOLEAN,
		supportEUTRA-TDD					BOOLEAN
}

ProtocolErrorCause ::=			ENUMERATED {
										asn1-ViolationOrEncodingError,
										messageTypeNonexistent,
										messageNotCompatibleWithReceiverState,
										ie-ValueNotComprehended,
										informationElementMissing,
										messageExtensionNotComprehended,
										spare2, spare1 }

ProtocolErrorIndicator ::=		ENUMERATED {
										noError, errorOccurred }

ProtocolErrorIndicatorWithMoreInfo ::= 	CHOICE {
	noError										NULL,
	errorOccurred								SEQUENCE {
		rrc-TransactionIdentifier					RRC-TransactionIdentifier,
		protocolErrorInformation					ProtocolErrorInformation
	}
}

ProtocolErrorMoreInformation ::=	SEQUENCE {
	diagnosticsType					CHOICE {
		type1								CHOICE {
			asn1-ViolationOrEncodingError		NULL,
			messageTypeNonexistent			NULL,
			messageNotCompatibleWithReceiverState
												IdentificationOfReceivedMessage,
			ie-ValueNotComprehended			IdentificationOfReceivedMessage,
			conditionalInformationElementError	IdentificationOfReceivedMessage,
			messageExtensionNotComprehended	IdentificationOfReceivedMessage,
			spare1								NULL,
			spare2								NULL
		},
		spare								NULL
	}
}

RadioFrequencyBandEUTRA ::=			INTEGER (1..64)

RadioFrequencyBandEUTRAExt ::=		INTEGER (65..256)

RadioFrequencyBandEUTRAExt2 ::=		INTEGER (1..256)

RadioFrequencyBandFDD ::=			ENUMERATED {
	-- fdd2100, fdd1900, fdd1800 correspond to Band I, Band II and Band III respectively
										fdd2100,
										fdd1900,
										fdd1800,
										bandVI,
										bandIV,
										bandV,
										bandVII,
										extension-indicator }

RadioFrequencyBandFDD2 ::=		ENUMERATED {
										bandVIII,
										bandIX,
										bandX,
										bandXI,
										bandXII,
										bandXIII,
										bandXIV,
										bandXV,
										bandXVI,
										bandXVII,
										bandXVIII,
										bandXIX,
										bandXX,
										bandXXI,
										bandXXII,
										extension-indicator }

RadioFrequencyBandFDD3 ::=		ENUMERATED {spare64, spare63, bandXXV, bandXXVI, spare60, spare59, spare58, spare57, spare56, bandXXXII, spare54, spare53, spare52, spare51, spare50, spare49, spare48, spare47, spare46, spare45, spare44, spare43, spare42, spare41, spare40, spare39, spare38, spare37, spare36, spare35, spare34, spare33, spare32, spare31, spare30, spare29, spare28, spare27, spare26, spare25, spare24, spare23, spare22, spare21, spare20, spare19, spare18, spare17, spare16, spare15, spare14, spare13, spare12, spare11, spare10, spare9, spare8, spare7, spare6, spare5, spare4, spare3, spare2, extension-indicator }

RadioFrequencyBandTDDList ::=		ENUMERATED {
										a, b, c, ab, ac, bc, abc, spare }

RadioFrequencyBandTDDList-r7 ::=	ENUMERATED {
										a, b, c, d, ab, ac, ad, bc, bd, cd, abc, abd, acd, bcd,
										abcd, notabcd }

RadioFrequencyBandTDDext ::=		ENUMERATED {
										e, f, g, h, i, j, k, l, m, n, o, p, spare4, spare3,
										spare2, spare1 }

RadioFrequencyBandTDDextList ::=	SEQUENCE (SIZE (1..maxFreqBandsTDD-ext)) OF
										RadioFrequencyBandTDDext

RadioFrequencyBandTDD ::=			ENUMERATED {
										a, b, c, d }

RadioFrequencyBandTDD-r10 ::=		ENUMERATED {
										a, b, c, d, e, f, spare2, spare1 }

RadioFrequencyBandGSM ::=			ENUMERATED {
										gsm450,
										gsm480,
										gsm850,
										gsm900P,
										gsm900E,
										gsm1800,
										gsm1900,
										spare9, spare8, spare7, spare6, spare5,
										spare4, spare3, spare2, spare1}

Rb-timer-indicator ::=			SEQUENCE {
	t314-expired						BOOLEAN,
	t315-expired						BOOLEAN }

Re-EstablishmentTimer ::=			ENUMERATED {
										useT314, useT315
}

RedirectionInfo ::=				CHOICE {
	frequencyInfo						FrequencyInfo,
	interRATInfo						InterRATInfo
}

RedirectionInfo-r6 ::=			CHOICE {
	frequencyInfo						FrequencyInfo,
	interRATInfo						InterRATInfo-r6
}

RedirectionInfo-v860ext ::=		CHOICE {
	-- CHOICE frequencyInfo is provided in IE RedirectionInfo or IE RedirectionInfo-r6
	frequencyInfo						NULL,
	interRATInfo						InterRATInfo-v860ext
}

RejectionCause ::=					ENUMERATED {
										congestion,
										unspecified }

ReleaseCause ::=					ENUMERATED {
										normalEvent,
										unspecified,
										pre-emptiveRelease,
										congestion,
										re-establishmentReject,
										directedsignallingconnectionre-establishment,
										userInactivity,
										spare }

RF-Capability ::=					SEQUENCE {
		fddRF-Capability				SEQUENCE {
			ue-PowerClass					UE-PowerClass,
			txRxFrequencySeparation		TxRxFrequencySeparation
		}									OPTIONAL,
		tddRF-Capability				SEQUENCE {
			ue-PowerClass					UE-PowerClass,
			radioFrequencyTDDBandList		RadioFrequencyBandTDDList,
			chipRateCapability				ChipRateCapability
		}									OPTIONAL
}

RF-Capability-r4-ext ::=				SEQUENCE {
		tddRF-Capability					SEQUENCE {
			ue-PowerClass						UE-PowerClass,
			radioFrequencyBandTDDList			RadioFrequencyBandTDDList,
			chipRateCapability					ChipRateCapability
		}									OPTIONAL
}

RF-Capability-v770ext ::=		SEQUENCE {
	-- If TDD384 and/or TDD128 RF capability is indicated in IEs 'RF-Capability' or
	-- 'RF-Capability-r4-ext', the corresponding IE 'RadioFrequencyBandTDDList-r7' shall
	-- be included in this IE.
	tdd384RF-Capability				RadioFrequencyBandTDDList-r7				OPTIONAL,
	tdd768RF-Capability				SEQUENCE {
		ue-PowerClass						UE-PowerClass,
		radioFrequencyBandTDDList			RadioFrequencyBandTDDList-r7
		-- The element 'chipRateCapability' = 'mcps7-68'
	}		OPTIONAL,
	tdd128RF-Capability				RadioFrequencyBandTDDList-r7				OPTIONAL
}

RF-Capability-v860ext ::=			SEQUENCE {
	tdd128RF-Capability					RadioFrequencyBandTDDextList			OPTIONAL,
	tdd384RF-Capability					RadioFrequencyBandTDDextList			OPTIONAL,
	tdd768RF-Capability					RadioFrequencyBandTDDextList			OPTIONAL
}

RF-Capability-vaa0ext ::=			SEQUENCE {
	supportOfMFBI						ENUMERATED { true }						OPTIONAL
}

RLC-Capability ::=					SEQUENCE {
	-- If present, the "totalRLC-AM-BufferSize" in the IE "RLC-Capability-r5-ext" overrides the
	-- corresponding value in this IE. The value in this IE may be used by a pre-REL-5 UTRAN.
	totalRLC-AM-BufferSize			TotalRLC-AM-BufferSize,
	maximumRLC-WindowSize				MaximumRLC-WindowSize,
	maximumAM-EntityNumber			MaximumAM-EntityNumberRLC-Cap
}

RLC-Capability-r5-ext ::=			SEQUENCE {
	totalRLC-AM-BufferSize			TotalRLC-AM-BufferSize-r5-ext				OPTIONAL
}

RLC-Capability-v770ext ::=			SEQUENCE {
	supportOfTwoLogicalChannel			BOOLEAN
}

RLC-Capability-v920ext ::=			SEQUENCE {
	totalRLC-AM-BufferSize				TotalRLC-AM-BufferSize-v920ext		OPTIONAL
}

RLC-Capability-va40ext ::=			SEQUENCE {
	totalRLC-AM-BufferSize				TotalRLC-AM-BufferSize-va40ext		OPTIONAL
}

RLC-Capability-vb50ext ::=			SEQUENCE {
	totalRLC-AM-BufferSize				TotalRLC-AM-BufferSize-vb50ext		OPTIONAL
}

RRC-ConnectionReleaseInformation ::=	CHOICE {
	noRelease								NULL,
	release									SEQUENCE {
		releaseCause							ReleaseCause
	}
}

RRC-MessageSequenceNumber ::=		INTEGER (0..15)


RRC-MessageSequenceNumberList ::=	SEQUENCE (SIZE (4..5)) OF
											RRC-MessageSequenceNumber

RRC-StateIndicator ::=			ENUMERATED {
										cell-DCH, cell-FACH, cell-PCH, ura-PCH }

RRC-TransactionIdentifier ::=		INTEGER (0..3)

RSR-VCC-Info ::=					SEQUENCE {
	nonce								BIT STRING (SIZE (128))					OPTIONAL,
	ims-Information					OCTET STRING (SIZE (1.. 32))
}

S-RNTI ::=							BIT STRING (SIZE (20))

S-RNTI-2 ::=						BIT STRING (SIZE (10))

SecurityCapability ::=			SEQUENCE {
	cipheringAlgorithmCap				BIT STRING {
										-- For each bit value "0" means false/ not supported
											spare15(0),
											spare14(1),
											spare13(2),
											spare12(3),
											spare11(4),
											spare10(5),
											spare9(6),
											spare8(7),
											spare7(8),
											spare6(9),
											spare5(10),
											spare4(11),
											spare3(12),
											uea2(13),
											uea1(14),
											uea0(15)
											}	(SIZE (16)),
	integrityProtectionAlgorithmCap		BIT STRING {
										-- For each bit value "0" means false/ not supported
											spare15(0),
											spare14(1),
											spare13(2),
											spare12(3),
											spare11(4),
											spare10(5),
											spare9(6),
											spare8(7),
											spare7(8),
											spare6(9),
											spare5(10),
											spare4(11),
											spare3(12),
											uia2(13),
											uia1(14),
											spare0(15)
										 	} 	 (SIZE (16))
}

SecondaryServingEDCHCell-Info ::=	SEQUENCE {
	primary-E-RNTI							E-RNTI										OPTIONAL,
	secondary-E-RNTI						E-RNTI										OPTIONAL
	}

SecondaryEDCH-Info-Common ::=		SEQUENCE {
	frequencyInfo							FrequencyInfo,
	scramblingCodeType						ScramblingCodeType,
	scramblingCodeNumber					UL-ScramblingCode,
	ms2-SchedTransmGrantHARQAlloc		BIT STRING (SIZE (8))						OPTIONAL,
	servingGrant							SEQUENCE {
		primary-Secondary-GrantSelector		ENUMERATED { primary, secondary }
	}		OPTIONAL,
	minReduced-E-DPDCH-GainFactor		MinReduced-E-DPDCH-GainFactor			OPTIONAL,
	e-DCH-minimumSet-E-TFCI				E-DCH-MinimumSet-E-TFCI					OPTIONAL,
	dpcchPowerOffset-SecondaryULFrequency	INTEGER(0..7),
	pc-Preamble							PC-Preamble
}

SecondaryEDCH-Info-Common-r12 ::=	SEQUENCE {
	frequencyInfo							FrequencyInfo,
	scramblingCodeType						ScramblingCodeType,
	scramblingCodeNumber					UL-ScramblingCode,
	ms2-SchedTransmGrantHARQAlloc		BIT STRING (SIZE (8))						OPTIONAL,
	servingGrant							SEQUENCE {
		primary-Secondary-GrantSelector		ENUMERATED { primary, secondary }
	}		OPTIONAL,
	minReduced-E-DPDCH-GainFactor		MinReduced-E-DPDCH-GainFactor			OPTIONAL,
	e-DCH-minimumSet-E-TFCI				E-DCH-MinimumSet-E-TFCI					OPTIONAL,
	minimumTEBS-threshold					MinimumTEBS-threshold						OPTIONAL,
	implicitGrantHandling					ENUMERATED { true }						OPTIONAL,
	dpcchPowerOffset-SecondaryULFrequency	INTEGER(0..7),
	pc-Preamble							PC-Preamble,
	ue-DPCCHPowerResetAfterDTXOnSecUplink	UE-DPCCHPowerResetAfterDTXOnSecUplink	OPTIONAL
}

SecondaryEDCH-Info-Common-r14 ::=	SEQUENCE {
	frequencyInfo							FrequencyInfo,
	scramblingCodeType						ScramblingCodeType,
	scramblingCodeNumber					UL-ScramblingCode,
	ms2-SchedTransmGrantHARQAlloc		BIT STRING (SIZE (8))						OPTIONAL,
	servingGrant							SEQUENCE {
		primary-Secondary-GrantSelector		ENUMERATED { primary, secondary }
	}		OPTIONAL,
	minReduced-E-DPDCH-GainFactor		MinReduced-E-DPDCH-GainFactor			OPTIONAL,
	e-DCH-minimumSet-E-TFCI				E-DCH-MinimumSet-E-TFCI					OPTIONAL,
	minimumTEBS-threshold					MinimumTEBS-threshold						OPTIONAL,
	implicitGrantHandling					ENUMERATED { true }						OPTIONAL,
	dpcchPowerOffset-SecondaryULFrequency	INTEGER(0..7),
	pc-Preamble							PC-Preamble,
	ue-DPCCHPowerResetAfterDTXOnSecUplink	UE-DPCCHPowerResetAfterDTXOnSecUplink	OPTIONAL,
	additionalSecondaryCellInfoForMixedTTIConfiguration				AdditionalSecondaryCellInfoForMixedTTIConfiguration				OPTIONAL
}

Serving-HSDSCH-CellInformation ::=	SEQUENCE {
	deltaACK						DeltaACK							OPTIONAL,
	deltaNACK						DeltaNACK							OPTIONAL,
	harq-Preamble-Mode				HARQ-Preamble-Mode,
	primaryCPICH-Info				PrimaryCPICH-Info					OPTIONAL,
	dl-hspdsch-Information		DL-HSPDSCH-Information			OPTIONAL,
	harqInfo						HARQ-Info 							OPTIONAL,
	mac-hsResetIndicator			ENUMERATED { true }				OPTIONAL
}

Serving-HSDSCH-CellInformation-r7 ::=	SEQUENCE {
	deltaACK						DeltaACK							OPTIONAL,
	deltaNACK						DeltaNACK							OPTIONAL,
	harq-Preamble-Mode				HARQ-Preamble-Mode,
	primaryCPICH-Info				PrimaryCPICH-Info					OPTIONAL,
	dl-hspdsch-Information		DL-HSPDSCH-Information-r7			OPTIONAL,
	harqInfo						HARQ-Info-r7						OPTIONAL,
	mac-hsResetIndicator			ENUMERATED { true }				OPTIONAL
}

Serving-HSDSCH-CellInformation-r8 ::=	SEQUENCE {
	deltaACK						DeltaACK							OPTIONAL,
	deltaNACK						DeltaNACK							OPTIONAL,
	harq-Preamble-Mode				HARQ-Preamble-Mode,
	primaryCPICH-Info				PrimaryCPICH-Info					OPTIONAL,
	dl-hspdsch-Information		DL-HSPDSCH-Information-r8			OPTIONAL,
	harqInfo						HARQ-Info-r7						OPTIONAL,
	mac-hsResetIndicator			ENUMERATED { true }				OPTIONAL
}

Serving-HSDSCH-CellInformation-r9 ::=	SEQUENCE {
	deltaACK						DeltaACK							OPTIONAL,
	deltaNACK						DeltaNACK							OPTIONAL,
	harq-Preamble-Mode				HARQ-Preamble-Mode,
	primaryCPICH-Info				PrimaryCPICH-Info					OPTIONAL,
	dl-hspdsch-Information		DL-HSPDSCH-Information-r9			OPTIONAL,
	harqInfo						HARQ-Info-r7						OPTIONAL,
	mac-hsResetIndicator			ENUMERATED { true }				OPTIONAL
}

Serving-HSDSCH-CellInformation-r11 ::=	SEQUENCE {
	deltaACK						DeltaACK-r11						OPTIONAL,
	deltaNACK						DeltaNACK-r11						OPTIONAL,
	harq-Preamble-Mode				HARQ-Preamble-Mode,
	primaryCPICH-Info				PrimaryCPICH-Info					OPTIONAL,
	dl-hspdsch-Information		DL-HSPDSCH-Information-r11		OPTIONAL,
	harqInfo						HARQ-Info-r11						OPTIONAL,
	mac-hsResetIndicator			ENUMERATED { true }				OPTIONAL,
	mac-hsResetIndicator-assisting	ENUMERATED { true }			OPTIONAL
}

Serving-HSDSCH-CellInformation-r12 ::=	SEQUENCE {
	deltaACK						DeltaACK-r11						OPTIONAL,
	deltaNACK						DeltaNACK-r11						OPTIONAL,
	harq-Preamble-Mode				HARQ-Preamble-Mode,
	primaryCPICH-Info				PrimaryCPICH-Info					OPTIONAL,
	dl-hspdsch-Information		DL-HSPDSCH-Information-r12		OPTIONAL,
	harqInfo						HARQ-Info-r11						OPTIONAL,
	mac-hsResetIndicator			ENUMERATED { true }				OPTIONAL,
	mac-hsResetIndicator-assisting	ENUMERATED { true }			OPTIONAL
}

SimultaneousSCCPCH-DPCH-Reception ::=	CHOICE {
	notSupported						NULL,
	supported							SEQUENCE {
		maxNoSCCPCH-RL						MaxNoSCCPCH-RL,
		-- simultaneousSCCPCH-DPCH-DPDCH-Reception is applicable only if
		-- the IE Support of PDSCH = TRUE
		-- Note: the reference to DPDCH in the element name below is incorrect (see tabular). The
		-- name is not changed, to keep it aligned with R99.
		simultaneousSCCPCH-DPCH-DPDCH-Reception		BOOLEAN
	}
}

SRNC-Identity ::=					BIT STRING (SIZE (12))

SR-VCC-Info ::=					SEQUENCE {
	nonce								BIT STRING (SIZE (128))		OPTIONAL
}

SR-VCC-SecurityRABInfo-v860ext ::=	SEQUENCE {
	sr-vcc-Info							SR-VCC-Info,
	rab-InfoReplace						RAB-InfoReplace
}

START-Value ::=						BIT STRING (SIZE (20))

STARTList ::=						SEQUENCE (SIZE (1..maxCNdomains)) OF
										STARTSingle

STARTSingle ::=					SEQUENCE {
	cn-DomainIdentity					CN-DomainIdentity,
	start-Value							START-Value
}

SystemSpecificCapUpdateReq ::=	ENUMERATED {
										gsm }

SystemSpecificCapUpdateReq-v590ext ::=		ENUMERATED {
													geranIu }

SystemSpecificCapUpdateReq-r5 ::=		ENUMERATED {
												gsm, geranIu }

SystemSpecificCapUpdateReq-r8 ::=	ENUMERATED {
											gsm, geranIu, eutra, spare5,
											spare4, spare3, spare2, spare1 }

SystemSpecificCapUpdateReqList ::=	SEQUENCE (SIZE (1..maxSystemCapability)) OF
											SystemSpecificCapUpdateReq

SystemSpecificCapUpdateReqList-r5 ::=	SEQUENCE (SIZE (1..maxSystemCapability)) OF
												SystemSpecificCapUpdateReq-r5

SystemSpecificCapUpdateReqList-r8 ::=	SEQUENCE (SIZE (1..maxSystemCapability)) OF
												SystemSpecificCapUpdateReq-r8

T-300 ::=							ENUMERATED {
										ms100, ms200, ms400, ms600, ms800,
										ms1000, ms1200, ms1400, ms1600,
										ms1800, ms2000, ms3000, ms4000,
										ms6000, ms8000 }

T-301 ::=							ENUMERATED {
										ms100, ms200, ms400, ms600, ms800,
										ms1000, ms1200, ms1400, ms1600,
										ms1800, ms2000, ms3000, ms4000,
										ms6000, ms8000, spare }

T-302 ::=							ENUMERATED {
										ms100, ms200, ms400, ms600, ms800,
										ms1000, ms1200, ms1400, ms1600,
										ms1800, ms2000, ms3000, ms4000,
										ms6000, ms8000, spare }

T-304 ::=							ENUMERATED {
										ms100, ms200, ms400,
										ms1000, ms2000, spare3, spare2, spare1 }

T-305 ::=							ENUMERATED {
										noUpdate, m5, m10, m30,
										m60, m120, m360, m720 }

T-307 ::=							ENUMERATED {
										s5, s10, s15, s20,
										s30, s40, s50, spare }

T-308 ::=							ENUMERATED {
										ms40, ms80, ms160, ms320 }

T-309 ::=							INTEGER (1..8)

T-310 ::=							ENUMERATED {
										ms40, ms80, ms120, ms160,
										ms200, ms240, ms280, ms320 }

T-311 ::=							ENUMERATED {
										ms250, ms500, ms750, ms1000,
										ms1250, ms1500, ms1750, ms2000 }

-- The value 0 for T-312 is not used in this version of the specification
T-312 ::=							INTEGER (0..15)

T-313 ::=							INTEGER (0..15)

T-314 ::=							ENUMERATED {
										s0, s2, s4, s6, s8,
										s12, s16, s20 }

T-315 ::=							ENUMERATED {
										s0, s10, s30, s60, s180,
										s600, s1200, s1800 }

T-316 ::=							ENUMERATED {
										s0, s10, s20, s30, s40,
										s50, s-inf, spare }

-- All the values are changed to "infinity" in Rel-5
T-317 ::=							ENUMERATED {
										infinity0,  infinity1,  infinity2, infinity3, infinity4,
										infinity5, infinity6, infinity7}

T-318 ::=							ENUMERATED {
										ms250, ms500, ms750, ms1000, ms1250, ms1500,
										ms1750, ms2000, ms3000, ms4000, ms6000, ms8000,
										ms10000, ms12000, ms16000 }

T-319 ::=							ENUMERATED {
										ms80, ms160, ms320, ms640, ms1280, ms2560, ms5120 }

T-321 ::=							ENUMERATED {
										ms100, ms200, ms400, ms800 }

T-322 ::=							ENUMERATED { m5, m10, m20, m30, m60,
										m120, m180, spare1 }

T-323 ::=							ENUMERATED { s0, s5, s10, s20, s30, s60, s90, s120 }

T-328 ::=							ENUMERATED { ms20, ms40, ms60, ms80 }

T-329 ::=							ENUMERATED { s05p, s1, s2, s4 }
T-330 ::=							ENUMERATED { m5, m10, m20, m30,
										m60, m120, m180, spare1 }

T-CPCH ::=							ENUMERATED {
										ct0, ct1 }

TMSI-and-LAI-GSM-MAP ::=			SEQUENCE {
	tmsi								TMSI-GSM-MAP,
	lai									LAI
}

TMSI-DS-41 ::=						OCTET STRING (SIZE (2..17))

TotalRLC-AM-BufferSize ::=		ENUMERATED {
										dummy, kb10, kb50, kb100,
										kb150, kb500, kb1000, spare }

TotalRLC-AM-BufferSize-r5-ext ::=	ENUMERATED {
										kb200, kb300, kb400, kb750 }

TotalRLC-AM-BufferSize-v920ext ::=	ENUMERATED {
										kb1150, kb1250 }

TotalRLC-AM-BufferSize-va40ext ::=	ENUMERATED {
										kb1500, kb1800, kb2300, kb2550 }

TotalRLC-AM-BufferSize-vb50ext ::=	ENUMERATED {
										kb3400, kb3500, kb4400, kb4500, kb5000, spare3, spare2, spare1 }

-- Actual value TransmissionProbability = IE value * 0.125
TransmissionProbability ::=			INTEGER (1..8)

TransportChannelCapability ::=	SEQUENCE {
	dl-TransChCapability				DL-TransChCapability,
	ul-TransChCapability				UL-TransChCapability
}

TurboSupport ::=					CHOICE {
	notSupported						NULL,
	supported							MaxNoBits
}

-- Values defined as spare shall not be sent in this version of the protocol. If a spare value is
-- received, it should be interpreted as 'default-RxTX-sparation'.
TxRxFrequencySeparation ::=		ENUMERATED {
										default-TxRx-separation, spare2, spare1 }

U-RNTI ::=							SEQUENCE {
	srnc-Identity						SRNC-Identity,
	s-RNTI								S-RNTI
}

U-RNTI-Group ::=					CHOICE {
-- TABULAR: not following the tabular strictly, but this will most likely save bits
	all										NULL,
	u-RNTI-BitMaskIndex-b1				BIT STRING (SIZE (31)),
	u-RNTI-BitMaskIndex-b2				BIT STRING (SIZE (30)),
	u-RNTI-BitMaskIndex-b3				BIT STRING (SIZE (29)),
	u-RNTI-BitMaskIndex-b4				BIT STRING (SIZE (28)),
	u-RNTI-BitMaskIndex-b5				BIT STRING (SIZE (27)),
	u-RNTI-BitMaskIndex-b6				BIT STRING (SIZE (26)),
	u-RNTI-BitMaskIndex-b7				BIT STRING (SIZE (25)),
	u-RNTI-BitMaskIndex-b8				BIT STRING (SIZE (24)),
	u-RNTI-BitMaskIndex-b9				BIT STRING (SIZE (23)),
	u-RNTI-BitMaskIndex-b10				BIT STRING (SIZE (22)),
	u-RNTI-BitMaskIndex-b11				BIT STRING (SIZE (21)),
	u-RNTI-BitMaskIndex-b12				BIT STRING (SIZE (20)),
	u-RNTI-BitMaskIndex-b13				BIT STRING (SIZE (19)),
	u-RNTI-BitMaskIndex-b14				BIT STRING (SIZE (18)),
	u-RNTI-BitMaskIndex-b15				BIT STRING (SIZE (17)),
	u-RNTI-BitMaskIndex-b16				BIT STRING (SIZE (16)),
	u-RNTI-BitMaskIndex-b17				BIT STRING (SIZE (15)),
	u-RNTI-BitMaskIndex-b18				BIT STRING (SIZE (14)),
	u-RNTI-BitMaskIndex-b19				BIT STRING (SIZE (13)),
	u-RNTI-BitMaskIndex-b20				BIT STRING (SIZE (12)),
	u-RNTI-BitMaskIndex-b21				BIT STRING (SIZE (11)),
	u-RNTI-BitMaskIndex-b22				BIT STRING (SIZE (10)),
	u-RNTI-BitMaskIndex-b23				BIT STRING (SIZE (9)),
	u-RNTI-BitMaskIndex-b24				BIT STRING (SIZE (8)),
	u-RNTI-BitMaskIndex-b25				BIT STRING (SIZE (7)),
	u-RNTI-BitMaskIndex-b26				BIT STRING (SIZE (6)),
	u-RNTI-BitMaskIndex-b27				BIT STRING (SIZE (5)),
	u-RNTI-BitMaskIndex-b28				BIT STRING (SIZE (4)),
	u-RNTI-BitMaskIndex-b29				BIT STRING (SIZE (3)),
	u-RNTI-BitMaskIndex-b30				BIT STRING (SIZE (2)),
	u-RNTI-BitMaskIndex-b31				BIT STRING (SIZE (1))
}

U-RNTI-Short ::=					SEQUENCE {
	srnc-Identity						SRNC-Identity,
	s-RNTI-2							S-RNTI-2
}

UE-AddPos-Supported-List ::= 		SEQUENCE (SIZE (1..maxAddPos)) OF UE-AddPos-element

UE-AddPos-element ::=	SEQUENCE{
	addPos-ID							ENUMERATED {barometricPressure, wlan, bt, mbs,
														spare4, spare3, spare2, spare1 },
	addPos-Mode						 ENUMERATED {standalone, ue-assisted,
																	both, spare1 }

}

UE-BasedNetworkPerformanceMeasurementsParameters ::= 	SEQUENCE {
	supportOfLoggedMeasurementsIdlePCH	ENUMERATED { true }				OPTIONAL
}

UE-CapabilityContainer-IEs ::=			SEQUENCE {
-- Container for transparent transfer of capability information not related to
-- features for which early implementation is desired
		ue-RadioAccessCapability-v690ext	UE-RadioAccessCapability-v690ext,
		ue-RATSpecificCapability-v690ext	InterRAT-UE-RadioAccessCapability-v690ext	OPTIONAL,
		v6b0NonCriticalExtensions			SEQUENCE {
			ue-RadioAccessCapability-v6b0ext	UE-RadioAccessCapability-v6b0ext-IEs,
			v6e0NonCriticalExtensions			SEQUENCE {
				ue-RadioAccessCapability-v6e0ext	UE-RadioAccessCapability-v6e0ext-IEs,
				v770NonCriticalExtensions			SEQUENCE {
					ue-RadioAccessCapability-v770ext	UE-RadioAccessCapability-v770ext-IEs,
					v790NonCriticalExtensions			SEQUENCE {
						ue-RadioAccessCapability-v790ext	UE-RadioAccessCapability-v790ext-IEs,
						v860NonCriticalExtensions			SEQUENCE {
							ue-RadioAccessCapability-v860ext
															UE-RadioAccessCapability-v860ext-IEs,
							ue-RATSpecificCapability-v860ext
											InterRAT-UE-RadioAccessCapability-v860ext	OPTIONAL,
							v880NonCriticalExtensions			SEQUENCE {
								ue-RadioAccessCapability-v880ext
															UE-RadioAccessCapability-v880ext-IEs,
								v890NonCriticalExtensions			SEQUENCE {
									ue-RadioAccessCapability-v890ext
															UE-RadioAccessCapability-v890ext-IEs,
									v920NonCriticalExtensions			SEQUENCE {
										ue-RadioAccessCapability-v920ext
															UE-RadioAccessCapability-v920ext-IEs,
										v970NonCriticalExtensions			SEQUENCE {
											ue-RadioAccessCapability-v970ext
															UE-RadioAccessCapability-v970ext-IEs,
											va40NonCriticalExtensions			SEQUENCE {
												ue-RadioAccessCapability-va40ext
															UE-RadioAccessCapability-va40ext-IEs,
												va60NonCriticalExtensions			SEQUENCE {
													ue-RadioAccessCapability-va60ext
														UE-RadioAccessCapability-va60ext-IEs,
													va80NonCriticalExtensions		SEQUENCE {
														ue-RadioAccessCapability-va80ext
															UE-RadioAccessCapability-va80ext-IEs,
														laterNonCriticalExtensions
															UE-RadioAccessCapability-LaterNonCriticalExtensions		OPTIONAL
													}		OPTIONAL
												}		OPTIONAL
											}		OPTIONAL
										}		OPTIONAL
									}		OPTIONAL
								}		OPTIONAL
							}		OPTIONAL
						}		OPTIONAL
					}		OPTIONAL
				}		OPTIONAL
			}		OPTIONAL
		}		OPTIONAL
}

UE-RadioAccessCapability-v6b0ext-IEs ::=		SEQUENCE {
	-- User equipment IEs
		supportForSIB11bis							ENUMERATED { true }				OPTIONAL
}

UE-RadioAccessCapability-v6e0ext-IEs ::=		SEQUENCE {
	-- User equipment IEs
		supportForFDPCH							ENUMERATED { true }				OPTIONAL
}

UE-RadioAccessCapability-v770ext-IEs ::=		SEQUENCE {
	-- User equipment IEs
		pdcp-Capability							PDCP-Capability-v770ext			OPTIONAL,
		rlc-Capability								RLC-Capability-v770ext,
		rf-Capability								RF-Capability-v770ext				OPTIONAL,
		physicalChannelCapability					PhysicalChannelCapability-v770ext,
		multiModeRAT-Capability					MultiModeRAT-Capability-v770ext,
		ue-PositioningCapability					UE-PositioningCapability-v770ext,
		mac-ehsSupport								ENUMERATED { true }				OPTIONAL,
		ue-specificCapabilityInformation	UE-SpecificCapabilityInformation-LCRTDD	OPTIONAL
}

UE-RadioAccessCapability-v790ext-IEs ::=		SEQUENCE {
	-- User equipment IEs
		supportForEDPCCHPowerBoosting				ENUMERATED { true }				OPTIONAL
}

UE-RadioAccessCapability-v860ext-IEs ::=		SEQUENCE {
	-- UE radio access capability
		rf-Capability						RF-Capability-v860ext						OPTIONAL,
		physicalChannelCapability			PhysicalChannelCapability-v860ext,
		multiModeRAT-Capability			MultiModeRAT-Capability-v860ext,
		ue-PositioningCapability			UE-PositioningCapability-v860ext,
		measurementCapability				MeasurementCapability-v860ext			OPTIONAL,
		measurementCapabilityTDD			MeasurementCapabilityTDD					OPTIONAL,
		supportOfCommonEDCH				ENUMERATED { true }						OPTIONAL,
		supportOfMACiis					ENUMERATED { true }						OPTIONAL,
		supportOfSPSOperation				ENUMERATED { true }						OPTIONAL,
		supportOfControlChannelDRXOperation	ENUMERATED { true }					OPTIONAL,
		supportOfCSG						ENUMERATED { true }						OPTIONAL,
	-- UE radio access capability extension
		ue-RadioAccessCapabBandFDDList3		UE-RadioAccessCapabBandFDDList3		OPTIONAL
}

UE-RadioAccessCapability-v880ext-IEs ::=		SEQUENCE {
	-- UE radio access capability
		supportForPriorityReselectionInUTRAN 	ENUMERATED { true }				OPTIONAL
}

UE-RadioAccessCapability-v890ext-IEs ::=		SEQUENCE {
	-- UE radio access capability
		supportCellSpecificTxDiversityinDC-Operation 	ENUMERATED { true }		OPTIONAL
}

UE-RadioAccessCapability-v920ext-IEs ::=		SEQUENCE {
	-- UE physical channel capability,
	ue-RadioAccessCapabBandCombList				UE-RadioAccessCapabBandCombList	OPTIONAL,
	physicalChannelCapability						PhysicalChannelCapability-v920ext,
	rlc-Capability									RLC-Capability-v920ext,
	supportOfenhancedTS0							ENUMERATED { true }				OPTIONAL,
	measurementCapability							MeasurementCapability-v920ext		OPTIONAL,
	-- UE radio access capability
	csgProximityIndicationCapability				CSG-ProximityIndicationCapability	OPTIONAL,
	neighCellSI-AcquisitionCapability			NeighCellSI-AcquisitionCapability	OPTIONAL
}

UE-RadioAccessCapability-v970ext-IEs ::=		SEQUENCE {
	-- UE physical channel capability
	ue-ExtendedMeasurementSupport				ENUMERATED { true }				OPTIONAL
}

UE-RadioAccessCapability-v9c0ext-IEs ::=		SEQUENCE {
	-- UE voice over IMS related capability
		voiceOverUTRA-PS-HS-Support				ENUMERATED { true }				OPTIONAL,
		srvcc-SupportFromUTRA-to-UTRA				ENUMERATED { true }				OPTIONAL,
		srvcc-SupportFromUTRA-to-GERAN			ENUMERATED { true }				OPTIONAL,
	-- UE radio access capability
	ue-supportMac-ehsWindowSizeExtension			ENUMERATED { true }				OPTIONAL
}

UE-RadioAccessCapability-LaterNonCriticalExtensions ::=	SEQUENCE {
	v9c0NonCriticalExtensions			SEQUENCE {
		ue-RadioAccessCapability-v9c0ext		UE-RadioAccessCapability-v9c0ext-IEs,
		vaa0NonCriticalExtensions		SEQUENCE	{
			ue-RadioAccessCapability-vaa0ext		UE-RadioAccessCapability-vaa0ext-IEs,
			vb50NonCriticalExtensions		SEQUENCE {
				ue-RadioAccessCapability-vb50ext		UE-RadioAccessCapability-vb50ext-IEs,
				vb70NonCriticalExtensions		SEQUENCE {
					ue-RadioAccessCapability-vb70ext		UE-RadioAccessCapability-vb70ext-IEs,
					vae0NonCriticalExtensions				SEQUENCE {
						ue-RadioAccessCapability-vae0ext	UE-RadioAccessCapability-vae0ext-IEs,
						vb80NonCriticalExtensions		SEQUENCE {
							ue-RadioAccessCapability-vb80ext	UE-RadioAccessCapability-vb80ext-IEs,
							vc50NonCriticalExtensions		SEQUENCE {
								ue-RadioAccessCapability-vc50ext
											UE-RadioAccessCapability-vc50ext-IEs,
								vd20NonCriticalExtensions			SEQUENCE {
									ue-RadioAccessCapability-vd20ext
											UE-RadioAccessCapability-vd20ext-IEs,
									ve30NonCriticalExtensions		UE-RadioAccessCapability-ve30ext-IEs OPTIONAL
								}		OPTIONAL
							}		OPTIONAL
						}		OPTIONAL
					}		OPTIONAL
				}		OPTIONAL
			}		OPTIONAL
		}		OPTIONAL
	}
}


UE-RadioAccessCapability-va40ext-IEs ::=		SEQUENCE {
	-- UE physical channel capability
	ue-RadioAccessCapabBandCombList-va40ext	UE-RadioAccessCapabBandCombList-va40ext		OPTIONAL,
	physicalChannelCapability					PhysicalChannelCapability-va40ext,
	rlc-Capability								RLC-Capability-va40ext,
	measurementCapability						MeasurementCapability-va40ext			OPTIONAL,
	supportOfMUMIMO							ENUMERATED { uplink, uplink-and-downlink }	OPTIONAL,
	supportForDualCellMimoInDifferentBands	ENUMERATED { true }					OPTIONAL,
	ue-BasedNetworkPerformanceMeasurementsParameters
								UE-BasedNetworkPerformanceMeasurementsParameters	OPTIONAL,
	supportOfUTRANANR							ENUMERATED { true }					OPTIONAL,
	-- UE radio access capability extension
	ue-RadioAccessCapabBandFDDList4			UE-RadioAccessCapabBandFDDList4		OPTIONAL
}

UE-RadioAccessCapability-va60ext-IEs ::=		SEQUENCE {
	ue-RadioAccessCapabBandFDDList4				UE-RadioAccessCapabBandFDDList4-va60ext		OPTIONAL
}

UE-RadioAccessCapability-va80ext-IEs ::=		SEQUENCE {
	ue-RadioAccessCapabBandFDDList4				UE-RadioAccessCapabBandFDDList4-va80ext		OPTIONAL
}

UE-RadioAccessCapability-vaa0ext-IEs ::=	SEQUENCE {
	supportOfUMRLCre-establish-via-reconfig	ENUMERATED { true }					OPTIONAL,
	rf-capability								RF-Capability-vaa0ext					OPTIONAL
}

UE-RadioAccessCapability-vae0ext-IEs ::=		SEQUENCE {
	-- UE radio access capability
		multiModeRAT-Capability					MultiModeRAT-Capability-vae0ext	OPTIONAL
}

UE-RadioAccessCapability-vb50ext-IEs ::=		SEQUENCE {
	multiModeRAT-Capability							MultiModeRAT-Capability-vb50ext,
	supportOfCommonERGCHBasedInterferenceControl	ENUMERATED { true }			OPTIONAL,
	supportOfFallbackToR99PRACH						ENUMERATED { true }			OPTIONAL,
	supportOfConcurrentDeployment					ENUMERATED { true }			OPTIONAL,
	supportOfTTIalignmentAndPerHARQProcess			ENUMERATED { true }			OPTIONAL,
	-- UE physical channel capability
	ue-RadioAccessCapabBandCombList-vb50ext			UE-RadioAccessCapabBandCombList-vb50ext		OPTIONAL,
	multiflowCapabBandCombList						MultiflowCapabBandCombList	OPTIONAL,
	physicalChannelCapability							PhysicalChannelCapability-vb50ext,
	rlc-Capability										RLC-Capability-vb50ext,
	multiflowCapability								MultiflowCapability			OPTIONAL,
	-- UE radio access capability extension
	ue-RadioAccessCapabBandFDDList6					UE-RadioAccessCapabBandFDDList6		OPTIONAL,
	-- Measurement capability
	measurementCapability								MeasurementCapability-vb50ext				OPTIONAL,
	measurementCapabilityTDD							MeasurementCapabilityTDD-vb50ext			OPTIONAL,
	-- UE voice over IMS related capability
	rsrvcc-SupportFromUTRA-CS-to-EUTRA-FDD			ENUMERATED { true }			OPTIONAL,
	rsrvcc-SupportFromUTRA-CS-to-EUTRA-TDD			ENUMERATED { true }			OPTIONAL,
	supportOfHSDPCCHPowerOffsetExtension				ENUMERATED { true }			OPTIONAL,
	supportOfSTTDOnDLControlChannelsWhenMultiflowOperationIsActive
														ENUMERATED { true }			OPTIONAL
}

UE-RadioAccessCapability-vb70ext-IEs ::=		SEQUENCE {
	measurementCapability							MeasurementCapability-vb70ext		OPTIONAL,
	ue-RadioAccessCapabBandFDDList7				UE-RadioAccessCapabBandFDDList7	OPTIONAL
}

UE-RadioAccessCapability-vb80ext-IEs ::=		SEQUENCE {
	-- UE physical channel capability
	physicalChannelCapability						PhysicalChannelCapability-vb80ext
}

UE-RadioAccessCapability-vc50ext-IEs ::=		SEQUENCE {
	--the capability is for FDD only
	measurementCapability							MeasurementCapability-vc50ext		OPTIONAL,
	supportofDsacAndPpacInCellDch				ENUMERATED { true }				OPTIONAL,
	supportOfMultiflowWithFTPICHFromAssisting	ENUMERATED { true }				OPTIONAL,
	multiModeRAT-Capability						MultiModeRAT-Capability-vc50ext	OPTIONAL,
	-- UE physical channel capability
	physicalChannelCapability						PhysicalChannelCapability-vc50ext	OPTIONAL
}

UE-RadioAccessCapability-vd20ext-IEs ::=		SEQUENCE {
	ue-RadioAccessCapabBandCombList		UE-RadioAccessCapabBandCombList-vd20ext	OPTIONAL,
	multiModeRAT-Capability						MultiModeRAT-Capability-vd20ext			OPTIONAL,
	-- UE physical channel capability
	physicalChannelCapability				PhysicalChannelCapability-vd20ext		OPTIONAL,
	-- UE positioning capability
	ue-PositioningCapability				UE-PositioningCapability-vd20ext			OPTIONAL,
	-- the capability is for FDD only
	supportofRetrievableConfigurations			ENUMERATED { true }						OPTIONAL,
	supportofURAPCHwithSeamlessTransition		ENUMERATED { true }						OPTIONAL,
	supportofImprovedSynchronizedRRCProcedures	ENUMERATED { true }						OPTIONAL,
	supportofEnhancedStateTransition			ENUMERATED { true }						OPTIONAL
}

UE-RadioAccessCapability-ve30ext-IEs ::=		SEQUENCE {
	measurementCapability							MeasurementCapability-ve30ext		OPTIONAL,
	supportofSimultaneousSetupandReleaseofRABsRBs	ENUMERATED { true }					OPTIONAL,
	physicalChannelCapability						PhysicalChannelCapability-ve30ext	OPTIONAL,
	ue-RadioAccessCapability-vf10ext    		UE-RadioAccessCapability-vf10ext-IEs    OPTIONAL
}

UE-RadioAccessCapability-vf10ext-IEs ::=		SEQUENCE {
	physicalChannelCapability					PhysicalChannelCapability-vf10ext   OPTIONAL,
	ue-RadioAccessCapability-vf20ext-IEs	    UE-RadioAccessCapability-vf20ext-IEs OPTIONAL
}

UE-RadioAccessCapability-vf20ext-IEs ::=		SEQUENCE {
	measurementCapability						MeasurementCapability-vf20ext		OPTIONAL,
	nonCriticalExtensions						SEQUENCE {}							OPTIONAL
}


UE-ConnTimersAndConstants ::=		SEQUENCE {
-- Optional is used also for parameters for which the default value is the last one read in SIB1
-- t-301 and n-301 should not be used by the UE in this version of the specification
	t-301								T-301								DEFAULT ms2000,
	n-301								N-301								DEFAULT 2,
	t-302								T-302								DEFAULT ms4000,
	n-302								N-302								DEFAULT 3,
	t-304								T-304								DEFAULT ms2000,
	n-304								N-304								DEFAULT 2,
	t-305								T-305								DEFAULT m30,
	t-307								T-307								DEFAULT s30,
	t-308								T-308								DEFAULT ms160,
	t-309								T-309								DEFAULT 5,
	t-310								T-310								DEFAULT ms160,
	n-310								N-310								DEFAULT 4,
	t-311								T-311								DEFAULT ms2000,
	t-312								T-312								DEFAULT 1,
	-- n-312 shall be ignored if n-312 in UE-ConnTimersAndConstants-v3a0ext is present, and the
	-- value of that element shall be used instead.
	n-312								N-312								DEFAULT s1,
	t-313								T-313								DEFAULT 3,
	n-313								N-313								DEFAULT s20,
	t-314								T-314								DEFAULT s12,
	t-315								T-315								DEFAULT s180,
	-- n-315 shall be ignored if n-315 in UE-ConnTimersAndConstants-v3a0ext is present, and the
	-- value of that element shall be used instead.
	n-315								N-315								DEFAULT s1,
	t-316								T-316								DEFAULT s30,
	t-317								T-317								DEFAULT infinity4
}

UE-ConnTimersAndConstants-v3a0ext ::=		SEQUENCE {
	n-312								N-312ext								OPTIONAL,
	n-315								N-315ext								OPTIONAL
}

UE-ConnTimersAndConstants-r5 ::=		SEQUENCE {
-- Optional is used also for parameters for which the default value is the last one read in SIB1
-- t-301 and n-301 should not be used by the UE in this version of the specification
	t-301								T-301								DEFAULT ms2000,
	n-301								N-301								DEFAULT 2,
	t-302								T-302								DEFAULT ms4000,
	n-302								N-302								DEFAULT 3,
	t-304								T-304								DEFAULT ms2000,
	n-304								N-304								DEFAULT 2,
	t-305								T-305								DEFAULT m30,
	t-307								T-307								DEFAULT s30,
	t-308								T-308								DEFAULT ms160,
	t-309								T-309								DEFAULT 5,
	t-310								T-310								DEFAULT ms160,
	n-310								N-310								DEFAULT 4,
	t-311								T-311								DEFAULT ms2000,
	t-312								T-312								DEFAULT 1,
	n-312								N-312-r5							DEFAULT s1,
	t-313								T-313								DEFAULT 3,
	n-313								N-313								DEFAULT s20,
	t-314								T-314								DEFAULT s12,
	t-315								T-315								DEFAULT s180,
	n-315								N-315-r5							DEFAULT s1,
	t-316								T-316								DEFAULT s30,
	t-317								T-317								DEFAULT infinity4
}

UE-ConnTimersAndConstants-v860ext ::=	SEQUENCE {
	t-323										T-323						OPTIONAL
}

UE-ConnTimersAndConstants-r11 ::=		SEQUENCE {
-- Optional is used also for parameters for which the default value is the last one read in SIB1
-- t-301 and n-301 should not be used by the UE in this version of the specification
	t-301								T-301								DEFAULT ms2000,
	n-301								N-301								DEFAULT 2,
	t-302								T-302								DEFAULT ms4000,
	n-302								N-302								DEFAULT 3,
	t-304								T-304								DEFAULT ms2000,
	n-304								N-304								DEFAULT 2,
	t-305								T-305								DEFAULT m30,
	t-307								T-307								DEFAULT s30,
	t-308								T-308								DEFAULT ms160,
	t-309								T-309								DEFAULT 5,
	t-310								T-310								DEFAULT ms160,
	n-310								N-310								DEFAULT 4,
	t-311								T-311								DEFAULT ms2000,
	t-312								T-312								DEFAULT 1,
	n-312								N-312-r5							DEFAULT s1,
	t-313								T-313								DEFAULT 3,
	n-313								N-313								DEFAULT s20,
	t-314								T-314								DEFAULT s12,
	t-315								T-315								DEFAULT s180,
	n-315								N-315-r5							DEFAULT s1,
	t-316								T-316								DEFAULT s30,
	t-317								T-317								DEFAULT infinity4,
	t-323								T-323								OPTIONAL
}

UE-GANSSPositioning-Capability ::=	SEQUENCE {
	networkAssistedGANSS-supportedList	NetworkAssistedGANSS-Supported-List	OPTIONAL
}

UE-GANSSPositioning-Capability-v860ext-IEs ::=	SEQUENCE {
	networkAssistedGANSS-supportedList	NetworkAssistedGANSS-Supported-List-v860ext	OPTIONAL
}

UE-IdleTimersAndConstants ::=		SEQUENCE {
	t-300								T-300,
	n-300								N-300,
	t-312								T-312,
	-- n-312 shall be ignored if n-312 in UE-IdleTimersAndConstants-v3a0ext is present, and the
	-- value of that element shall be used instead.
	n-312								N-312
}

UE-HSPA-Identities-r6 ::= SEQUENCE {
	new-H-RNTI					H-RNTI								OPTIONAL,
	newPrimary-E-RNTI			E-RNTI								OPTIONAL,
	newSecondary-E-RNTI		E-RNTI								OPTIONAL
}

UE-IdleTimersAndConstants-v3a0ext ::=		SEQUENCE {
	n-312											N-312ext		OPTIONAL
}

UE-MultiModeRAT-Capability ::=		SEQUENCE {
	multiRAT-CapabilityList				MultiRAT-Capability,
	multiModeCapability					MultiModeCapability
}

UE-PowerClass ::=					INTEGER (1..4)

UE-PowerClassExt ::=				ENUMERATED {class1, class2, class3, class4,
										 spare4, spare3, spare2, spare1 }

UE-RadioAccessCapability ::=		SEQUENCE {
	-- UE-RadioAccessCapability is compatible with R99, although accessStratumReleaseIndicator
	-- is removed from this IE, since its encoding did not result in bits. The
	-- accessStratumReleaseIndicator is provided in the relevant REL-4 extension IEs.
	pdcp-Capability					PDCP-Capability,
	rlc-Capability						RLC-Capability,
	transportChannelCapability		TransportChannelCapability,
	rf-Capability						RF-Capability,
	physicalChannelCapability			PhysicalChannelCapability,
	ue-MultiModeRAT-Capability		UE-MultiModeRAT-Capability,
	securityCapability					SecurityCapability,
	ue-positioning-Capability			UE-Positioning-Capability,
	measurementCapability				MeasurementCapability			OPTIONAL
}

UE-RadioAccessCapabilityInfo ::=		SEQUENCE {
	ue-RadioAccessCapability				UE-RadioAccessCapability,
	ue-RadioAccessCapability-v370ext		UE-RadioAccessCapability-v370ext
}

UE-RadioAccessCapability-v370ext ::=	SEQUENCE {
	ue-RadioAccessCapabBandFDDList		UE-RadioAccessCapabBandFDDList
}

UE-RadioAccessCapability-v380ext ::=	SEQUENCE {
	ue-PositioningCapabilityExt-v380		UE-PositioningCapabilityExt-v380
}

UE-RadioAccessCapability-v3a0ext ::=	SEQUENCE {
	ue-PositioningCapabilityExt-v3a0		UE-PositioningCapabilityExt-v3a0
}

UE-RadioAccessCapability-v3g0ext ::=	SEQUENCE {
	ue-PositioningCapabilityExt-v3g0		UE-PositioningCapabilityExt-v3g0
}

UE-RadioAccessCapability-v650ext ::=	SEQUENCE {
	ue-RadioAccessCapabBandFDDList2		UE-RadioAccessCapabBandFDDList2,
	-- This IE shall be included if the UE also supports Band I-VII
	ue-RadioAccessCapabBandFDDList-ext	UE-RadioAccessCapabBandFDDList-ext	OPTIONAL
}

UE-RadioAccessCapability-v690ext ::= SEQUENCE {
		physicalchannelcapability-edch	PhysicalChannelCapability-edch-r6,
		-- TABULAR: deviceType is MD in tabular description
		-- Default value is 'doesBenefitFromBatteryConsumptionOptimisation'
		deviceType		ENUMERATED { doesNotBenefitFromBatteryConsumptionOptimisation }	OPTIONAL
}

UE-RadioAccessCapability-v7e0ext ::=	SEQUENCE {
	-- User equipment IEs
		supportForTwoDRXSchemesInPCH		ENUMERATED { true }						OPTIONAL,
		supportEDPDCHPowerInterpolation		ENUMERATED { true }						OPTIONAL
}

UE-RadioAccessCapability-v7f0ext ::=	SEQUENCE {
	supportofTxDivOnNonMIMOChannel			ENUMERATED { true }							OPTIONAL,
	-- IE physicalChannelCapability-LCR and ue-RadioAccessCapabilityComp-TDD128 shall only be
	-- included in InterRATHandoverInfo for 1.28 Mcps TDD, otherwise these IEs are not needed here.
	physicalChannelCapability-LCR			PhysicalChannelCapability-LCR-r4			OPTIONAL,
	ue-RadioAccessCapabilityComp-TDD128		UE-RadioAccessCapabilityComp-TDD128-v7f0ext	OPTIONAL
}

UE-RadioAccessCapabilityInfo-v770ext ::= SEQUENCE {
	rf-Capability							RF-Capability-v770ext					OPTIONAL,
	physicalChannelCapability				PhysicalChannelCapabilityInfo-v770ext,
	ganssSupportIndication					ENUMERATED { true }						OPTIONAL,
	mac-ehsSupport							ENUMERATED { true }						OPTIONAL,
	ue-SpecificCapabilityInformation		UE-SpecificCapabilityInformation-LCRTDD	OPTIONAL
}

UE-RadioAccessCapabilityInfo-TDD128-v8b0ext ::=	SEQUENCE {
	-- INTER RAT HANDOVER INFO
	measurementCapabilityTDD						MeasurementCapabilityTDD			OPTIONAL,
	hSDSCH-physical-layer-category-extension
											HSDSCH-physical-layer-category-extension	OPTIONAL
}

UE-RadioAccessCapabilityInfo-TDD128-vb50ext ::=	SEQUENCE {
	-- INTER RAT HANDOVER INFO
	measurementCapabilityTDD						MeasurementCapabilityTDD-vb50ext	OPTIONAL
}

UE-RadioAccessCapability-v860ext ::=	SEQUENCE {
	ue-RadioAccessCapabBandFDDList3			UE-RadioAccessCapabBandFDDList3
}

UE-RadioAccessCapability-v880ext ::=	SEQUENCE {
	-- INTER RAT HANDOVER INFO
	supportForPriorityReselectionInUTRAN 	ENUMERATED { true }					OPTIONAL
}

UE-RadioAccessCapability-v890ext ::= SEQUENCE {
	-- UE radio access capability
		supportCellSpecificTxDiversityinDC-Operation 	ENUMERATED { true }			OPTIONAL
}

UE-RadioAccessCapability-v920ext ::=	SEQUENCE {
	supportOfenhancedTS0				ENUMERATED { true }						OPTIONAL
}

UE-RadioAccessCapability-va40ext ::= SEQUENCE {
		ue-RadioAccessCapabBandFDDList4			UE-RadioAccessCapabBandFDDList4
}

UE-RadioAccessCapability-va60ext ::= SEQUENCE {
	ue-RadioAccessCapabBandFDDList4			UE-RadioAccessCapabBandFDDList4-va60ext			OPTIONAL
}

UE-RadioAccessCapability-va80ext ::= SEQUENCE {
		ue-RadioAccessCapabBandFDDList4-va60ext	UE-RadioAccessCapabBandFDDList4-va60ext	OPTIONAL,
		ue-RadioAccessCapabBandFDDList4-va80ext	UE-RadioAccessCapabBandFDDList4-va80ext	OPTIONAL
}

UE-RadioAccessCapability-vb50ext ::= SEQUENCE {
	ue-RadioAccessCapabBandFDDList6		UE-RadioAccessCapabBandFDDList6		OPTIONAL
}

UE-RadioAccessCapability-vb70ext ::= SEQUENCE {
	ue-RadioAccessCapabBandFDDList7		UE-RadioAccessCapabBandFDDList7		OPTIONAL
}

UE-RadioAccessCapability-vbc0ext ::= SEQUENCE {
	interRATsupportMultiCellConfiguration		ENUMERATED { true }			OPTIONAL,
	ue-RadioAccessCapabBandCombList			UE-RadioAccessCapabBandCombList	OPTIONAL,
	ue-RadioAccessCapabBandCombList-va40ext	UE-RadioAccessCapabBandCombList-va40ext																								OPTIONAL
}

UE-RadioAccessCapability-vd20ext ::= SEQUENCE {
	ue-RadioAccessCapabBandCombList	UE-RadioAccessCapabBandCombList-vd20ext	OPTIONAL
}


UE-RadioAccessCapabBand-va40ext ::= SEQUENCE {
	ue-RadioAccessCapabBandFDDList5				UE-RadioAccessCapabBandFDDList5,
	-- This IE shall be included if the UE also supports Band I – Band XXII
	ue-RadioAccessCapabBandFDDList-ext2			UE-RadioAccessCapabBandFDDList-ext2		OPTIONAL
}

UE-RadioAccessCapabBandFDDList2 ::=	SEQUENCE (SIZE (1..maxFreqBandsFDD)) OF
											UE-RadioAccessCapabBandFDD2

UE-RadioAccessCapabBandFDDList3 ::=	SEQUENCE (SIZE (1..maxFreqBandsFDD)) OF
											UE-RadioAccessCapabBandFDD3

UE-RadioAccessCapabBandFDDList4 ::=	SEQUENCE (SIZE (1..maxFreqBandsFDD)) OF
											UE-RadioAccessCapabBandFDD4

UE-RadioAccessCapabBandFDDList4-va60ext ::=	SEQUENCE (SIZE (1..maxFreqBandsFDD)) OF
											UE-RadioAccessCapabBandFDD4-va60ext

UE-RadioAccessCapabBandFDDList4-va80ext ::=	SEQUENCE (SIZE (1..maxFreqBandsFDD-ext3)) OF
											UE-RadioAccessCapabBandFDD4-va80ext

UE-RadioAccessCapabBandFDDList5 ::=	SEQUENCE (SIZE (1..maxFreqBandsFDD-ext2)) OF
											UE-RadioAccessCapabBandFDD5

UE-RadioAccessCapabBandFDDList6 ::=	SEQUENCE (SIZE (1..maxFreqBandsFDD3)) OF
											UE-RadioAccessCapabBandFDD6

UE-RadioAccessCapabBandFDDList7 ::=	SEQUENCE (SIZE (1..maxFreqBandsFDD3)) OF
											UE-RadioAccessCapabBandFDD7

UE-RadioAccessCapabBandFDD2 ::=	SEQUENCE {
	radioFrequencyBandFDD2				RadioFrequencyBandFDD2,
	fddRF-Capability					SEQUENCE {
		ue-PowerClass						UE-PowerClassExt,
		txRxFrequencySeparation				TxRxFrequencySeparation
	}		OPTIONAL,
	measurementCapability2				MeasurementCapabilityExt2
}

UE-RadioAccessCapabBandFDD3 ::=		SEQUENCE {
	-- UE may omit both IEs if this IE indicates the same EUTRA compressed
	-- mode capability for all supported UTRA bands
	-- Otherwise, the UE shall include either one of the following OPTIONAL IEs.
	radioFrequencyBandFDD				RadioFrequencyBandFDD		OPTIONAL,
	radioFrequencyBandFDD2				RadioFrequencyBandFDD2		OPTIONAL,
	measurementCapability3				MeasurementCapabilityExt3
}

UE-RadioAccessCapabBandFDD4 ::=		SEQUENCE {
	-- UE may omit all the radioFrequencyBand IEs if this IE indicates the same
	-- capability for all supported UTRA bands
	-- Otherwise, the UE shall include either one of the following OPTIONAL IEs.
	radioFrequencyBandFDD				RadioFrequencyBandFDD		OPTIONAL,
	radioFrequencyBandFDD2				RadioFrequencyBandFDD2		OPTIONAL,
	radioFrequencyBandFDD3				RadioFrequencyBandFDD3		OPTIONAL,
	additionalSecondaryCells				ENUMERATED { a1, a2 }	OPTIONAL,
	nonContiguousMultiCellCombinationList			NonContiguousMultiCellCombinationList	OPTIONAL
}

UE-RadioAccessCapabBandFDD4-va60ext ::=		SEQUENCE {
	supportofULOLTD					ENUMERATED { true }				OPTIONAL
}

UE-RadioAccessCapabBandFDD4-va80ext ::=		SEQUENCE {
	-- UE may omit all the radioFrequencyBand IEs if this IE indicates the same
	-- capability for all supported UTRA bands
	-- Otherwise, the UE shall include either one of the following OPTIONAL IEs.
	radioFrequencyBandFDD				RadioFrequencyBandFDD		OPTIONAL,
	radioFrequencyBandFDD2				RadioFrequencyBandFDD2		OPTIONAL,
	radioFrequencyBandFDD3				RadioFrequencyBandFDD3		OPTIONAL,
	additionalSecondaryCells				ENUMERATED { a1, a2 }		OPTIONAL,
	nonContiguousMultiCellCombinationList			NonContiguousMultiCellCombinationList	OPTIONAL,
	supportofULOLTD						ENUMERATED { true }				OPTIONAL
}

UE-RadioAccessCapabBandFDD5 ::=		SEQUENCE {
	radioFrequencyBandFDD3				RadioFrequencyBandFDD3,
	fddRF-Capability					SEQUENCE {
		ue-PowerClass						UE-PowerClassExt,
		txRxFrequencySeparation				TxRxFrequencySeparation
	}		OPTIONAL,
	measurementCapability4				MeasurementCapabilityExt4
}

UE-RadioAccessCapabBandFDD6 ::=		SEQUENCE {
	-- UE may omit all the radioFrequencyBand IEs if this IE indicates the same
	-- capability for all supported UTRA bands
	-- Otherwise, the UE shall include either one of the following OPTIONAL IEs.
	radioFrequencyBandFDD				RadioFrequencyBandFDD		OPTIONAL,
	radioFrequencyBandFDD2				RadioFrequencyBandFDD2		OPTIONAL,
	radioFrequencyBandFDD3				RadioFrequencyBandFDD3		OPTIONAL,
	additionalSecondaryCells2			ENUMERATED { a3, a4, a5, a6 }			OPTIONAL,
	supportOfULCLTD						ENUMERATED { true }						OPTIONAL,
	multiflowCapability					MultiflowPerBandCapability				OPTIONAL,
	mimo4x4CapabilityBand				ENUMERATED { true }						OPTIONAL,
	supportOfULMIMO						ENUMERATED { true }						OPTIONAL,
	measurementCapability5				MeasurementCapabilityExt5,
	freqSpecificCompressedModeForNonContiguous	ENUMERATED { true }				OPTIONAL
}

UE-RadioAccessCapabBandFDD7 ::=		SEQUENCE {
	-- UE may omit all the radioFrequencyBand IEs if this IE indicates the same
	-- capability for all supported UTRA bands
	-- Otherwise, the UE shall include either one of the following OPTIONAL IEs.
	radioFrequencyBandFDD				RadioFrequencyBandFDD		OPTIONAL,
	radioFrequencyBandFDD2				RadioFrequencyBandFDD2		OPTIONAL,
	radioFrequencyBandFDD3				RadioFrequencyBandFDD3		OPTIONAL,
	measurementCapability6				MeasurementCapabilityExt6
}

UE-PositioningCapabilityExt-v380 ::=	SEQUENCE {
	rx-tx-TimeDifferenceType2Capable		BOOLEAN
}

UE-PositioningCapabilityExt-v3a0 ::=	SEQUENCE {
	validity-CellPCH-UraPCH					ENUMERATED { true }
}

UE-PositioningCapabilityExt-v3g0 ::=	SEQUENCE {
	sfn-sfnType2Capability				ENUMERATED { true }
}

UE-PositioningCapability-v770ext ::= SEQUENCE {
	ue-GANSSPositioning-Capability		UE-GANSSPositioning-Capability		OPTIONAL
}

UE-PositioningCapability-v860ext ::= SEQUENCE {
	ue-GANSSPositioning-Capability-v860ext
										UE-GANSSPositioning-Capability-v860ext-IEs	OPTIONAL
}

UE-PositioningCapability-vd20ext ::= SEQUENCE {
	ue-Positioning-AddPos-Capability	UE-AddPos-Supported-List	OPTIONAL
}

UE-RadioAccessCapabBandCombList	::=	SEQUENCE (SIZE (1..16)) OF BandComb

UE-RadioAccessCapabBandFDDList ::=	SEQUENCE (SIZE (1..maxFreqBandsFDD)) OF
											UE-RadioAccessCapabBandFDD

UE-RadioAccessCapabBandFDDList-ext ::= SEQUENCE (SIZE (1..maxFreqBandsFDD)) OF
										UE-RadioAccessCapabBandFDD-ext

UE-RadioAccessCapabBandFDDList-ext2 ::= SEQUENCE (SIZE (1..maxFreqBandsFDD2)) OF
										UE-RadioAccessCapabBandFDD-ext2

UE-RadioAccessCapabBandFDD ::=	SEQUENCE{
	radioFrequencyBandFDD				RadioFrequencyBandFDD,
	fddRF-Capability					SEQUENCE {
		ue-PowerClass						UE-PowerClassExt,
		txRxFrequencySeparation				TxRxFrequencySeparation
	}																OPTIONAL,
	measurementCapability				MeasurementCapabilityExt
}

UE-RadioAccessCapabBandFDD-ext ::= SEQUENCE {
	radioFrequencyBandFDD				RadioFrequencyBandFDD,
	compressedModeMeasCapabFDDList-ext	CompressedModeMeasCapabFDDList-ext
}

UE-RadioAccessCapabBandFDD-ext2 ::= SEQUENCE {
	radioFrequencyBandFDD				RadioFrequencyBandFDD		OPTIONAL,
	radioFrequencyBandFDD2				RadioFrequencyBandFDD2		OPTIONAL,
	compressedModeMeasCapabFDDList3		CompressedModeMeasCapabFDDList3
}

UE-RadioAccessCapability-v4b0ext ::=	SEQUENCE {
	pdcp-Capability-r4-ext				PDCP-Capability-r4-ext,
	tdd-CapabilityExt					SEQUENCE {
		rf-Capability						RF-Capability-r4-ext,
		physicalChannelCapability-LCR		PhysicalChannelCapability-LCR-r4,
		measurementCapability-r4-ext		MeasurementCapability-r4-ext
	}											OPTIONAL,
	-- IE " AccessStratumReleaseIndicator" is not needed in RRC CONNECTION SETUP COMPLETE
	accessStratumReleaseIndicator				AccessStratumReleaseIndicator 	OPTIONAL
}

UE-RadioAccessCapabilityComp ::= SEQUENCE {
	totalAM-RLCMemoryExceeds10kB			BOOLEAN,
	rf-CapabilityComp						RF-CapabilityComp
}

UE-RadioAccessCapabilityComp-ext ::= SEQUENCE {
	rf-CapabilityFDDComp				RF-CapabBandListFDDComp-ext
}

UE-RadioAccessCapabilityComp-TDD128-v7f0ext ::=	SEQUENCE {
	hSDSCH-physical-layer-category
											HSDSCH-physical-layer-category				OPTIONAL,
	multiCarrier-physical-layer-category
								MultiCarrier-HSDSCH-physical-layer-category				OPTIONAL,
	tdd-edch-PhysicalLayerCategory			INTEGER (1..6)								OPTIONAL,
	dl-CapabilityWithSimultaneousHS-DSCHConfig
											DL-CapabilityWithSimultaneousHS-DSCHConfig	OPTIONAL,
	supportForCSVoiceoverHSPA				ENUMERATED { true }						OPTIONAL,
	totalRLC-AM-BufferSize					TotalRLC-AM-BufferSize-r5-ext			OPTIONAL
}

UE-RadioAccessCapabilityComp-v770ext ::= SEQUENCE {
	rf-CapabilityComp						RF-CapabilityComp-v770ext,
	securityCapabilityIndication			ENUMERATED { true }						OPTIONAL,
	ganssSupportIndication					ENUMERATED { true }						OPTIONAL,
	mac-ehsSupport							ENUMERATED { true }						OPTIONAL
}

UE-RadioAccessCapabilityComp2 ::=		SEQUENCE {
	fddPhysicalChannelCapab-hspdsch-edch	SEQUENCE {
		dl-CapabilityWithSimultaneousHS-DSCHConfig
										DL-CapabilityWithSimultaneousHS-DSCHConfig	OPTIONAL,
		physicalChannelCapabComp-hspdsch-r6		HSDSCH-physical-layer-category,
		physicalChannelCapability-edch-r6		PhysicalChannelCapability-edch-r6
	}		OPTIONAL
}

UE-RadioAccessCapabilityComp2-v770ext ::= SEQUENCE {
	hsdsch-physical-layer-category-ext		HSDSCH-physical-layer-category-ext		OPTIONAL,
	edch-PhysicalLayerCategory-extension	INTEGER (7)								OPTIONAL,
	hsscchlessHsdschOperation				ENUMERATED { true }						OPTIONAL,
	enhancedFdpch							ENUMERATED { true }						OPTIONAL,
	hsdschReception-CellFach				ENUMERATED { true }						OPTIONAL,
	hsdschReception-CellUraPch				ENUMERATED { true }						OPTIONAL,
	discontinuousDpcchTransmission			ENUMERATED { true }						OPTIONAL,
	slotFormat4								ENUMERATED { true }						OPTIONAL,
	pdcp-Capability							PDCP-Capability-v770ext					OPTIONAL
}

UE-RadioAccessCapabilityComp2-v7f0ext ::= SEQUENCE {
		supportofTxDivOnNonMIMOChannel		ENUMERATED { true }						OPTIONAL
}

UE-RadioAccessCapabilityComp2-v860ext ::= SEQUENCE {
	hsdsch-physical-layer-category-ext2		HSDSCH-physical-layer-category-ext2		OPTIONAL,
	supportOfMACiis							ENUMERATED { true }						OPTIONAL
}

UE-RadioAccessCapabilityComp2-v920ext ::= SEQUENCE {
	hsdsch-physical-layer-category-ext3		HSDSCH-physical-layer-category-ext3		OPTIONAL,
	edch-PhysicalLayerCategory-extension2	INTEGER (8..9)							OPTIONAL
}

UE-RadioAccessCapabilityComp2-va40ext ::= SEQUENCE {
	hsdsch-physical-layer-category-ext4		HSDSCH-physical-layer-category-ext4		OPTIONAL,
	hsdsch-physical-layer-category-ext5		HSDSCH-physical-layer-category-ext5		OPTIONAL
}

UE-RadioAccessCapabilityComp2-vb50ext ::= SEQUENCE {
	hsdsch-physical-layer-category-ext6		HSDSCH-physical-layer-category-ext6		OPTIONAL,
	hsdsch-physical-layer-category-ext7		HSDSCH-physical-layer-category-ext7		OPTIONAL,
	hsdsch-physical-layer-category-ext8		HSDSCH-physical-layer-category-ext8		OPTIONAL,
	edch-PhysicalLayerCategory-extension3	INTEGER (10..12)						OPTIONAL,
	supportOfHSDPCCHPowerOffsetExtension	ENUMERATED { true }						OPTIONAL
}

UE-RadioAccessCapabilityComp2-vc50ext ::= SEQUENCE {
	supportofDsacAndPpacInCellDch					ENUMERATED { true }				OPTIONAL,
	supportforDCHEnhancements						ENUMERATED { basic, full }		OPTIONAL,
	simultaneousSupportforDCHEnhancementsAndCM		ENUMERATED { true }				OPTIONAL,
	simultaneousSupportforDCHEnhancementsAndDPCCHDiscntTx	ENUMERATED { true }		OPTIONAL
}

UE-RadioAccessCapabilityComp2-vd20ext ::= SEQUENCE {
	supportOfDualCellEDCHwithDPDCH			ENUMERATED { true }					OPTIONAL
}

UE-RadioAccessCapabilityComp-TDD128 ::=		SEQUENCE {
	tdd128RF-Capability						RadioFrequencyBandTDDextList			OPTIONAL,
	supportOfSFModeForHSPDSCHDualStream		ENUMERATED { sf1, sf1sf16 }				OPTIONAL,
	supportOfCommonEDCH						ENUMERATED { true }						OPTIONAL,
	supportOfMACiis							ENUMERATED { true }						OPTIONAL,
	supportOfSPSOperation					ENUMERATED { true }						OPTIONAL,
	supportOfControlChannelDRXOperation		ENUMERATED { true }						OPTIONAL
}

RF-CapabilityComp ::= SEQUENCE {
	fdd 					CHOICE {
		notSupported					NULL,
		supported						RF-CapabBandListFDDComp
	},
	tdd384-RF-Capability	CHOICE {
		notSupported					NULL,
		supported						RadioFrequencyBandTDDList
	},
	tdd128-RF-Capability	CHOICE {
		notSupported					NULL,
		supported						RadioFrequencyBandTDDList
	}
}

RF-CapabilityComp-v770ext ::=		SEQUENCE {
	-- If support of TDD384 and/or TDD128 RF capability is indicated in IEs 'RF-CapabilityComp',
	-- the corresponding IE 'RadioFrequencyBandTDDList-r7' shall be included in this IE.
	tdd384-RF-Capability				RadioFrequencyBandTDDList-r7			OPTIONAL,
	tdd768-RF-Capability				CHOICE {
		notSupported						NULL,
		supported							RadioFrequencyBandTDDList-r7
	},
	tdd128-RF-Capability				RadioFrequencyBandTDDList-r7			OPTIONAL
}

-- NOTE: This IE defines the supported TX/RX frequency separation for the respective supported
-- frequency band. Values defined as spare shall not be sent in this version of the protocol.
-- If a spare value is received, it should be interpreted as 'default-RxTX-sparation'.
RF-CapabBandFDDComp ::=				ENUMERATED { notSupported,
										default-TxRx-separation, spare2, spare1 }

RF-CapabBandListFDDComp ::=			SEQUENCE (SIZE (1..maxFreqBandsFDD)) OF
	-- The first entry corresponds with the first value of IE RadioFrequencyBandFDD,
	-- fdd2100, and so on. No more than seven entries should be included in this IE. The
	-- 8'th entry, if present, shall be ignored.
	-- An extension of this IE may be provided using the IE 'RF-CapabBandListFDDComp-ext'.
	RF-CapabBandFDDComp

RF-CapabBandListFDDComp-ext ::=		SEQUENCE (SIZE (1..maxFreqBandsFDD-ext)) OF
	-- The first entry corresponds with the first value of IE RadioFrequencyBandFDD2,
	-- bandVIII, and so on.
	RF-CapabBandFDDComp

RF-CapabBandListFDDComp-ext2 ::=		SEQUENCE (SIZE (1..maxFreqBandsFDD-ext2)) OF
	-- The first entry corresponds with the first value of IE RadioFrequencyBandFDD3,
	-- 23 (Band XXIII), and so on.
	RF-CapabBandFDDComp

UE-RadioAccessCapabBandCombList-va40ext ::= SEQUENCE (SIZE (1..16)) OF SupportedCarrierCombination

UE-RadioAccessCapabBandCombList-vb50ext ::= SEQUENCE (SIZE (1..16)) OF
																	SupportedCarrierCombination-ext


UE-RadioAccessCapabBandCombList-vd20ext ::= SEQUENCE (SIZE (1..16)) OF
 											SupportDualBandDualCellEdch

SupportedCarrierCombination ::= SEQUENCE {
	carrierCombination12					BOOLEAN,
	carrierCombination21					BOOLEAN,
	carrierCombination13					BOOLEAN,
	carrierCombination31					BOOLEAN,
	carrierCombination22					BOOLEAN
}

SupportedCarrierCombination-ext ::= SEQUENCE {
	carrierCombination14					BOOLEAN,
	carrierCombination41					BOOLEAN,
	carrierCombination15					BOOLEAN,
	carrierCombination51					BOOLEAN,
	carrierCombination16					BOOLEAN,
	carrierCombination61					BOOLEAN,
	carrierCombination17					BOOLEAN,
	carrierCombination71					BOOLEAN,
	carrierCombination23					BOOLEAN,
	carrierCombination32					BOOLEAN,
	carrierCombination24					BOOLEAN,
	carrierCombination42					BOOLEAN,
	carrierCombination25					BOOLEAN,
	carrierCombination52					BOOLEAN,
	carrierCombination26					BOOLEAN,
	carrierCombination62					BOOLEAN,
	carrierCombination33					BOOLEAN,
	carrierCombination34					BOOLEAN,
	carrierCombination43					BOOLEAN,
	carrierCombination44					BOOLEAN,
	carrierCombination35					BOOLEAN,
	carrierCombination53					BOOLEAN
}

SupportDualBandDualCellEdch ::= SEQUENCE {
	dualBandDualCellEdchIndication		ENUMERATED { true }						OPTIONAL
}

UE-RadioAccessCapability-v590ext ::=	SEQUENCE {
	dl-CapabilityWithSimultaneousHS-DSCHConfig
										DL-CapabilityWithSimultaneousHS-DSCHConfig	OPTIONAL,
	pdcp-Capability-r5-ext				PDCP-Capability-r5-ext,
	rlc-Capability-r5-ext				RLC-Capability-r5-ext,
	physicalChannelCapability			PhysicalChannelCapability-hspdsch-r5,
	multiModeRAT-Capability-v590ext		MultiModeRAT-Capability-v590ext
}

UE-RadioAccessCapability-v5c0ext ::= SEQUENCE {
	pdcp-Capability-r5-ext2				PDCP-Capability-r5-ext2
}

UE-RadioAccessCapability-v680ext ::= SEQUENCE {
	multiModeRAT-Capability-v680ext		MultiModeRAT-Capability-v680ext
}

UL-OLTD-InfoFDD ::= 	SEQUENCE {
	ulOLTDActivation			ENUMERATED	{true}
}

UL-PhysChCapabilityFDD ::=			SEQUENCE {
	maxNoDPDCH-BitsTransmitted			MaxNoDPDCH-BitsTransmitted,
	-- dummy is not used in this version of the specification and
	-- it should be ignored by the receiver.
	dummy								BOOLEAN
}

UL-PhysChCapabilityFDD-r6 ::=			SEQUENCE {
	maxNoDPDCH-BitsTransmitted				MaxNoDPDCH-BitsTransmitted,
	physicalchannelcapability-edch			PhysicalChannelCapability-edch-r6
}

UL-PhysChCapabilityFDD-v770ext ::=		SEQUENCE {
	edch-PhysicalLayerCategory-extension	INTEGER (7)							OPTIONAL,
	discontinuousDpcchTransmission			ENUMERATED { true }					OPTIONAL,
	slotFormat4								ENUMERATED { true }					OPTIONAL
}

UL-PhysChCapabilityFDD-v920ext ::=		SEQUENCE {
	edch-PhysicalLayerCategory-extension2	INTEGER (8..9)						OPTIONAL
}
UL-PhysChCapabilityFDD-vb50ext ::=		SEQUENCE {
	edch-PhysicalLayerCategory-extension3	INTEGER (10..12)					OPTIONAL
}

UL-PhysChCapabilityFDD-vc50ext ::=		SEQUENCE {
	supportofCellReselectionIndicationReporting		ENUMERATED { true }		OPTIONAL,
	supportofRadioLinkswithoutDPCHFDPCH				ENUMERATED { true }		OPTIONAL,
	supportofServingE-DCHCellDecoupling				ENUMERATED { true }		OPTIONAL,
	accessGroupsAccessControl							ENUMERATED { true }		OPTIONAL,
	enhancedTTISwitching								ENUMERATED { true }		OPTIONAL,
	implicitGrantHandling								ENUMERATED { true }		OPTIONAL,
	dtx-enhancements									ENUMERATED { true }		OPTIONAL
}

UL-PhysChCapabilityFDD-vd20ext ::=		SEQUENCE {
	supportOfDualCellEDCHwithDPDCH			ENUMERATED { true }				OPTIONAL
}

UL-PhysChCapabilityFDD-ve30ext ::=		SEQUENCE {
	supportOfDualCellEDCHOperationEnhancements			ENUMERATED { true }				OPTIONAL
}

UL-PhysChCapabilityTDD ::=			SEQUENCE {
	maxTS-PerFrame						MaxTS-PerFrame,
	maxPhysChPerTimeslot				MaxPhysChPerTimeslot,
	minimumSF							MinimumSF-UL,
	supportOfPUSCH						BOOLEAN
}

UL-PhysChCapabilityTDD-384-v770ext ::=	SEQUENCE {
	tdd384-edch								CHOICE {
		supported								SEQUENCE {
			tdd-edch-PhysicalLayerCategory			INTEGER (1..16)
		},
		unsupported								NULL
	}
}

UL-PhysChCapabilityTDD-LCR-r4 ::=	SEQUENCE {
	maxTS-PerSubFrame					MaxTS-PerSubFrame-r4,
	maxPhysChPerTimeslot				MaxPhysChPerTimeslot,
	minimumSF							MinimumSF-UL,
	supportOfPUSCH						BOOLEAN,
	supportOf8PSK						BOOLEAN
}

UL-PhysChCapabilityTDD-128-v770ext ::=	SEQUENCE {
	maxPhysChPerTimeslot					MaxPhysChPerTimeslot-LCR-r7,
	tdd128-edch								CHOICE {
		supported								SEQUENCE {
			tdd-edch-PhysicalLayerCategory			INTEGER (1..6)
		},
		unsupported								NULL
	}
}

UL-PhysChCapabilityInfoTDD-128-v770ext ::= SEQUENCE {
	maxPhysChPerTimeslot					MaxPhysChPerTimeslot-LCR-r7
}

UL-PhysChCapabilityInfoTDD-128-va40ext ::= SEQUENCE {
	multiCarrier-EdchPhysicalLayerCategory-128	INTEGER (1..8)					OPTIONAL,
	maxNumberCarrierForMCHSUPA-TDD				ENUMERATED {nf-2, nf-3, nf-6, spare}	OPTIONAL
}

UL-PhysChCapabilityTDD-768 ::=			SEQUENCE {
	maxTS-PerFrame							MaxTS-PerFrame,
	maxPhysChPerTimeslot					MaxPhysChPerTimeslot,
	minimumSF								MinimumSF-UL,
	supportOfPUSCH							BOOLEAN,
	tdd384-edch								CHOICE {
		supported								SEQUENCE {
			tdd-edch-PhysicalLayerCategory			INTEGER (1..16)
		},
		unsupported								NULL
	}
}

UL-OtherTTIConfiguration-Information ::= SEQUENCE {
	configurationInfo			CHOICE {
		continue							NULL,
		newConfiguration					SEQUENCE {
			ul-EDCH-Information				UL-EDCH-Information-r11,
			ul-AddReconfTransChInfoList		UL-AddReconfTransChInfoList-r8,
			dtx-drx-TimingInfo				DTX-DRX-TimingInfo-r7				OPTIONAL,
			dtx-drx-Info					DTX-DRX-Info-r12					OPTIONAL
		}
	},
	activationDelay				ActivationDelay									OPTIONAL
}

UL-OtherTTIConfigurationInfo-Sec ::= SEQUENCE {
	configurationInfo			CHOICE {
		continue							NULL,
		newConfiguration					SEQUENCE {
			secondaryEDCH-Info-Common			SecondaryEDCH-Info-Common-r14,
			ul-AddReconfTransChInfoList		UL-AddReconfTransChInfoList-r14
		}
	},
	activationDelay				ActivationDelay									OPTIONAL
}

UL-SecondaryCellInfoFDD ::=		CHOICE {
	continue							NULL,
	newConfiguration					SEQUENCE {
		secondaryServingEDCHCell-Info		SecondaryServingEDCHCell-Info		OPTIONAL,
		secondaryEDCH-Info-Common			SecondaryEDCH-Info-Common			OPTIONAL,
		dl-InformationPerSecondaryRL-List	DL-InformationPerSecondaryRL-List	OPTIONAL
	}
}

UL-SecondaryCellInfoFDD-r12 ::=		CHOICE {
	continue							NULL,
	newConfiguration					SEQUENCE {
		secondaryServingEDCHCell-Info		SecondaryServingEDCHCell-Info			OPTIONAL,
		secondaryEDCH-Info-Common			SecondaryEDCH-Info-Common-r12			OPTIONAL,
		dl-InformationPerSecondaryRL-List	DL-InformationPerSecondaryRL-List-r12	OPTIONAL
	}
}

UL-SecondaryCellInfoFDD-r13 ::=		CHOICE {
	continue							NULL,
	newConfiguration					SEQUENCE {
		secondaryServingEDCHCell-Info		SecondaryServingEDCHCell-Info			OPTIONAL,
		secondaryEDCH-Info-Common			SecondaryEDCH-Info-Common-r12			OPTIONAL,
		dl-InformationPerSecondaryRL-List	DL-InformationPerSecondaryRL-List-r13	OPTIONAL
	}
}

UL-SecondaryCellInfoFDD-r14 ::=		CHOICE {
	continue							NULL,
	newConfiguration					SEQUENCE {
		secondaryServingEDCHCell-Info		SecondaryServingEDCHCell-Info			OPTIONAL,
		secondaryEDCH-Info-Common			SecondaryEDCH-Info-Common-r14			OPTIONAL,
		dl-InformationPerSecondaryRL-List	DL-InformationPerSecondaryRL-List-r13	OPTIONAL
	}
}

PhysicalChannelCapability-edch-r6 ::=	SEQUENCE {
	fdd-edch								CHOICE {
		supported								SEQUENCE {
			edch-PhysicalLayerCategory				INTEGER (1..16)
		},
		unsupported								NULL
	}
}

UL-TransChCapability ::=			SEQUENCE {
	maxNoBitsTransmitted				MaxNoBits,
	maxConvCodeBitsTransmitted			MaxNoBits,
	turboEncodingSupport				TurboSupport,
	maxSimultaneousTransChs				MaxSimultaneousTransChsUL,
	modeSpecificInfo					CHOICE {
		fdd									NULL,
		tdd									SEQUENCE {
			maxSimultaneousCCTrCH-Count			MaxSimultaneousCCTrCH-Count
		}
	},
	maxTransmittedBlocks				MaxTransportBlocksUL,
	maxNumberOfTFC						MaxNumberOfTFC-UL,
	maxNumberOfTF						MaxNumberOfTF
}

UE-Positioning-Capability ::=		SEQUENCE {
	standaloneLocMethodsSupported			BOOLEAN,
	ue-BasedOTDOA-Supported					BOOLEAN,
	networkAssistedGPS-Supported			NetworkAssistedGPS-Supported,
	supportForUE-GPS-TimingOfCellFrames		BOOLEAN,
	supportForIPDL							BOOLEAN
}

UE-SecurityInformation ::=			SEQUENCE {
	start-CS							START-Value
}

UE-SecurityInformation2 ::=			SEQUENCE {
	start-PS							START-Value
}

UE-SpecificCapabilityInformation-LCRTDD ::=	ENUMERATED {
												nF,
												nFMc-TriRx-UniTx,
												nFMc-TriRx-TriTx,
												nFMc-HexRx-UniTx,
												nFMc-HexRx-TriTx,
												nFMc-HexRx-HexTx,
												nFMc-TwoRx-UniTx-Discontiguous,
												nFMc-TwoRx-TwoTx-Discontiguous,
												nFMc-TwoRx-UniTx-Contiguous,
												nFMc-TwoRx-TwoTx-Contiguous,
												spare6,
												spare5,
												spare4,
												spare3,
												spare2,
												spare1 }

URA-UpdateCause ::=					ENUMERATED {
										changeOfURA,
										periodicURAUpdate,
										dummy,
										spare1 }

UTRAN-DRX-CycleLengthCoefficient ::= INTEGER (3..9)

UTRAN-DRX-CycleLengthCoefficient-r7 ::= SEQUENCE {
	drx-CycleLengthCoefficient			INTEGER (3..9),
	drx-CycleLengthCoefficient2			INTEGER (3..9)						OPTIONAL,
	timeForDRXCycle2					T-319								OPTIONAL
}

WaitTime ::=						INTEGER (0..15)

-- ***************************************************
--
--     RADIO BEARER INFORMATION ELEMENTS (10.3.4)
--
-- ***************************************************

AlgorithmSpecificInfo ::=			CHOICE {
	rfc2507-Info						RFC2507-Info
}

AlgorithmSpecificInfo-r4 ::=		CHOICE {
	rfc2507-Info						RFC2507-Info,
	rfc3095-Info						RFC3095-Info-r4
}

CID-InclusionInfo-r4 ::=			ENUMERATED {
										pdcp-Header,
										rfc3095-PacketFormat }

CommonRBMappingInfo ::=				SEQUENCE {
	logicalChannelIdentity				LogicalChannelIdentity,
	mac-ehs-QueueId						MAC-ehs-QueueId
}

-- Upper limit of COUNT-C is 2^32 - 1
COUNT-C ::=							INTEGER (0..4294967295)

-- Upper limit of COUNT-C-MSB is 2^25 - 1
COUNT-C-MSB ::=						INTEGER (0..33554431)

CS-HSPA-Information ::=				SEQUENCE {
	ul-AMR-Rate							UL-AMR-Rate				OPTIONAL,
	maxCS-Delay							MaxCS-Delay
}

DefaultConfigForCellFACH ::=		SEQUENCE {
	defaultConfigMode					DefaultConfigMode,
	defaultConfigIdForCellFACH			DefaultConfigIdForCellFACH
}

DefaultConfigIdentity ::=			INTEGER (0..10)

DefaultConfigIdentity-r4 ::=		INTEGER (0..12)

DefaultConfigIdentity-r5 ::=		INTEGER (0..13)

-- DefaultConfigIdentity-r6 values 25..31 are spare and shall not be used in this version of
-- the protocol
DefaultConfigIdentity-r6 ::=		INTEGER (0..31)

-- DefaultConfigIdForCellFACH values 1..15 are spare and shall not be used in this version of
-- the protocol
DefaultConfigIdForCellFACH ::=		INTEGER (0..15)

DefaultConfigMode ::=				ENUMERATED {
										fdd,
										tdd }

DDI ::=								INTEGER (0..62)

DL-AM-RLC-Mode ::=					SEQUENCE {
	inSequenceDelivery					BOOLEAN,
	receivingWindowSize					ReceivingWindowSize,
	dl-RLC-StatusInfo					DL-RLC-StatusInfo
}

DL-AM-RLC-Mode-r5 ::=					SEQUENCE {
	dl-RLC-PDU-size						OctetModeRLC-SizeInfoType1,
	inSequenceDelivery					BOOLEAN,
	receivingWindowSize					ReceivingWindowSize,
	dl-RLC-StatusInfo					DL-RLC-StatusInfo
}

DL-AM-RLC-Mode-r7 ::=				SEQUENCE {
	dl-RLC-PDU-size						CHOICE {
		fixedSize							OctetModeRLC-SizeInfoType1,
		flexibleSize						ENUMERATED { size7, size15 }
	},
	inSequenceDelivery					BOOLEAN,
	receivingWindowSize					ReceivingWindowSize,
	dl-RLC-StatusInfo					DL-RLC-StatusInfo
}

DL-AM-RLC-Mode-r11 ::=				SEQUENCE {
	dl-RLC-PDU-size						CHOICE {
		fixedSize							OctetModeRLC-SizeInfoType1,
		flexibleSize						ENUMERATED { size7, size15 }
	},
	inSequenceDelivery					BOOLEAN,
	receivingWindowSize					ReceivingWindowSize,
	dl-RLC-StatusInfo					DL-RLC-StatusInfo-r11
}

DL-CounterSynchronisationInfo ::=		SEQUENCE {
	rB-WithPDCP-InfoList					RB-WithPDCP-InfoList	OPTIONAL
}

DL-CounterSynchronisationInfo-r5 ::=	SEQUENCE {
	rb-WithPDCP-InfoList					RB-WithPDCP-InfoList			OPTIONAL,
	rb-PDCPContextRelocationList			RB-PDCPContextRelocationList	OPTIONAL
}

DL-LogicalChannelMapping ::=		SEQUENCE {
	-- TABULAR: DL-TransportChannelType contains TransportChannelIdentity as well.
	dl-TransportChannelType				DL-TransportChannelType,
	logicalChannelIdentity				LogicalChannelIdentity				OPTIONAL
}

DL-LogicalChannelMapping-r5 ::=		SEQUENCE {
	-- TABULAR: DL-TransportChannelType contains TransportChannelIdentity as well.
	dl-TransportChannelType				DL-TransportChannelType-r5,
	logicalChannelIdentity				LogicalChannelIdentity				OPTIONAL
}

DL-LogicalChannelMapping-r7 ::=		SEQUENCE {
	-- TABULAR: DL-TransportChannelType contains TransportChannelIdentity as well.
	dl-TransportChannelType				DL-TransportChannelType-r7,
	logicalChannelIdentity				LogicalChannelIdentity				OPTIONAL
}

DL-LogicalChannelMappingList ::=	SEQUENCE (SIZE (1..maxLoCHperRLC)) OF
										DL-LogicalChannelMapping

DL-LogicalChannelMappingList-r5 ::=	SEQUENCE (SIZE (1..maxLoCHperRLC)) OF
										DL-LogicalChannelMapping-r5

DL-LogicalChannelMappingList-r7 ::=	SEQUENCE (SIZE (1..maxLoCHperRLC)) OF
										DL-LogicalChannelMapping-r7

DL-Reception-Window-Size-r6 ::=		ENUMERATED { size32, size48, size64, size80, size96, size112 }

DL-RFC3095-r4 ::=					SEQUENCE {
	-- dummy is not used in this version of the specification and shall be ignored by the receiver.
	dummy								CID-InclusionInfo-r4,
	max-CID								INTEGER (1..16383)					DEFAULT 15,
	reverseDecompressionDepth			INTEGER (0..65535)					DEFAULT 0
}

DL-RLC-Mode ::=						CHOICE {
	dl-AM-RLC-Mode						DL-AM-RLC-Mode,
	dl-UM-RLC-Mode						NULL,
	dl-TM-RLC-Mode						DL-TM-RLC-Mode
}

DL-RLC-Mode-r5 ::=					CHOICE {
	dl-AM-RLC-Mode						DL-AM-RLC-Mode-r5,
	dl-UM-RLC-Mode						DL-UM-RLC-Mode-r5,
	dl-TM-RLC-Mode						DL-TM-RLC-Mode
}

DL-RLC-Mode-r6 ::=					CHOICE {
	dl-AM-RLC-Mode						DL-AM-RLC-Mode-r5,
	dl-UM-RLC-Mode						DL-UM-RLC-Mode-r6,
	dl-TM-RLC-Mode						DL-TM-RLC-Mode
}

DL-RLC-Mode-r7 ::=					CHOICE {
	dl-AM-RLC-Mode						DL-AM-RLC-Mode-r7,
	dl-UM-RLC-Mode						DL-UM-RLC-Mode-r6,
	dl-TM-RLC-Mode						DL-TM-RLC-Mode
}

DL-RLC-Mode-r11 ::=					CHOICE {
	dl-AM-RLC-Mode						DL-AM-RLC-Mode-r11,
	dl-UM-RLC-Mode						DL-UM-RLC-Mode-r6,
	dl-TM-RLC-Mode						DL-TM-RLC-Mode
}

DL-RLC-StatusInfo ::=				SEQUENCE {
	timerStatusProhibit					TimerStatusProhibit					OPTIONAL,
	-- dummy is not used in this version of the specification, it should not be sent
	-- and if received they should be ignored.
	dummy								TimerEPC							OPTIONAL,
	missingPDU-Indicator				BOOLEAN,
	timerStatusPeriodic					TimerStatusPeriodic					OPTIONAL
}

DL-RLC-StatusInfo-r11 ::=				SEQUENCE {
	timerStatusProhibit					TimerStatusProhibit					OPTIONAL,
	missingPDU-Indicator				BOOLEAN,
	timerStatusPeriodic					TimerStatusPeriodic					OPTIONAL,
	timerReordering						TimerReordering						OPTIONAL
}

DL-TM-RLC-Mode ::=					SEQUENCE {
	segmentationIndication					BOOLEAN
}

DL-TransportChannelType ::=			CHOICE {
	dch									TransportChannelIdentity,
	fach								NULL,
	-- The choice "dsch" should not be used in FDD mode, and if received
	-- the UE behaviour is unspecified.
	dsch								TransportChannelIdentity,
	-- The choice "dch-and-dsch" should not be used in FDD mode, and if received the UE
	-- behaviour is unspecified
	dch-and-dsch						TransportChannelIdentityDCHandDSCH
}

DL-TransportChannelType-r5 ::=			CHOICE {
	dch									TransportChannelIdentity,
	fach								NULL,
	-- The choice "dsch" should not be used in FDD mode, and if received
	-- the UE behaviour is unspecified.
	dsch								TransportChannelIdentity,
	-- The choice "dch-and-dsch" should not be used in FDD mode, and if received the UE
	-- behaviour is unspecified
	dch-and-dsch						TransportChannelIdentityDCHandDSCH,
	hsdsch								MAC-d-FlowIdentity,
	dch-and-hsdsch						MAC-d-FlowIdentityDCHandHSDSCH
}

DL-TransportChannelType-r7 ::=		CHOICE {
	dch									TransportChannelIdentity,
	fach								NULL,
	-- The choice "dsch" should not be used in FDD mode, and if received
	-- the UE behaviour is unspecified.
	dsch								TransportChannelIdentity,
	-- The choice "dch-and-dsch" should not be used in FDD mode, and if received the UE
	-- behaviour is unspecified
	dch-and-dsch						TransportChannelIdentityDCHandDSCH,
	hsdsch								CHOICE {
		mac-hs								MAC-d-FlowIdentity,
		mac-ehs								MAC-ehs-QueueId
	},
	dch-and-hsdsch						CHOICE {
		mac-hs								MAC-d-FlowIdentityDCHandHSDSCH,
		mac-ehs								MAC-ehs-QueueIdDCHandHSDSCH
	}
}

DL-UM-RLC-LI-size ::=					ENUMERATED {
										size7, size15 }

DL-UM-RLC-Mode-r5 ::=					SEQUENCE {
	dl-UM-RLC-LI-size					DL-UM-RLC-LI-size
}

DL-UM-RLC-Mode-r6 ::=				SEQUENCE {
	dl-UM-RLC-LI-size					DL-UM-RLC-LI-size,
	dl-Reception-Window-Size			DL-Reception-Window-Size-r6			OPTIONAL
}

ExpectReordering ::=				ENUMERATED {
										reorderingNotExpected,
										reorderingExpected }

ExplicitDiscard ::=					SEQUENCE {
	timerMRW							TimerMRW,
	timerDiscard						TimerDiscard,
	maxMRW								MaxMRW
}

HeaderCompressionInfo ::=			SEQUENCE {
	algorithmSpecificInfo				AlgorithmSpecificInfo
}

HeaderCompressionInfoList ::=		SEQUENCE (SIZE (1..maxPDCPAlgoType)) OF
										HeaderCompressionInfo

HeaderCompressionInfo-r4 ::=		SEQUENCE {
	algorithmSpecificInfo				AlgorithmSpecificInfo-r4
}

HeaderCompressionInfoList-r4 ::=	SEQUENCE (SIZE (1..maxPDCPAlgoType)) OF
										HeaderCompressionInfo-r4

HS-SCCH-DrxCellfach-info ::=	SEQUENCE {
	hs-scch-DrxCycleFach			ENUMERATED {sf20, sf40, sf80, sf160, sf320, sf640, spare2, spare1},
	hs-scch-RxBurstFach				ENUMERATED {sf1, sf2},
	t333							ENUMERATED {ms100, ms200, ms400, ms800}
}

LogicalChannelIdentity ::=			INTEGER (1..15)

LosslessSRNS-RelocSupport ::=		CHOICE {
	supported							MaxPDCP-SN-WindowSize,
	notSupported						NULL
}

MAC-d-HFN-initial-value ::=			BIT STRING (SIZE (24))

MAC-LogicalChannelPriority ::= 		INTEGER (1..8)

-- Actual value MaxCS-Delay = (IE value * 10) + 20
MaxCS-Delay ::=						INTEGER (0..18)

MaxDAT ::=							ENUMERATED {
										dat1, dat2, dat3, dat4, dat5, dat6,
										dat7, dat8, dat9, dat10, dat15, dat20,
										dat25, dat30, dat35, dat40 }

MaxDAT-Retransmissions ::=			SEQUENCE {
	maxDAT								MaxDAT,
	timerMRW							TimerMRW,
	maxMRW								MaxMRW
}

MaxMRW ::=							ENUMERATED {
										mm1, mm4, mm6, mm8, mm12, mm16,
										mm24, mm32 }

MaxPDCP-SN-WindowSize ::=			ENUMERATED {
										sn255, sn65535 }

MaxRST ::=							ENUMERATED {
										rst1, rst4, rst6, rst8, rst12,
										rst16, rst24, rst32 }

NoExplicitDiscard ::=				ENUMERATED {
										dt10, dt20, dt30, dt40, dt50,
										dt60, dt70, dt80, dt90, dt100 }

PDCP-Info ::=						SEQUENCE {
	losslessSRNS-RelocSupport			LosslessSRNS-RelocSupport			OPTIONAL,
	-- TABULAR: pdcp-PDU-Header is MD in the tabular format and it can be encoded
	-- in one bit, so the OPTIONAL is removed for compactness.
	pdcp-PDU-Header						PDCP-PDU-Header,
	headerCompressionInfoList			HeaderCompressionInfoList			OPTIONAL
}

PDCP-Info-r4 ::=					SEQUENCE {
	losslessSRNS-RelocSupport			LosslessSRNS-RelocSupport			OPTIONAL,
	-- TABULAR: pdcp-PDU-Header is MD in the tabular format and it can be encoded
	-- in one bit, so the OPTIONAL is removed for compactness.
	pdcp-PDU-Header						PDCP-PDU-Header,
	headerCompressionInfoList			HeaderCompressionInfoList-r4		OPTIONAL
}

PDCP-InfoReconfig ::=				SEQUENCE {
	pdcp-Info							PDCP-Info,
	-- dummy is not used in this version of the specification and
	-- it should be ignored.
	dummy								INTEGER (0..65535)
}

PDCP-InfoReconfig-r4 ::=			SEQUENCE {
	pdcp-Info							PDCP-Info-r4
}

PDCP-PDU-Header ::=					ENUMERATED {
										present, absent }

PDCP-ROHC-TargetMode ::=			ENUMERATED { o-Mode, r-Mode }

PDCP-SN-Info ::=					INTEGER (0..65535)

Poll-PDU ::=						ENUMERATED {
										pdu1, pdu2, pdu4, pdu8, pdu16,
										pdu32, pdu64, pdu128 }

Poll-SDU ::=						ENUMERATED {
										sdu1, sdu4, sdu16, sdu64 }

PollingInfo ::=						SEQUENCE {
	timerPollProhibit					TimerPollProhibit					OPTIONAL,
	timerPoll							TimerPoll							OPTIONAL,
	poll-PDU							Poll-PDU							OPTIONAL,
	poll-SDU							Poll-SDU							OPTIONAL,
	lastTransmissionPDU-Poll			BOOLEAN,
	lastRetransmissionPDU-Poll			BOOLEAN,
	pollWindow							PollWindow							OPTIONAL,
	timerPollPeriodic					TimerPollPeriodic					OPTIONAL
}

PollWindow ::=						ENUMERATED {
										pw50, pw60, pw70, pw80, pw85,
										pw90, pw95, pw99 }

PredefinedConfigIdentity ::=		INTEGER (0..15)

PredefinedConfigValueTag ::=		INTEGER (0..15)

PredefinedRB-Configuration ::=		SEQUENCE {
	re-EstablishmentTimer				Re-EstablishmentTimer,
	srb-InformationList					SRB-InformationSetupList,
	rb-InformationList					RB-InformationSetupList
}

PreDefRadioConfiguration ::=		SEQUENCE {
	-- Radio bearer IEs
		predefinedRB-Configuration			PredefinedRB-Configuration,
	-- Transport channel IEs
		preDefTransChConfiguration			PreDefTransChConfiguration,
	-- Physical channel IEs
		preDefPhyChConfiguration			PreDefPhyChConfiguration
}

PreDefRadioConfiguration-v770ext ::= SEQUENCE {
	-- Physical channel IEs
		preDefPhyChConfiguration			PreDefPhyChConfiguration-v770ext
}

PreDefRadioConfiguration-v920ext ::= SEQUENCE {
	-- Transport channel IEs
		mac-ehsWindowSize					MAC-hs-WindowSize-r9
}

PredefinedConfigStatusList ::=				SEQUENCE (SIZE (maxPredefConfig)) OF
											PredefinedConfigStatusInfo

PredefinedConfigStatusInfo ::=		CHOICE {
	storedWithValueTagSameAsPrevius		NULL,
	other								CHOICE {
		notStored							NULL,
		storedWithDifferentValueTag			PredefinedConfigValueTag
	}
}

PredefinedConfigStatusListComp ::= SEQUENCE {
	setsWithDifferentValueTag			PredefinedConfigSetsWithDifferentValueTag,
	otherEntries						PredefinedConfigStatusListVarSz				OPTIONAL
}

PredefinedConfigSetsWithDifferentValueTag ::= SEQUENCE (SIZE (1..2)) OF
												PredefinedConfigSetWithDifferentValueTag

PredefinedConfigSetWithDifferentValueTag ::= SEQUENCE {
	startPosition								INTEGER (0..10)		DEFAULT 0,
	-- numberOfEntries							INTEGER (6..16),
	-- numberOfEntries is covered by the size of the list in IE PredefinedConfigValueTagList
	valueTagList								PredefinedConfigValueTagList
}


PredefinedConfigValueTagList ::=		SEQUENCE (SIZE (1..maxPredefConfig)) OF
											PredefinedConfigValueTag

PredefinedConfigStatusListVarSz ::=		SEQUENCE (SIZE (1..maxPredefConfig)) OF
											PredefinedConfigStatusInfo

RAB-Info ::=						SEQUENCE {
	rab-Identity						RAB-Identity,
	cn-DomainIdentity					CN-DomainIdentity,
	nas-Synchronisation-Indicator		NAS-Synchronisation-Indicator	OPTIONAL,
	re-EstablishmentTimer				Re-EstablishmentTimer
}

RAB-Info-r6-ext ::=					SEQUENCE {
	mbms-SessionIdentity				MBMS-SessionIdentity				OPTIONAL
}

RAB-Info-v6b0ext ::=				SEQUENCE {
	mbms-ServiceIdentity				OCTET STRING (SIZE (3))
}

RAB-Info-r6 ::=						SEQUENCE {
	rab-Identity						RAB-Identity,
	mbms-SessionIdentity				MBMS-SessionIdentity				OPTIONAL,
	cn-DomainIdentity					CN-DomainIdentity,
	nas-Synchronisation-Indicator		NAS-Synchronisation-Indicator		OPTIONAL,
	re-EstablishmentTimer				Re-EstablishmentTimer
}

RAB-Info-r7 ::=						SEQUENCE {
	rab-Identity						RAB-Identity,
	mbms-SessionIdentity				MBMS-SessionIdentity				OPTIONAL,
	mbms-ServiceIdentity				OCTET STRING (SIZE (3))				OPTIONAL,
	cn-DomainIdentity					CN-DomainIdentity,
	nas-Synchronisation-Indicator		NAS-Synchronisation-Indicator		OPTIONAL,
	re-EstablishmentTimer				Re-EstablishmentTimer
}

RAB-InfoReplace ::=					SEQUENCE {
	rab-Identity						RAB-Identity,
	cn-DomainIdentity					CN-DomainIdentity
}

RAB-InformationList ::=				SEQUENCE (SIZE (1..maxRABsetup)) OF
										RAB-Info

RAB-InformationList-r6 ::=			SEQUENCE (SIZE (1..maxRABsetup)) OF
										RAB-Info-r6

RAB-InformationReconfigList ::= 	SEQUENCE (SIZE (1.. maxRABsetup)) OF
										RAB-InformationReconfig

RAB-InformationReconfigList-r8 ::=	SEQUENCE (SIZE (1..maxRABsetup)) OF
										RAB-InformationReconfig-r8

RAB-InformationReconfig ::=			SEQUENCE {
	rab-Identity						RAB-Identity,
	cn-DomainIdentity					CN-DomainIdentity,
	nas-Synchronisation-Indicator		NAS-Synchronisation-Indicator
}

RAB-InformationReconfig-r8 ::=		SEQUENCE {
	rab-Identity						RAB-Identity,
	cn-DomainIdentity					CN-DomainIdentity,
	nas-Synchronisation-Indicator		NAS-Synchronisation-Indicator,
	cs-HSPA-Information					CS-HSPA-Information				OPTIONAL
}

RAB-Info-Post ::=						SEQUENCE {
	rab-Identity						RAB-Identity,
	cn-DomainIdentity					CN-DomainIdentity,
	nas-Synchronisation-Indicator		NAS-Synchronisation-Indicator	OPTIONAL
}

RAB-InformationMBMSPtp ::=			SEQUENCE {
	rb-Identity							RB-Identity,
	mbms-ServiceIdentity				OCTET STRING (SIZE (3)),
	mbms-SessionIdentity				MBMS-SessionIdentity				OPTIONAL
}

RAB-InformationMBMSPtpList ::=		SEQUENCE (SIZE (1..maxMBMSservSelect)) OF
										RAB-InformationMBMSPtp

RAB-InformationSetup ::=			SEQUENCE {
	rab-Info							RAB-Info,
	rb-InformationSetupList				RB-InformationSetupList
}

RAB-InformationSetup-r4 ::=			SEQUENCE {
	rab-Info							RAB-Info,
	rb-InformationSetupList				RB-InformationSetupList-r4
}

RAB-InformationSetup-r5 ::=			SEQUENCE {
	rab-Info							RAB-Info,
	rb-InformationSetupList				RB-InformationSetupList-r5
}

RAB-InformationSetup-r6-ext ::=		SEQUENCE {
	rab-Info-r6-ext						RAB-Info-r6-ext
}

RAB-InformationSetup-r6 ::=			SEQUENCE {
	rab-Info							RAB-Info-r6,
	rb-InformationSetupList				RB-InformationSetupList-r6
}

RAB-InformationSetup-v6b0ext ::=	SEQUENCE {
	rab-Info-v6b0ext					RAB-Info-v6b0ext			OPTIONAL
}

RAB-InformationSetup-r7 ::=			SEQUENCE {
	rab-Info							RAB-Info-r7,
	rb-InformationSetupList				RB-InformationSetupList-r7
}

RAB-InformationSetup-r8 ::=			SEQUENCE {
	rab-Info							RAB-Info-r7,
	cs-HSPA-Information					CS-HSPA-Information			OPTIONAL,
	rab-InfoReplace						RAB-InfoReplace				OPTIONAL,
	rb-InformationSetupList				RB-InformationSetupList-r8
}

RAB-InformationSetup-v820ext ::=	SEQUENCE {
	cs-HSPA-Information					CS-HSPA-Information			OPTIONAL
}

RAB-InformationSetup-r11 ::=			SEQUENCE {
	rab-Info							RAB-Info-r7,
	cs-HSPA-Information					CS-HSPA-Information			OPTIONAL,
	rab-InfoReplace						RAB-InfoReplace				OPTIONAL,
	rb-InformationSetupList				RB-InformationSetupList-r11
}

RAB-InformationSetupList ::=		SEQUENCE (SIZE (1..maxRABsetup)) OF
										RAB-InformationSetup

RAB-InformationSetupList-r4 ::=		SEQUENCE (SIZE (1..maxRABsetup)) OF
										RAB-InformationSetup-r4

RAB-InformationSetupList-r5 ::=		SEQUENCE (SIZE (1..maxRABsetup)) OF
										RAB-InformationSetup-r5

RAB-InformationSetupList-r6 ::=		SEQUENCE (SIZE (1..maxRABsetup)) OF
										RAB-InformationSetup-r6

-- The IE 'RAB-InformationSetupList-r6-ext' provides elements of extension information, which
-- are added to the corresponding elements of the IE 'RAB-InformationSetupList/-r4/-r5'.
RAB-InformationSetupList-r6-ext ::= SEQUENCE (SIZE (1..maxRABsetup)) OF
										RAB-InformationSetup-r6-ext

RAB-InformationSetupList-v6b0ext ::= SEQUENCE (SIZE (1..maxRABsetup)) OF
										RAB-InformationSetup-v6b0ext

RAB-InformationSetupList-r7 ::=		SEQUENCE (SIZE (1..maxRABsetup)) OF
										RAB-InformationSetup-r7

RAB-InformationSetupList-r8 ::=		SEQUENCE (SIZE (1..maxRABsetup)) OF
										RAB-InformationSetup-r8

RAB-InformationSetupList-v820ext ::= SEQUENCE (SIZE (1..maxRABsetup)) OF
										RAB-InformationSetup-v820ext

RAB-InformationSetupList-r11 ::=		SEQUENCE (SIZE (1..maxRABsetup)) OF
										RAB-InformationSetup-r11

RB-ActivationTimeInfo ::=			SEQUENCE {
	rb-Identity							RB-Identity,
	rlc-SequenceNumber					RLC-SequenceNumber
}

RB-ActivationTimeInfoList ::=		SEQUENCE (SIZE (1..maxRB)) OF
										RB-ActivationTimeInfo

RB-COUNT-C-Information ::=			SEQUENCE {
	rb-Identity							RB-Identity,
	count-C-UL							COUNT-C,
	count-C-DL							COUNT-C
}

RB-COUNT-C-InformationList ::=		SEQUENCE (SIZE (1..maxRBallRABs)) OF
										RB-COUNT-C-Information

RB-COUNT-C-MSB-Information ::=		SEQUENCE {
	rb-Identity							RB-Identity,
	count-C-MSB-UL						COUNT-C-MSB,
	count-C-MSB-DL						COUNT-C-MSB
}

RB-COUNT-C-MSB-InformationList ::=	SEQUENCE (SIZE (1..maxRBallRABs)) OF
										RB-COUNT-C-MSB-Information

RB-Identity ::=						INTEGER (1..32)

RB-IdentityList ::=					SEQUENCE (SIZE (1..maxRB)) OF
										RB-Identity

RB-InformationAffected ::=			SEQUENCE {
	rb-Identity							RB-Identity,
	rb-MappingInfo						RB-MappingInfo
}

RB-InformationAffected-r5 ::=		SEQUENCE {
	rb-Identity							RB-Identity,
	rb-MappingInfo						RB-MappingInfo-r5
}

RB-InformationAffected-r6 ::=		SEQUENCE {
	rb-Identity							RB-Identity,
	rb-MappingInfo						RB-MappingInfo-r6
}

RB-InformationAffected-r7 ::=		SEQUENCE {
	rb-Identity							RB-Identity,
	rb-MappingInfo						RB-MappingInfo-r7
}

RB-InformationAffected-r8 ::=		SEQUENCE {
	rb-Identity							RB-Identity,
	rb-MappingInfo						RB-MappingInfo-r8
}

RB-InformationAffectedList ::=		SEQUENCE (SIZE (1..maxRB)) OF
										RB-InformationAffected

RB-InformationAffectedList-r5 ::=	SEQUENCE (SIZE (1..maxRB)) OF
										RB-InformationAffected-r5

RB-InformationAffectedList-r6 ::=	SEQUENCE (SIZE (1..maxRB)) OF
										RB-InformationAffected-r6

RB-InformationAffectedList-r7 ::=	SEQUENCE (SIZE (1..maxRB)) OF
										RB-InformationAffected-r7

RB-InformationAffectedList-r8 ::=	SEQUENCE (SIZE (1..maxRB)) OF
										RB-InformationAffected-r8

RB-InformationChanged-r6 ::=		SEQUENCE {
	rb-Identity							RB-Identity,
	rb-Change							CHOICE {
		release								NULL,
		re-mapToDefaultRb					RB-Identity
	}
}

RB-InformationChangedList-r6 ::= 		SEQUENCE (SIZE (1..maxRB)) OF
											RB-InformationChanged-r6

RB-InformationReconfig ::=			SEQUENCE {
	rb-Identity							RB-Identity,
	pdcp-Info							PDCP-InfoReconfig					OPTIONAL,
	pdcp-SN-Info						PDCP-SN-Info						OPTIONAL,
	rlc-Info							RLC-Info							OPTIONAL,
	rb-MappingInfo						RB-MappingInfo						OPTIONAL,
	rb-StopContinue						RB-StopContinue						OPTIONAL
}

RB-InformationReconfig-r4 ::=		SEQUENCE {
	rb-Identity							RB-Identity,
	pdcp-Info							PDCP-InfoReconfig-r4				OPTIONAL,
	pdcp-SN-Info						PDCP-SN-Info						OPTIONAL,
	rlc-Info							RLC-Info							OPTIONAL,
	rb-MappingInfo						RB-MappingInfo						OPTIONAL,
	rb-StopContinue						RB-StopContinue						OPTIONAL
}

RB-InformationReconfig-r5 ::=		SEQUENCE {
	rb-Identity							RB-Identity,
	pdcp-Info							PDCP-InfoReconfig-r4				OPTIONAL,
	pdcp-SN-Info						PDCP-SN-Info						OPTIONAL,
	rlc-Info							RLC-Info-r5							OPTIONAL,
	rb-MappingInfo						RB-MappingInfo-r5					OPTIONAL,
	rb-StopContinue						RB-StopContinue						OPTIONAL
}

RB-InformationReconfig-r6 ::=		SEQUENCE {
	rb-Identity							RB-Identity,
	pdcp-Info							PDCP-InfoReconfig-r4				OPTIONAL,
	pdcp-SN-Info						PDCP-SN-Info						OPTIONAL,
	rlc-Info							RLC-Info-r6							OPTIONAL,
	rb-MappingInfo						RB-MappingInfo-r6					OPTIONAL,
	rb-StopContinue						RB-StopContinue						OPTIONAL
}

RB-InformationReconfig-r7 ::=		SEQUENCE {
	rb-Identity							RB-Identity,
	pdcp-Info							PDCP-InfoReconfig-r4				OPTIONAL,
	pdcp-SN-Info						PDCP-SN-Info						OPTIONAL,
	rlc-Info							RLC-Info-r7							OPTIONAL,
	rb-MappingInfo						RB-MappingInfo-r7					OPTIONAL,
	rb-StopContinue						RB-StopContinue						OPTIONAL
}

RB-InformationReconfig-r8 ::=		SEQUENCE {
	rb-Identity							RB-Identity,
	pdcp-Info							PDCP-InfoReconfig-r4				OPTIONAL,
	pdcp-SN-Info						PDCP-SN-Info						OPTIONAL,
	rlc-Info							RLC-Info-r7							OPTIONAL,
	rb-MappingInfo						RB-MappingInfo-r8					OPTIONAL,
	rb-StopContinue						RB-StopContinue						OPTIONAL
}

RB-InformationReconfig-r11 ::=		SEQUENCE {
	rb-Identity							RB-Identity,
	pdcp-Info							PDCP-InfoReconfig-r4				OPTIONAL,
	pdcp-SN-Info						PDCP-SN-Info						OPTIONAL,
	rlc-Info							RLC-Info-r11						OPTIONAL,
	rb-MappingInfo						RB-MappingInfo-r8					OPTIONAL,
	rb-StopContinue						RB-StopContinue						OPTIONAL
}

RB-InformationReconfigList ::=		SEQUENCE (SIZE (1..maxRB)) OF
										RB-InformationReconfig

RB-InformationReconfigList-r4 ::=	SEQUENCE (SIZE (1..maxRB)) OF
										RB-InformationReconfig-r4

RB-InformationReconfigList-r5 ::=	SEQUENCE (SIZE (1..maxRB)) OF
										RB-InformationReconfig-r5

RB-InformationReconfigList-r6 ::=	SEQUENCE (SIZE (1..maxRB)) OF
										RB-InformationReconfig-r6

RB-InformationReconfigList-r7 ::=	SEQUENCE (SIZE (1..maxRB)) OF
										RB-InformationReconfig-r7

RB-InformationReconfigList-r8 ::=	SEQUENCE (SIZE (1..maxRB)) OF
										RB-InformationReconfig-r8

RB-InformationReconfigList-r11 ::=	SEQUENCE (SIZE (1..maxRB)) OF
										RB-InformationReconfig-r11

RB-InformationReleaseList ::=		SEQUENCE (SIZE (1..maxRB)) OF
										RB-Identity

RB-InformationSetup ::=				SEQUENCE {
	rb-Identity							RB-Identity,
	pdcp-Info							PDCP-Info							OPTIONAL,
	rlc-InfoChoice						RLC-InfoChoice,
	rb-MappingInfo						RB-MappingInfo
}

RB-InformationSetup-r4 ::=			SEQUENCE {
	rb-Identity							RB-Identity,
	pdcp-Info							PDCP-Info-r4						OPTIONAL,
	rlc-InfoChoice						RLC-InfoChoice,
	rb-MappingInfo						RB-MappingInfo
}

RB-InformationSetup-r5 ::=			SEQUENCE {
	rb-Identity							RB-Identity,
	pdcp-Info							PDCP-Info-r4						OPTIONAL,
	rlc-InfoChoice						RLC-InfoChoice-r5,
	rb-MappingInfo						RB-MappingInfo-r5
}

RB-InformationSetup-r6 ::=			SEQUENCE {
	rb-Identity							RB-Identity,
	pdcp-Info							PDCP-Info-r4						OPTIONAL,
	rlc-InfoChoice						RLC-InfoChoice-r6,
	rb-MappingInfo						RB-MappingInfo-r6
}

RB-InformationSetup-r7 ::=			SEQUENCE {
	rb-Identity							RB-Identity,
	pdcp-Info							PDCP-Info-r4						OPTIONAL,
	rlc-InfoChoice						RLC-InfoChoice-r7,
	rb-MappingInfo						RB-MappingInfo-r7
}

RB-InformationSetup-r8 ::=			SEQUENCE {
	rb-Identity							RB-Identity,
	pdcp-Info							PDCP-Info-r4						OPTIONAL,
	rlc-InfoChoice						RLC-InfoChoice-r7,
	rb-MappingInfo						RB-MappingInfo-r8
}

RB-InformationSetup-r11 ::=			SEQUENCE {
	rb-Identity							RB-Identity,
	pdcp-Info							PDCP-Info-r4						OPTIONAL,
	rlc-InfoChoice						RLC-InfoChoice-r11,
	rb-MappingInfo						RB-MappingInfo-r8
}

RB-InformationSetupList ::=			SEQUENCE (SIZE (1..maxRBperRAB)) OF
										RB-InformationSetup

RB-InformationSetupList-r4 ::=		SEQUENCE (SIZE (1..maxRBperRAB)) OF
										RB-InformationSetup-r4

RB-InformationSetupList-r5 ::=		SEQUENCE (SIZE (1..maxRBperRAB)) OF
										RB-InformationSetup-r5

RB-InformationSetupList-r6 ::=		SEQUENCE (SIZE (1..maxRBperRAB)) OF
										RB-InformationSetup-r6

RB-InformationSetupList-r7 ::=		SEQUENCE (SIZE (1..maxRBperRAB)) OF
										RB-InformationSetup-r7

RB-InformationSetupList-r8 ::=		SEQUENCE (SIZE (1..maxRBperRAB)) OF
										RB-InformationSetup-r8

RB-InformationSetupList-r11 ::=		SEQUENCE (SIZE (1..maxRBperRAB)) OF
										RB-InformationSetup-r11

RB-MappingInfo ::=					SEQUENCE (SIZE (1..maxRBMuxOptions)) OF
										RB-MappingOption

RB-MappingInfo-r5 ::=				SEQUENCE (SIZE (1..maxRBMuxOptions)) OF
										RB-MappingOption-r5

RB-MappingInfo-r6 ::=				SEQUENCE (SIZE (1..maxRBMuxOptions)) OF
										RB-MappingOption-r6

RB-MappingInfo-r7 ::=				SEQUENCE (SIZE (1..maxRBMuxOptions)) OF
										RB-MappingOption-r7

RB-MappingInfo-r8 ::=				SEQUENCE (SIZE (1..maxRBMuxOptions)) OF
										RB-MappingOption-r8

RB-MappingOption ::=				SEQUENCE {
	ul-LogicalChannelMappings			UL-LogicalChannelMappings			OPTIONAL,
	dl-LogicalChannelMappingList		DL-LogicalChannelMappingList		OPTIONAL
}

RB-MappingOption-r5 ::=				SEQUENCE {
	ul-LogicalChannelMappings			UL-LogicalChannelMappings			OPTIONAL,
	dl-LogicalChannelMappingList		DL-LogicalChannelMappingList-r5		OPTIONAL
}

RB-MappingOption-r6 ::=				SEQUENCE {
	ul-LogicalChannelMappings			UL-LogicalChannelMappings-r6		OPTIONAL,
	dl-LogicalChannelMappingList		DL-LogicalChannelMappingList-r5		OPTIONAL
}

RB-MappingOption-r7 ::=				SEQUENCE {
	ul-LogicalChannelMappings			UL-LogicalChannelMappings-r6		OPTIONAL,
	dl-LogicalChannelMappingList		DL-LogicalChannelMappingList-r7		OPTIONAL
}

RB-MappingOption-r8 ::=				SEQUENCE {
	ul-LogicalChannelMappings			UL-LogicalChannelMappings-r8		OPTIONAL,
	dl-LogicalChannelMappingList		DL-LogicalChannelMappingList-r7		OPTIONAL
}

RB-PDCPContextRelocation ::=			SEQUENCE {
	rb-Identity								RB-Identity,
	dl-RFC3095-Context-Relocation			BOOLEAN,
	ul-RFC3095-Context-Relocation			BOOLEAN
}

RB-PDCPContextRelocationList ::=			SEQUENCE (SIZE (1..maxRBallRABs)) OF
											RB-PDCPContextRelocation

RB-StopContinue ::=					ENUMERATED {
										stopRB, continueRB }

RB-WithPDCP-Info ::=				SEQUENCE {
	rb-Identity							RB-Identity,
	pdcp-SN-Info						PDCP-SN-Info
}

RB-WithPDCP-InfoList ::=			SEQUENCE (SIZE (1..maxRBallRABs)) OF
										RB-WithPDCP-Info

ReceivingWindowSize ::=				ENUMERATED {
										rw1, rw8, rw16, rw32, rw64, rw128, rw256,
										rw512, rw768, rw1024, rw1536, rw2047,
										rw2560, rw3072, rw3584, rw4095 }

RetrievableConfig ::=	SEQUENCE {
	retrievableConfigIdentity			RetrievableConfigIdentity,
	retrievableConfigData				RetrievableConfigData
}

RetrievableConfigData ::=	SEQUENCE {
	srb-InformationSetupList			SRB-InformationSetupList-r11			OPTIONAL,
	rab-InformationSetupList			RAB-InformationSetupList-r11			OPTIONAL,
	rb-InformationReconfigList		RB-InformationReconfigList-r11		OPTIONAL,
	ul-CommonTransChInfo				UL-CommonTransChInfo-r12				OPTIONAL,
	ul-TransChInfoList					UL-AddReconfTransChInfoList-r8		OPTIONAL,
	dl-CommonTransChInfo				DL-CommonTransChInfo-r4				OPTIONAL,
	dl-TransChInfoList					DL-AddReconfTransChInfoList-r13		OPTIONAL,
	dtx-drx-Info						DTX-DRX-Info-r12						OPTIONAL,
	hs-scch-LessInfo					HS-SCCH-LessInfo-r7					OPTIONAL,
	mimoParameters						MIMO-Parameters-r9						OPTIONAL,
	mimo4x4Parameters					MIMO4x4-Parameters						OPTIONAL,
	dch-Enhancements-Info-FDD			DCH-Enhancements-Info-FDD				OPTIONAL,
	ul-EDCH-Information				UL-EDCH-Information-r11				OPTIONAL,
	dl-HSPDSCH-Information			DL-HSPDSCH-Information-r12			OPTIONAL,
	dl-SecondaryCellInfoFDD			DL-SecondaryCellInfoFDD-r11			OPTIONAL,
	additionalDLSecCellInfoListFDD	AdditionalDLSecCellInfoListFDD-r11	OPTIONAL,
	additionalDLSecCellInfoListFDD2	AdditionalDLSecCellInfoListFDD2		OPTIONAL
}

RetrievableConfigIdentity ::=		INTEGER (0..maxRetrievConfig-1)

RetrievableConfigInfo ::=			SEQUENCE {
	retrievableConfigToBeInvoked		RetrievableConfigIdentity			OPTIONAL,
	retrievableConfigToBeStored		RetrievableConfigIdentity			OPTIONAL,
	retrievableConfigToBeRemoved		RetrievableConfigListToRemove		OPTIONAL,
	preconfiguredRetrievableConfig	RetrievableConfig-List			OPTIONAL
}

RetrievableConfig-List ::= 	SEQUENCE (SIZE(1.. maxRetrievConfig)) OF
										RetrievableConfig

RetrievableConfigListToRemove ::=	SEQUENCE (SIZE (1..maxRetrievConfig)) OF
											RetrievableConfigIdentity



RFC2507-Info ::=					SEQUENCE {
	f-MAX-PERIOD						INTEGER (1..65535)					DEFAULT 256,
	f-MAX-TIME							INTEGER (1..255)					DEFAULT 5,
	max-HEADER							INTEGER (60..65535)					DEFAULT 168,
	tcp-SPACE							INTEGER (3..255)					DEFAULT 15,
	non-TCP-SPACE						INTEGER (3..65535)					DEFAULT 15,
	-- TABULAR: expectReordering has only two possible values, so using Optional or Default
	-- would be wasteful
	expectReordering					ExpectReordering
}

RFC3095-Info-r4 ::=				SEQUENCE {
	rohcProfileList						ROHC-ProfileList-r4,
	ul-RFC3095							UL-RFC3095-r4						OPTIONAL,
	dl-RFC3095							DL-RFC3095-r4						OPTIONAL
}

RLC-Info ::=						SEQUENCE {
	ul-RLC-Mode							UL-RLC-Mode							OPTIONAL,
	dl-RLC-Mode							DL-RLC-Mode							OPTIONAL
}

RLC-Info-r5 ::=						SEQUENCE {
	ul-RLC-Mode							UL-RLC-Mode							OPTIONAL,
	dl-RLC-Mode							DL-RLC-Mode-r5						OPTIONAL,
	rlc-OneSidedReEst					BOOLEAN
}

RLC-Info-r6 ::=						SEQUENCE {
	ul-RLC-Mode							UL-RLC-Mode							OPTIONAL,
	dl-RLC-Mode							DL-RLC-Mode-r6						OPTIONAL,
	rlc-OneSidedReEst					BOOLEAN,
	altE-bitInterpretation				ENUMERATED { true }					OPTIONAL
}

RLC-Info-r7 ::=						SEQUENCE {
	ul-RLC-Mode							UL-RLC-Mode							OPTIONAL,
	dl-RLC-Mode							DL-RLC-Mode-r7						OPTIONAL,
	rlc-OneSidedReEst					BOOLEAN,
	altE-bitInterpretation				ENUMERATED { true }					OPTIONAL,
	useSpecialValueOfHEField			ENUMERATED { true }					OPTIONAL
}

RLC-Info-r11 ::=						SEQUENCE {
	ul-RLC-Mode							UL-RLC-Mode							OPTIONAL,
	dl-RLC-Mode							DL-RLC-Mode-r11						OPTIONAL,
	rlc-OneSidedReEst					BOOLEAN,
	altE-bitInterpretation				ENUMERATED { true }					OPTIONAL,
	useSpecialValueOfHEField			ENUMERATED { true }					OPTIONAL
}

RLC-Info-MCCH-r6 ::=				SEQUENCE {
	dl-UM-RLC-LI-size					DL-UM-RLC-LI-size,
	dl-UM-RLC-OutOSeqDelivery-Info		UM-RLC-OutOSeqDelivery-Info-r6		OPTIONAL
}

RLC-Info-MSCH-r6 ::=				SEQUENCE {
	dl-UM-RLC-LI-size					DL-UM-RLC-LI-size
}

RLC-Info-MTCH-r6 ::=				SEQUENCE {
	dl-UM-RLC-LI-size					DL-UM-RLC-LI-size,
	dl-UM-RLC-DuplAvoid-Reord-Info		UM-RLC-DuplAvoid-Reord-Info-r6		OPTIONAL
}

RLC-InfoChoice ::=					CHOICE {
	rlc-Info							RLC-Info,
	same-as-RB							RB-Identity
}

RLC-InfoChoice-r5 ::=				CHOICE {
	rlc-Info							RLC-Info-r5,
	same-as-RB							RB-Identity
}

RLC-InfoChoice-r6 ::=				CHOICE {
	rlc-Info							RLC-Info-r6,
	same-as-RB							RB-Identity
}

RLC-InfoChoice-r7 ::=				CHOICE {
	rlc-Info							RLC-Info-r7,
	same-as-RB							RB-Identity
}

RLC-InfoChoice-r11 ::=				CHOICE {
	rlc-Info							RLC-Info-r11,
	same-as-RB							RB-Identity
}

RLC-PDU-Size ::=					OctetModeRLC-SizeInfoType1

RLC-PDU-SizeConstraint ::=			SEQUENCE {
	lengthIndicatorSize					ENUMERATED { size7, size15 }		OPTIONAL,
	-- the actual values are (IE value * 8) + 16
	minRLC-PDU-Size						INTEGER (0..1503),
	largestRLC-PDU-Size					INTEGER (0..1503)
}

RLC-PDU-SizeList ::=				SEQUENCE (SIZE (1..maxRLCPDUsizePerLogChan)) OF
										RLC-PDU-Size

RLC-SequenceNumber ::=				INTEGER (0..4095)

RLC-SizeInfo ::=					SEQUENCE {
	rlc-SizeIndex						INTEGER (1..maxTF)
}

RLC-SizeExplicitList ::=			SEQUENCE (SIZE	(1..maxTF))	OF
										RLC-SizeInfo

ROHC-Profile-r4 ::=					INTEGER (1..3)

ROHC-ProfileList-r4 ::=				SEQUENCE (SIZE	(1..maxROHC-Profile-r4))	OF
										ROHC-Profile-r4

ROHC-PacketSize-r4 ::=				INTEGER (2..1500)

ROHC-PacketSizeList-r4 ::=			SEQUENCE (SIZE	(1..maxROHC-PacketSizes-r4))	OF
										ROHC-PacketSize-r4

SRB-InformationSetup ::=			SEQUENCE {
	-- The default value for rb-Identity is the smallest value not used yet.
	rb-Identity							RB-Identity							OPTIONAL,
	rlc-InfoChoice						RLC-InfoChoice,
	rb-MappingInfo						RB-MappingInfo
}

SRB-InformationSetup-r5 ::=			SEQUENCE {
	-- The default value for rb-Identity is the smallest value not used yet.
	rb-Identity							RB-Identity							OPTIONAL,
	rlc-InfoChoice						RLC-InfoChoice-r5,
	rb-MappingInfo						RB-MappingInfo-r5
}

SRB-InformationSetup-r6 ::=			SEQUENCE {
	-- The default value for rb-Identity is the smallest value not used yet.
	rb-Identity							RB-Identity							OPTIONAL,
	rlc-InfoChoice						RLC-InfoChoice-r6,
	rb-MappingInfo						RB-MappingInfo-r6
}

SRB-InformationSetup-r7 ::=			SEQUENCE {
	-- The default value for rb-Identity is the smallest value not used yet.
	rb-Identity							RB-Identity							OPTIONAL,
	rlc-InfoChoice						RLC-InfoChoice-r7,
	rb-MappingInfo						RB-MappingInfo-r7
}

SRB-InformationSetup-r8 ::=			SEQUENCE {
	-- The default value for rb-Identity is the smallest value not used yet.
	rb-Identity							RB-Identity							OPTIONAL,
	rlc-InfoChoice						RLC-InfoChoice-r7,
	rb-MappingInfo						RB-MappingInfo-r8
}

SRB-InformationSetup-r11 ::=			SEQUENCE {
	-- The default value for rb-Identity is the smallest value not used yet.
	rb-Identity							RB-Identity							OPTIONAL,
	rlc-InfoChoice						RLC-InfoChoice-r11,
	rb-MappingInfo						RB-MappingInfo-r8
}

SRB-InformationSetupList ::=		SEQUENCE (SIZE (1..maxSRBsetup)) OF
										SRB-InformationSetup

SRB-InformationSetupList-r5 ::=		SEQUENCE (SIZE (1..maxSRBsetup)) OF
										SRB-InformationSetup-r5

SRB-InformationSetupList-r6 ::=		SEQUENCE (SIZE (1..maxSRBsetup)) OF
										SRB-InformationSetup-r6

SRB-InformationSetupList-r7 ::=		SEQUENCE (SIZE (1..maxSRBsetup)) OF
										SRB-InformationSetup-r7

SRB-InformationSetupList-r8 ::=		SEQUENCE (SIZE (1..maxSRBsetup)) OF
										SRB-InformationSetup-r8

SRB-InformationSetupList-r11 ::=	SEQUENCE (SIZE (1..maxSRBsetup)) OF
										SRB-InformationSetup-r11

SRB-InformationSetupList2 ::=		SEQUENCE (SIZE (3..4)) OF
										SRB-InformationSetup

SRB-InformationSetupList2-r6 ::=	SEQUENCE (SIZE (3..4)) OF
										SRB-InformationSetup-r6

SRB-InformationSetupList2-r7 ::=	SEQUENCE (SIZE (3..4)) OF
										SRB-InformationSetup-r7

SRB-InformationSetupList2-r8 ::=	SEQUENCE (SIZE (3..4)) OF
										SRB-InformationSetup-r8

TimerDAR-r6 ::=						ENUMERATED {
										ms40, ms80, ms120, ms160, ms240, ms320, ms480, ms640,
										ms960, ms1280, ms1920, ms2560, ms3840, ms5120 }

TimerDiscard ::=					ENUMERATED {
										td0-1, td0-25, td0-5, td0-75,
										td1, td1-25, td1-5, td1-75,
										td2, td2-5, td3, td3-5, td4,
										td4-5, td5, td7-5 }

TimerEPC ::=						ENUMERATED {
										te50, te60, te70, te80, te90,
										te100, te120, te140, te160, te180,
										te200, te300, te400, te500, te700,
										te900 }

TimerMRW ::=						ENUMERATED {
										te50, te60, te70, te80, te90, te100,
										te120, te140, te160, te180, te200,
										te300, te400, te500, te700, te900 }

TimerOSD-r6 ::=						ENUMERATED {
										ms40, ms80, ms120, ms160, ms240, ms320, ms480, ms640,
										ms960, ms1280, ms1920, ms2560, ms3840, ms5120 }

TimerPoll ::=						ENUMERATED {
										tp10, tp20, tp30, tp40, tp50,
										tp60, tp70, tp80, tp90, tp100,
										tp110, tp120, tp130, tp140, tp150,
										tp160, tp170, tp180, tp190, tp200,
										tp210, tp220, tp230, tp240, tp250,
										tp260, tp270, tp280, tp290, tp300,
										tp310, tp320, tp330, tp340, tp350,
										tp360, tp370, tp380, tp390, tp400,
										tp410, tp420, tp430, tp440, tp450,
										tp460, tp470, tp480, tp490, tp500,
										tp510, tp520, tp530, tp540, tp550,
										tp600, tp650, tp700, tp750, tp800,
										tp850, tp900, tp950, tp1000 }

TimerPollPeriodic ::=				ENUMERATED {
										tper100, tper200, tper300, tper400,
										tper500, tper750, tper1000, tper2000 }

TimerPollProhibit ::=				ENUMERATED {
										tpp10, tpp20, tpp30, tpp40, tpp50,
										tpp60, tpp70, tpp80, tpp90, tpp100,
										tpp110, tpp120, tpp130, tpp140, tpp150,
										tpp160, tpp170, tpp180, tpp190, tpp200,
										tpp210, tpp220, tpp230, tpp240, tpp250,
										tpp260, tpp270, tpp280, tpp290, tpp300,
										tpp310, tpp320, tpp330, tpp340, tpp350,
										tpp360, tpp370, tpp380, tpp390, tpp400,
										tpp410, tpp420, tpp430, tpp440, tpp450,
										tpp460, tpp470, tpp480, tpp490, tpp500,
										tpp510, tpp520, tpp530, tpp540, tpp550,
										tpp600, tpp650, tpp700, tpp750, tpp800,
										tpp850, tpp900, tpp950, tpp1000 }

TimerReordering ::=					ENUMERATED {
										tr50, tr100, tr150, tr200, tr400, tr600, tr800, tr1000 }

TimerRST ::=						ENUMERATED {
										tr50, tr100, tr150, tr200, tr250, tr300,
										tr350, tr400, tr450, tr500, tr550,
										tr600, tr700, tr800, tr900, tr1000 }

TimerStatusPeriodic ::=				ENUMERATED {
										tsp100, tsp200,	tsp300, tsp400, tsp500,
										tsp750, tsp1000, tsp2000 }

TimerStatusProhibit ::=				ENUMERATED {
										tsp10,tsp20,tsp30,tsp40,tsp50,
										tsp60,tsp70,tsp80,tsp90,tsp100,
										tsp110,tsp120,tsp130,tsp140,tsp150,
										tsp160,tsp170,tsp180,tsp190,tsp200,
										tsp210,tsp220,tsp230,tsp240,tsp250,
										tsp260,tsp270,tsp280,tsp290,tsp300,
										tsp310,tsp320,tsp330,tsp340,tsp350,
										tsp360,tsp370,tsp380,tsp390,tsp400,
										tsp410,tsp420,tsp430,tsp440,tsp450,
										tsp460,tsp470,tsp480,tsp490,tsp500,
										tsp510,tsp520,tsp530,tsp540,tsp550,
										tsp600,tsp650,tsp700,tsp750,tsp800,
										tsp850,tsp900,tsp950,tsp1000 }

TransmissionRLC-Discard ::=			CHOICE {
	timerBasedExplicit					ExplicitDiscard,
	timerBasedNoExplicit				NoExplicitDiscard,
	maxDAT-Retransmissions				MaxDAT-Retransmissions,
	noDiscard							MaxDAT
}

TransmissionWindowSize ::=			ENUMERATED {
										tw1, tw8, tw16, tw32, tw64, tw128, tw256,
										tw512, tw768, tw1024, tw1536, tw2047,
										tw2560, tw3072, tw3584, tw4095 }

-- Actual bit rate per each value is defined in [62] and [63]
UL-AMR-Rate ::=						ENUMERATED {
										t0, t1, t2, t3, t4, t5, t6, t7, t8, spare7, spare6, spare5,
										spare4, spare3, spare2, spare1 }

UL-AM-RLC-Mode ::=					SEQUENCE {
	transmissionRLC-Discard				TransmissionRLC-Discard,
	transmissionWindowSize				TransmissionWindowSize,
	timerRST							TimerRST,
	max-RST								MaxRST,
	pollingInfo							PollingInfo							OPTIONAL
}

UL-CounterSynchronisationInfo ::=		SEQUENCE {
	rB-WithPDCP-InfoList					RB-WithPDCP-InfoList 	OPTIONAL,
	startList								STARTList
}

UL-LogicalChannelMapping ::=		SEQUENCE {
	-- TABULAR: UL-TransportChannelType contains TransportChannelIdentity as well.
	ul-TransportChannelType				UL-TransportChannelType,
	logicalChannelIdentity				LogicalChannelIdentity				OPTIONAL,
	rlc-SizeList						CHOICE {
		allSizes							NULL,
		configured							NULL,
		explicitList						RLC-SizeExplicitList
	},
	mac-LogicalChannelPriority			MAC-LogicalChannelPriority
}

UL-LogicalChannelMapping-r6 ::=		SEQUENCE {
	ul-TrCH-Type						CHOICE {
		dch-rach-usch						SEQUENCE {
			-- TABULAR: UL-TransportChannelType contains TransportChannelIdentity as well.
			ul-TransportChannelType				UL-TransportChannelType,
			logicalChannelIdentity				LogicalChannelIdentity				OPTIONAL,
			rlc-SizeList						CHOICE {
				allSizes							NULL,
				configured							NULL,
				explicitList						RLC-SizeExplicitList
			}
		},
		e-dch								SEQUENCE {
			logicalChannelIdentity				LogicalChannelIdentity,
			e-DCH-MAC-d-FlowIdentity			E-DCH-MAC-d-FlowIdentity,
			ddi									DDI,
			rlc-PDU-SizeList					RLC-PDU-SizeList,
			includeInSchedulingInfo				BOOLEAN
		}
	},
	mac-LogicalChannelPriority			MAC-LogicalChannelPriority
}

UL-LogicalChannelMapping-r8 ::=		SEQUENCE {
	ul-TrCH-Type						CHOICE {
		dch-rach-usch						SEQUENCE {
			-- TABULAR: UL-TransportChannelType contains TransportChannelIdentity as well.
			ul-TransportChannelType				UL-TransportChannelType,
			logicalChannelIdentity				LogicalChannelIdentity				OPTIONAL,
			rlc-SizeList						CHOICE {
				allSizes							NULL,
				configured							NULL,
				explicitList						RLC-SizeExplicitList
			}
		},
		e-dch								SEQUENCE {
			logicalChannelIdentity				LogicalChannelIdentity,
			e-DCH-MAC-d-FlowIdentity			E-DCH-MAC-d-FlowIdentity,
			rlc-PDU-Size						CHOICE {
				fixedSize							SEQUENCE {
					ddi									DDI,
					rlc-PDU-SizeList					RLC-PDU-SizeList
				},
				flexibleSize						RLC-PDU-SizeConstraint
			},
			includeInSchedulingInfo				BOOLEAN
		}
	},
	mac-LogicalChannelPriority			MAC-LogicalChannelPriority
}

UL-LogicalChannelMappingList ::=	SEQUENCE {
	-- rlc-LogicalChannelMappingIndicator shall be set to TRUE in this version
	-- of the specification
	rlc-LogicalChannelMappingIndicator	BOOLEAN,
	ul-LogicalChannelMapping			SEQUENCE (SIZE (maxLoCHperRLC)) OF
										UL-LogicalChannelMapping
}

UL-LogicalChannelMappingList-r6 ::=	SEQUENCE {
	-- rlc-LogicalChannelMappingIndicator shall be set to TRUE in this version
	-- of the specification
	rlc-LogicalChannelMappingIndicator	BOOLEAN,
	ul-LogicalChannelMapping			SEQUENCE (SIZE (maxLoCHperRLC)) OF
											UL-LogicalChannelMapping-r6
}

UL-LogicalChannelMappingList-r8 ::=	SEQUENCE {
	-- rlc-LogicalChannelMappingIndicator shall be set to TRUE in this version
	-- of the specification
	rlc-LogicalChannelMappingIndicator	BOOLEAN,
	ul-LogicalChannelMapping			SEQUENCE (SIZE (maxLoCHperRLC)) OF
											UL-LogicalChannelMapping-r8
}

UL-LogicalChannelMappings ::=		CHOICE {
	oneLogicalChannel					UL-LogicalChannelMapping,
	twoLogicalChannels					UL-LogicalChannelMappingList
}

UL-LogicalChannelMappings-r6 ::=	CHOICE {
	oneLogicalChannel					UL-LogicalChannelMapping-r6,
	twoLogicalChannels					UL-LogicalChannelMappingList-r6
}

UL-LogicalChannelMappings-r8 ::=	CHOICE {
	oneLogicalChannel					UL-LogicalChannelMapping-r8,
	twoLogicalChannels					UL-LogicalChannelMappingList-r8
}

UL-RFC3095-r4 ::=					SEQUENCE {
	-- dummy1 is not used in this version of the specification and shall be ignored by the receiver.
	dummy1								CID-InclusionInfo-r4,
	max-CID								INTEGER (1..16383)					DEFAULT 15,
	-- dummy is not used in this version of the specification and
	-- it should be ignored by the receiver.
	dummy								ROHC-PacketSizeList-r4
}

UL-RLC-Mode ::=						CHOICE {
	ul-AM-RLC-Mode						UL-AM-RLC-Mode,
	ul-UM-RLC-Mode						UL-UM-RLC-Mode,
	ul-TM-RLC-Mode						UL-TM-RLC-Mode,
	spare								NULL
}

UL-TM-RLC-Mode ::=					SEQUENCE {
	transmissionRLC-Discard				TransmissionRLC-Discard				OPTIONAL,
	segmentationIndication				BOOLEAN
}

UL-UM-RLC-Mode ::=					SEQUENCE {
	transmissionRLC-Discard				TransmissionRLC-Discard				OPTIONAL
}

UL-TransportChannelType ::=			CHOICE {
	dch									TransportChannelIdentity,
	rach								NULL,
	-- dummy is not used in this version of the specification and
	-- if received the UE behaviour is not specified.
	dummy								NULL,
	usch								TransportChannelIdentity
}

UM-RLC-DuplAvoid-Reord-Info-r6 ::=	SEQUENCE {
	timer-DAR							TimerDAR-r6,
	widowSize-DAR						WindowSizeDAR-r6
}

UM-RLC-OutOSeqDelivery-Info-r6 ::=	SEQUENCE {
	timer-OSD							TimerOSD-r6							OPTIONAL,
	windowSize-OSD						WindowSizeOSD-r6
}

WindowSizeDAR-r6 ::=				ENUMERATED {
										ws4, ws8, ws16, ws32, ws40, ws48,
										ws56, ws64 }

WindowSizeOSD-r6 ::=				ENUMERATED {
										ws8, ws16, ws32, ws40, ws48,
										ws56, ws64 }

-- ***************************************************
--
--     TRANSPORT CHANNEL INFORMATION ELEMENTS (10.3.5)
--
-- ***************************************************

AddOrReconfMAC-dFlow ::=			SEQUENCE {
	mac-hs-AddReconfQueue-List			MAC-hs-AddReconfQueue-List		OPTIONAL,
	mac-hs-DelQueue-List				MAC-hs-DelQueue-List			OPTIONAL
}

AddOrReconfMAC-ehs-ReordQ ::=		SEQUENCE {
	mac-ehs-AddReconfQueue-List			MAC-ehs-AddReconfReordQ-List	OPTIONAL,
	-- dummy is not used in this version of the specification, it should
	-- not be sent and if received it should be ignored.
	dummy								MAC-ehs-DelReordQ-List			OPTIONAL
}

AddOrReconfMAC-ehs-ReordQ-r9 ::=		SEQUENCE {
	mac-ehs-AddReconfQueue-List			MAC-ehs-AddReconfReordQ-List-r9	OPTIONAL
}

AddOrReconfMAC-ehs-ReordQ-TDD128-v9c0ext ::=		SEQUENCE {
	mac-ehs-AddReconfQueue-List			MAC-ehs-AddReconfReordQ-List-TDD128-v9c0ext	OPTIONAL
}

AddOrReconfMAC-ehs-ReordQ-r11 ::=		SEQUENCE {
	mac-ehs-AddReconfQueue-List			MAC-ehs-AddReconfReordQ-List-r11	OPTIONAL
}

AllowedTFC-List ::=					SEQUENCE (SIZE (1..maxTFC)) OF
										TFC-Value

AllowedTFI-List ::=					SEQUENCE (SIZE (1..maxTF)) OF
										INTEGER (0..31)

BitModeRLC-SizeInfo ::=				CHOICE {
	sizeType1							INTEGER (0..127),
	-- Actual value sizeType2 = (part1 * 8) + 128 + part2
	sizeType2							SEQUENCE {
		part1								INTEGER (0..15),
		part2								INTEGER (1..7)					OPTIONAL
	},
	-- Actual value sizeType3 = (part1 * 16) + 256 + part2
	sizeType3							SEQUENCE {
		part1								INTEGER (0..47),
		part2								INTEGER (1..15)					OPTIONAL
	},
	-- Actual value sizeType4 = (part1 * 64) + 1024 + part2
	sizeType4							SEQUENCE {
		part1								INTEGER (0..62),
		part2								INTEGER (1..63)					OPTIONAL
	}
}

-- Actual value BLER-QualityValue = IE value * 0.1
BLER-QualityValue ::=				INTEGER (-63..0)

ChannelCodingType ::=				CHOICE {
	-- noCoding is only used for TDD in this version of the specification,
	-- otherwise it should be ignored
	noCoding							NULL,
	convolutional						CodingRate,
	turbo								NULL
}

CodingRate ::=						ENUMERATED {
										half,
										third }

Common-E-DCH-MAC-d-Flow ::=		SEQUENCE {
	mac-d-FlowIdentity					E-DCH-MAC-d-FlowIdentity,
	mac-d-FlowPowerOffset				E-DCH-MAC-d-FlowPowerOffset,
	mac-d-FlowMaxRetrans				E-DCH-MAC-d-FlowMaxRetrans,
	mac-d-FlowMultiplexingList			E-DCH-MAC-d-FlowMultiplexingList	OPTIONAL,
	e-dch-mac-d-flow-retransmission-timer	E-DCH-MAC-d-FlowRetransTimer	OPTIONAL
}

Common-E-DCH-MAC-d-FlowList ::=		SEQUENCE (SIZE (1..maxE-DCHMACdFlow)) OF
										Common-E-DCH-MAC-d-Flow

Common-E-DCH-MAC-d-Flow-Info-ConcurrentTTI ::=		SEQUENCE {
	mac-d-FlowIdentity					E-DCH-MAC-d-FlowIdentity,
	mac-d-FlowPowerOffset				E-DCH-MAC-d-FlowPowerOffset	OPTIONAL,
	mac-d-FlowMaxRetrans				E-DCH-MAC-d-FlowMaxRetrans	OPTIONAL
}

Common-E-DCH-MAC-d-Flow-Info-List-ConcurrentTTI ::=		SEQUENCE (SIZE (1..maxE-DCHMACdFlow)) OF
													Common-E-DCH-MAC-d-Flow-Info-ConcurrentTTI

CommonDynamicTF-Info ::=			SEQUENCE {
	rlc-Size							CHOICE {
		fdd									SEQUENCE {
			octetModeRLC-SizeInfoType2			OctetModeRLC-SizeInfoType2
		},
		tdd									SEQUENCE {
			commonTDD-Choice					CHOICE {
				bitModeRLC-SizeInfo					BitModeRLC-SizeInfo,
				octetModeRLC-SizeInfoType1			OctetModeRLC-SizeInfoType1
			}
		}
	},
	numberOfTbSizeList				SEQUENCE (SIZE (1..maxTF)) OF
											NumberOfTransportBlocks,
	logicalChannelList				LogicalChannelList
}

CommonDynamicTF-Info-DynamicTTI ::=	SEQUENCE {
	commonTDD-Choice					CHOICE {
		bitModeRLC-SizeInfo					BitModeRLC-SizeInfo,
		octetModeRLC-SizeInfoType1			OctetModeRLC-SizeInfoType1
	},
	numberOfTbSizeAndTTIList			NumberOfTbSizeAndTTIList,
	logicalChannelList					LogicalChannelList
}

CommonDynamicTF-InfoList ::=		SEQUENCE (SIZE (1..maxTF)) OF
										CommonDynamicTF-Info

CommonDynamicTF-InfoList-DynamicTTI ::= SEQUENCE (SIZE (1..maxTF)) OF
										CommonDynamicTF-Info-DynamicTTI

CommonTransChTFS ::=				SEQUENCE {
	tti									CHOICE {
		tti10								CommonDynamicTF-InfoList,
		tti20								CommonDynamicTF-InfoList,
		tti40								CommonDynamicTF-InfoList,
		tti80								CommonDynamicTF-InfoList,
		dynamic								CommonDynamicTF-InfoList-DynamicTTI
	},
	semistaticTF-Information			SemistaticTF-Information
}

CommonTransChTFS-LCR ::=				SEQUENCE {
	tti									CHOICE {
		tti5								CommonDynamicTF-InfoList,
		tti10								CommonDynamicTF-InfoList,
		tti20								CommonDynamicTF-InfoList,
		tti40								CommonDynamicTF-InfoList,
		tti80								CommonDynamicTF-InfoList,
		dynamic								CommonDynamicTF-InfoList-DynamicTTI
	},
	semistaticTF-Information			SemistaticTF-Information
}

Common-MAC-ehs-ReorderingQueue ::=	SEQUENCE {
	mac-ehs-QueueId						MAC-ehs-QueueId,
	t1-ReleaseTimer						T1-ReleaseTimer,
	reorderingResetTimer				Treset-ResetTimer						OPTIONAL,
	mac-ehsWindowSize					MAC-hs-WindowSize
}

Common-MAC-ehs-ReorderingQueueList ::=	SEQUENCE (SIZE (1.. maxCommonQueueID)) OF
										Common-MAC-ehs-ReorderingQueue

Concurrent-Deployment-2ms-10ms-TTI ::=	SEQUENCE {
	tti-selection							CHOICE	{
		fixed									SEQUENCE	{
			fixed-TTI-Selection							ENUMERATED { tti2, tti10 }
		},
		threshold-based							SEQUENCE	{
			common-E-DCH-TTI-Selection-Thresh			INTEGER (0..15)
		}
	},
	concurrent-TTI-Partition-Index				INTEGER (0..maxEDCHs-1),
	commonEDCHSystemInfoParamConcurrentTTI		CommonEDCHSystemInfoParamConcurrentTTI	OPTIONAL
}

CPCH-SetID ::=						INTEGER (1..maxCPCHsets)

CRC-Size ::=						ENUMERATED {
										crc0, crc8, crc12, crc16, crc24 }

DedicatedDynamicTF-Info ::=			SEQUENCE {
	rlc-Size							CHOICE {
		bitMode								BitModeRLC-SizeInfo,
		octetModeType1						OctetModeRLC-SizeInfoType1
	},
	numberOfTbSizeList				SEQUENCE (SIZE (1..maxTF)) OF
										NumberOfTransportBlocks,
	logicalChannelList				LogicalChannelList
}

DedicatedDynamicTF-Info-DynamicTTI ::= SEQUENCE {
	rlc-Size							CHOICE {
		bitMode								BitModeRLC-SizeInfo,
		octetModeType1						OctetModeRLC-SizeInfoType1
	},
	numberOfTbSizeAndTTIList			NumberOfTbSizeAndTTIList,
	logicalChannelList				LogicalChannelList
}

DedicatedDynamicTF-InfoList ::=		SEQUENCE (SIZE (1..maxTF)) OF
										DedicatedDynamicTF-Info

DedicatedDynamicTF-InfoList-DynamicTTI ::= SEQUENCE (SIZE (1..maxTF)) OF
										DedicatedDynamicTF-Info-DynamicTTI

DedicatedTransChTFS ::=				SEQUENCE {
	tti									CHOICE {
		tti10								DedicatedDynamicTF-InfoList,
		tti20								DedicatedDynamicTF-InfoList,
		tti40								DedicatedDynamicTF-InfoList,
		tti80								DedicatedDynamicTF-InfoList,
		dynamic								DedicatedDynamicTF-InfoList-DynamicTTI
	},
	semistaticTF-Information			SemistaticTF-Information
}

-- The maximum allowed size of DL-AddReconfTransChInfo2List sequence is 16
DL-AddReconfTransChInfo2List ::=	SEQUENCE (SIZE (1..maxTrCHpreconf)) OF
										DL-AddReconfTransChInformation2

-- The maximum allowed size of DL-AddReconfTransChInfoList sequence is 16
DL-AddReconfTransChInfoList ::=		SEQUENCE (SIZE (1..maxTrCHpreconf)) OF
										DL-AddReconfTransChInformation

-- The maximum allowed size of DL-AddReconfTransChInfoList-r4 sequence is 16
DL-AddReconfTransChInfoList-r4 ::=	SEQUENCE (SIZE (1..maxTrCHpreconf)) OF
										DL-AddReconfTransChInformation-r4

-- The maximum allowed size of DL-AddReconfTransChInfoList-r5 sequence is 16
DL-AddReconfTransChInfoList-r5 ::=	SEQUENCE (SIZE (1..maxTrCHpreconf)) OF
										DL-AddReconfTransChInformation-r5

-- The maximum allowed size of DL-AddReconfTransChInfoList-r7 sequence is 16
DL-AddReconfTransChInfoList-r7 ::=	SEQUENCE (SIZE (1..maxTrCHpreconf)) OF
										DL-AddReconfTransChInformation-r7

DL-AddReconfTransChInfoList-r9 ::=	SEQUENCE (SIZE (1..maxTrCHpreconf)) OF
										DL-AddReconfTransChInformation-r9

DL-AddReconfTransChInfoList-r11 ::=	SEQUENCE (SIZE (1..maxTrCHpreconf)) OF
										DL-AddReconfTransChInformation-r11

DL-AddReconfTransChInfoList-r13 ::=	SEQUENCE (SIZE (1..maxTrCH)) OF
										DL-AddReconfTransChInformation-r13

DL-AddReconfTransChInfoList-TDD128-v9c0ext ::=	SEQUENCE (SIZE (1..maxTrCHpreconf)) OF
										DL-AddReconfTransChInformation-TDD128-v9c0ext


-- ASN.1 for IE "Added or Reconfigured DL TrCH information"
-- in case of messages other than: Radio Bearer Release message and
-- Radio Bearer Reconfiguration message
DL-AddReconfTransChInformation ::= 	SEQUENCE {
	dl-TransportChannelType				DL-TrCH-Type,
	dl-transportChannelIdentity			TransportChannelIdentity,
	tfs-SignallingMode					CHOICE {
		explicit-config						TransportFormatSet,
		sameAsULTrCH						UL-TransportChannelIdentity
	},
	dch-QualityTarget					QualityTarget						OPTIONAL,
	-- dummy is not used in this version of the specification, it should
	-- not be sent and if received it should be ignored.
	dummy								TM-SignallingInfo					OPTIONAL
}

DL-AddReconfTransChInformation-r4 ::= 	SEQUENCE {
	dl-TransportChannelType				DL-TrCH-Type,
	dl-transportChannelIdentity			TransportChannelIdentity,
	tfs-SignallingMode					CHOICE {
		explicit-config						TransportFormatSet,
		sameAsULTrCH						UL-TransportChannelIdentity
	},
	dch-QualityTarget					QualityTarget						OPTIONAL
}

DL-AddReconfTransChInformation-r5 ::= 	SEQUENCE {
	dl-TransportChannelType				DL-TrCH-TypeId1-r5,
	tfs-SignallingMode					CHOICE {
		explicit-config						TransportFormatSet,
		sameAsULTrCH						UL-TransportChannelIdentity,
		hsdsch								HSDSCH-Info
	},
	dch-QualityTarget					QualityTarget						OPTIONAL
}

DL-AddReconfTransChInformation-r7 ::= SEQUENCE {
	dl-TransportChannelType				DL-TrCH-TypeId1-r5,
	tfs-SignallingMode					CHOICE {
		explicit-config						TransportFormatSet,
		sameAsULTrCH						UL-TransportChannelIdentity,
		hsdsch								HSDSCH-Info-r7
	},
	dch-QualityTarget					QualityTarget						OPTIONAL
}

DL-AddReconfTransChInformation-r9 ::= SEQUENCE {
	dl-TransportChannelType				DL-TrCH-TypeId1-r5,
	tfs-SignallingMode					CHOICE {
		explicit-config						TransportFormatSet,
		sameAsULTrCH						UL-TransportChannelIdentity,
		hsdsch								HSDSCH-Info-r9
	},
	dch-QualityTarget					QualityTarget						OPTIONAL
}

DL-AddReconfTransChInformation-r11 ::= SEQUENCE {
	dl-TransportChannelType				DL-TrCH-TypeId1-r5,
	tfs-SignallingMode					CHOICE {
		explicit-config						TransportFormatSet,
		sameAsULTrCH						UL-TransportChannelIdentity,
		hsdsch								HSDSCH-Info-r11
	},
	dch-QualityTarget					QualityTarget						OPTIONAL
}

DL-AddReconfTransChInformation-r13 ::= SEQUENCE {
	dl-TransportChannelType				DL-TrCH-TypeId1-r5,
	tfs-SignallingMode						CHOICE {
		explicit-config						TransportFormatSet,
		sameAsULTrCH							UL-TransportChannelIdentity,
		hsdsch									HSDSCH-Info-r13
	},
	dch-QualityTarget						QualityTarget					OPTIONAL
}

DL-AddReconfTransChInformation-TDD128-v9c0ext ::= SEQUENCE {
	hsdsch								HSDSCH-Info-TDD128-v9c0ext		OPTIONAL
}

-- ASN.1 for IE "Added or Reconfigured DL TrCH information"
-- in case of Radio Bearer Release message and
-- Radio Bearer Reconfiguration message
DL-AddReconfTransChInformation2 ::= SEQUENCE {
	dl-TransportChannelType				DL-TrCH-Type,
	transportChannelIdentity			TransportChannelIdentity,
	tfs-SignallingMode					CHOICE {
		explicit-config						TransportFormatSet,
		sameAsULTrCH						UL-TransportChannelIdentity
	},
	qualityTarget						QualityTarget						OPTIONAL
}

DL-CommonTransChInfo ::=			SEQUENCE {
	sccpch-TFCS							TFCS								OPTIONAL,
	-- modeSpecificInfo should be optional. A new version of this IE should be defined
	-- to be used in later versions of messages using this IE
	modeSpecificInfo					CHOICE {
		fdd									SEQUENCE {
			dl-Parameters						CHOICE {
				dl-DCH-TFCS							TFCS,
				sameAsUL							NULL
			}																OPTIONAL
		},
		tdd									SEQUENCE {
			individualDL-CCTrCH-InfoList		IndividualDL-CCTrCH-InfoList
																			OPTIONAL
		}
	}
}

DL-CommonTransChInfo-r4 ::=			SEQUENCE {
	sccpch-TFCS							TFCS								OPTIONAL,
	modeSpecificInfo					CHOICE {
		fdd									SEQUENCE {
			dl-Parameters						CHOICE {
				dl-DCH-TFCS							SEQUENCE {
					tfcs								TFCS				OPTIONAL
				},
				sameAsUL							NULL
			}																OPTIONAL
		},
		tdd									SEQUENCE {
			individualDL-CCTrCH-InfoList		IndividualDL-CCTrCH-InfoList
																			OPTIONAL
		}
	}	OPTIONAL
}

DL-DeletedTransChInfoList ::=		SEQUENCE (SIZE (1..maxTrCH)) OF
										DL-TransportChannelIdentity

DL-DeletedTransChInfoList-r5 ::=	SEQUENCE (SIZE (1..maxTrCH)) OF
										DL-TransportChannelIdentity-r5

DL-DeletedTransChInfoList-r7 ::=	SEQUENCE (SIZE (1..maxTrCH)) OF
										DL-TransportChannelIdentity-r7

DL-TransportChannelIdentity ::=		SEQUENCE {
	dl-TransportChannelType				DL-TrCH-Type,
	dl-TransportChannelIdentity			TransportChannelIdentity
}

DL-TransportChannelIdentity-r5 ::=	SEQUENCE {
	dl-TransportChannelType				DL-TrCH-TypeId2-r5
}

DL-TransportChannelIdentity-r7 ::=	SEQUENCE {
	dl-TransportChannelType				DL-TrCH-TypeId2-r7
}

-- The choice "dsch" should not be used in FDD mode, and if received the UE behaviour is unspecified
DL-TrCH-Type ::=					ENUMERATED {dch, dsch}

DL-TrCH-TypeId1-r5 ::=				CHOICE {
	dch									TransportChannelIdentity,
	-- The choice "dsch" should not be used in FDD mode, and if received
	-- the UE behaviour is unspecified.
	dsch								TransportChannelIdentity,
	hsdsch								NULL
}

DL-TrCH-TypeId2-r5 ::=				CHOICE {
	dch									TransportChannelIdentity,
	-- The choice "dsch" should not be used in FDD mode, and if received
	-- the UE behaviour is unspecified.
	dsch								TransportChannelIdentity,
	hsdsch								MAC-d-FlowIdentity
}

DL-TrCH-TypeId2-r7 ::=				CHOICE {
	dch									TransportChannelIdentity,
	-- The choice "dsch" should not be used in FDD mode, and if received
	-- the UE behaviour is unspecified.
	dsch								TransportChannelIdentity,
	hsdsch								CHOICE {
		mac-hs								MAC-d-FlowIdentity,
		mac-ehs								MAC-ehs-QueueId
	}
}

DRAC-ClassIdentity ::=				INTEGER (1..maxDRACclasses)

DRAC-StaticInformation ::=			SEQUENCE {
	transmissionTimeValidity			TransmissionTimeValidity,
	timeDurationBeforeRetry				TimeDurationBeforeRetry,
	drac-ClassIdentity					DRAC-ClassIdentity
}

DRAC-StaticInformationList ::=		SEQUENCE (SIZE (1..maxTrCH)) OF
										DRAC-StaticInformation

E-DCH-AddReconf-MAC-d-Flow ::=		SEQUENCE {
	mac-d-FlowIdentity					E-DCH-MAC-d-FlowIdentity,
	mac-d-FlowPowerOffset				E-DCH-MAC-d-FlowPowerOffset			OPTIONAL,
	mac-d-FlowMaxRetrans				E-DCH-MAC-d-FlowMaxRetrans			OPTIONAL,
	mac-d-FlowMultiplexingList			E-DCH-MAC-d-FlowMultiplexingList	OPTIONAL,
	transmissionGrantType				CHOICE {
		non-ScheduledTransGrantInfo			SEQUENCE {
			maxMAC-e-PDUContents				INTEGER (1..19982),
			ms2-NonSchedTransmGrantHARQAlloc	BIT STRING (SIZE (8))		OPTIONAL
		},
		scheduledTransmissionGrantInfo		NULL
	}	OPTIONAL
}

E-DCH-AddReconf-MAC-d-Flow-r7 ::=	SEQUENCE {
	mac-d-FlowIdentity					E-DCH-MAC-d-FlowIdentity,
	mac-d-FlowPowerOffset				E-DCH-MAC-d-FlowPowerOffset			OPTIONAL,
	mac-d-FlowMaxRetrans				E-DCH-MAC-d-FlowMaxRetrans			OPTIONAL,
	mac-d-FlowRetransTimer				E-DCH-MAC-d-FlowRetransTimer		OPTIONAL,
	mac-d-FlowMultiplexingList			E-DCH-MAC-d-FlowMultiplexingList	OPTIONAL,
	transmissionGrantType				CHOICE {
		non-ScheduledTransGrantInfo			SEQUENCE {
			modeSpecificInfo					CHOICE {
				fdd									SEQUENCE {
					maxMAC-e-PDUContents				INTEGER (1..19982),
					ms2-NonSchedTransmGrantHARQAlloc	BIT STRING (SIZE (8))		OPTIONAL
				},
				tdd									NULL
			}
		},
		scheduledTransmissionGrantInfo		NULL
	}	OPTIONAL
}

E-DCH-AddReconf-MAC-d-FlowList ::=	SEQUENCE (SIZE (1..maxE-DCHMACdFlow)) OF
							E-DCH-AddReconf-MAC-d-Flow

E-DCH-AddReconf-MAC-d-FlowList-r7 ::= SEQUENCE (SIZE (1..maxE-DCHMACdFlow)) OF
										E-DCH-AddReconf-MAC-d-Flow-r7

E-DCH-MAC-d-FlowIdentity ::=		INTEGER (0..maxE-DCHMACdFlow-1)

E-DCH-MAC-d-FlowMaxRetrans ::=		INTEGER (0..15)

E-DCH-MAC-d-FlowMultiplexingList ::= BIT STRING (SIZE (maxE-DCHMACdFlow))

E-DCH-MAC-d-FlowPowerOffset ::=		INTEGER (0..6)

E-DCH-MAC-d-FlowRetransTimer ::=	ENUMERATED {
										ms10, ms15, ms20, ms25, ms30, ms35, ms40, ms45, ms50,
										ms55, ms60, ms65, ms70, ms75, ms80, ms85, ms90, ms95,
										ms100, ms110, ms120, ms140, ms160, ms200, ms240, ms280,
										ms320, ms400, ms480, ms560 }

E-DCH-TTI ::=						ENUMERATED { tti2, tti10 }

ExplicitTFCS-Configuration ::=		CHOICE {
	complete							TFCS-ReconfAdd,
	addition							TFCS-ReconfAdd,
	removal								TFCS-RemovalList,
	replacement							SEQUENCE {
		tfcsRemoval							TFCS-RemovalList,
		tfcsAdd								TFCS-ReconfAdd
	}
}

ExplicitTFCS-Configuration-r12 ::=		CHOICE {
	complete							TFCS-ReconfAdd-r12,
	addition							TFCS-ReconfAdd-r12,
	removal								TFCS-RemovalList,
	replacement							SEQUENCE {
		tfcsRemoval							TFCS-RemovalList,
		tfcsAdd								TFCS-ReconfAdd-r12
	}
}

GainFactor ::=						INTEGER (0..15)

GainFactorInformation ::=			CHOICE {
	signalledGainFactors				SignalledGainFactors,
	computedGainFactors					ReferenceTFC-ID
}

GainFactorInformation-10msMode ::=	CHOICE {
	signalledGainFactors				SEQUENCE {
		gainFactorBetaC						GainFactor,
		gainFactorBetaD						GainFactor,
		referenceTFC-ID						ReferenceTFC-ID					OPTIONAL
	},
	computedGainFactors					ReferenceTFC-ID
}


HSDSCH-Info ::=						SEQUENCE {
	harqInfo							HARQ-Info 				OPTIONAL,
	addOrReconfMAC-dFlow				AddOrReconfMAC-dFlow	OPTIONAL
}

HSDSCH-Info-r7 ::=					SEQUENCE {
	harqInfo							HARQ-Info-r7			OPTIONAL,
	dl-MAC-HeaderType					CHOICE {
		mac-hs								AddOrReconfMAC-dFlow,
		mac-ehs								AddOrReconfMAC-ehs-ReordQ
	}		OPTIONAL
}

HSDSCH-Info-r9 ::=					SEQUENCE {
	harqInfo							HARQ-Info-r7			OPTIONAL,
	dl-MAC-HeaderType					CHOICE {
		mac-hs								AddOrReconfMAC-dFlow,
		mac-ehs								AddOrReconfMAC-ehs-ReordQ-r9
	}		OPTIONAL
}

HSDSCH-Info-r11 ::=					SEQUENCE {
	harqInfo							HARQ-Info-r11			OPTIONAL,
	dl-MAC-HeaderType					CHOICE {
		mac-hs								AddOrReconfMAC-dFlow,
		mac-ehs								AddOrReconfMAC-ehs-ReordQ-r11
	}		OPTIONAL
}

HSDSCH-Info-r13 ::=				SEQUENCE {
	harqInfo							HARQ-Info-r13			OPTIONAL,
	dl-MAC-HeaderType					CHOICE {
		mac-hs								AddOrReconfMAC-dFlow,
		mac-ehs								AddOrReconfMAC-ehs-ReordQ-r11
	}		OPTIONAL
}

HSDSCH-Info-TDD128-v9c0ext ::=			SEQUENCE {
	mac-ehs								AddOrReconfMAC-ehs-ReordQ-TDD128-v9c0ext		OPTIONAL
}

HARQ-Info ::=						SEQUENCE {
	numberOfProcesses					INTEGER (1..8),
	memoryPartitioning					CHOICE {
		implicit							NULL,
		explicit							SEQUENCE (SIZE (1..maxHProcesses)) OF
												HARQMemorySize
	}
}

HARQ-Info-r7 ::=					SEQUENCE {
	numberOfProcesses					ENUMERATED { n1, n2, n3, n4, n5, n6, n7, n8,
											n12, n14, n16 },
	memoryPartitioning					CHOICE {
		implicit							NULL,
		explicit							SEQUENCE {
			memorySize							SEQUENCE (SIZE (1..maxHProcesses)) OF
													HARQMemorySize,
			additionalMemorySizesForMIMO		SEQUENCE (SIZE (1..maxHProcesses)) OF
													HARQMemorySize		OPTIONAL
		}
	}
}

HARQ-Info-r11 ::=					SEQUENCE {
	numberOfProcesses					ENUMERATED { n1, n2, n3, n4, n5, n6, n7, n8,
											n12, n14, n16, n24, n28, n32 },
	memoryPartitioning					CHOICE {
		implicit							NULL,
		explicit							SEQUENCE {
			memorySize							SEQUENCE (SIZE (1..maxHProcesses)) OF
													HARQMemorySize,
			additionalMemorySizesForMIMO		SEQUENCE (SIZE (1..maxHProcesses)) OF
													HARQMemorySize		OPTIONAL,
			additionalMemorySizesThirdMIMOStream		SEQUENCE (SIZE (1..maxHProcesses)) OF
													HARQMemorySize		OPTIONAL,
			additionalMemorySizesFourthMIMOStream		SEQUENCE (SIZE (1..maxHProcesses)) OF
													HARQMemorySize		OPTIONAL
		}
	}
}

HARQ-Info-r13 ::=					SEQUENCE {
	numberOfProcesses					ENUMERATED { n1, n2, n3, n4, n5, n6, n7, n8,
											n12, n14, n16, n24, n28, n32 },
	memoryPartitioning					CHOICE {
		implicit							NULL,
		explicit							SEQUENCE {
			memorySize							SEQUENCE (SIZE (1..maxHProcesses)) OF
													HARQMemorySize,
			additionalMemorySizesForMIMO		SEQUENCE (SIZE (1..maxHProcesses)) OF
													HARQMemorySize		OPTIONAL,
			additionalMemorySizesThirdMIMOStream		SEQUENCE (SIZE (1..maxHProcesses)) OF
													HARQMemorySize		OPTIONAL,
			additionalMemorySizesFourthMIMOStream		SEQUENCE (SIZE (1..maxHProcesses)) OF
													HARQMemorySize		OPTIONAL
		}
	},
	blindHARQRetransmissionsForHSDPA			ENUMERATED { true }				OPTIONAL
}

HARQMemorySize ::= 					ENUMERATED {
										hms800, hms1600, hms2400, hms3200, hms4000,
										hms4800, hms5600, hms6400, hms7200, hms8000,
										hms8800, hms9600, hms10400, hms11200, hms12000,
										hms12800, hms13600, hms14400, hms15200, hms16000,
										hms17600, hms19200, hms20800, hms22400, hms24000,
										hms25600, hms27200, hms28800, hms30400, hms32000,
										hms36000, hms40000, hms44000, hms48000, hms52000,
										hms56000, hms60000, hms64000, hms68000, hms72000,
										hms76000, hms80000, hms88000, hms96000, hms104000,
										hms112000, hms120000, hms128000, hms136000, hms144000,
										hms152000, hms160000, hms176000, hms192000, hms208000,
										hms224000, hms240000, hms256000, hms272000, hms288000,
										hms304000 }

IndividualDL-CCTrCH-Info ::=		SEQUENCE {
	dl-TFCS-Identity					TFCS-Identity,
	tfcs-SignallingMode					CHOICE {
		explicit-config						TFCS,
		sameAsUL							TFCS-Identity
	}
}

IndividualDL-CCTrCH-InfoList ::=	SEQUENCE (SIZE (1..maxCCTrCH)) OF
										IndividualDL-CCTrCH-Info

IndividualUL-CCTrCH-Info ::=		SEQUENCE {
	ul-TFCS-Identity					TFCS-Identity,
	ul-TFCS								TFCS ,
	tfc-Subset							TFC-Subset
}

IndividualUL-CCTrCH-InfoList ::=	SEQUENCE (SIZE (1..maxCCTrCH)) OF
										IndividualUL-CCTrCH-Info

LogicalChannelByRB ::=				SEQUENCE {
	rb-Identity							RB-Identity,
	logChOfRb							INTEGER (0..1)						OPTIONAL
}

LogicalChannelList ::=				CHOICE {
		allSizes							NULL,
		configured							NULL,
		explicitList						SEQUENCE (SIZE (1..15)) OF
												LogicalChannelByRB
}

MAC-d-FlowIdentityDCHandHSDSCH ::=	SEQUENCE {
	dch-transport-ch-id				TransportChannelIdentity,
	hsdsch-mac-d-flow-id			MAC-d-FlowIdentity
}

MAC-d-FlowIdentity ::=				INTEGER (0..7)

MAC-d-PDU-SizeInfo-List ::=			SEQUENCE (SIZE(1.. maxMAC-d-PDUsizes)) OF
										MAC-d-PDUsizeInfo

--MAC-d-Pdu sizes need to be defined
MAC-d-PDUsizeInfo ::=				SEQUENCE{
	mac-d-PDU-Size						INTEGER (1..5000),
	mac-d-PDU-Index						INTEGER(0..7)
}

MAC-hs-AddReconfQueue-List ::=		SEQUENCE (SIZE(1..maxQueueIDs)) OF
										MAC-hs-AddReconfQueue

MAC-hs-AddReconfQueue ::=			SEQUENCE {
	mac-hsQueueId						INTEGER(0..7),
	mac-dFlowId							MAC-d-FlowIdentity,
	reorderingReleaseTimer				T1-ReleaseTimer,
	mac-hsWindowSize					MAC-hs-WindowSize,
	mac-d-PDU-SizeInfo-List				MAC-d-PDU-SizeInfo-List				OPTIONAL
}

MAC-hs-DelQueue-List ::=			SEQUENCE (SIZE(1..maxQueueIDs)) OF
										MAC-hs-DelQueue

MAC-hs-DelQueue ::=					SEQUENCE {
	mac-hsQueueId						INTEGER(0..7)
}

MAC-ehs-AddReconfReordQ-List ::=	SEQUENCE (SIZE(1..maxQueueIDs)) OF
										MAC-ehs-AddReconfReordQ

MAC-ehs-AddReconfReordQ-List-r9 ::=	SEQUENCE (SIZE(1..maxQueueIDs)) OF
										MAC-ehs-AddReconfReordQ-r9

MAC-ehs-AddReconfReordQ-List-TDD128-v9c0ext ::=	SEQUENCE (SIZE(1..maxQueueIDs)) OF
										MAC-ehs-AddReconfReordQ-TDD128-v9c0ext

MAC-ehs-AddReconfReordQ-List-r11 ::=	SEQUENCE (SIZE(1..maxQueueIDs)) OF
										MAC-ehs-AddReconfReordQ-r11

MAC-ehs-AddReconfReordQ ::=			SEQUENCE {
	mac-ehs-QueueId						MAC-ehs-QueueId,
	reorderingReleaseTimer				T1-ReleaseTimer,
	reorderingResetTimer				Treset-ResetTimer						OPTIONAL,
	mac-ehsWindowSize					MAC-hs-WindowSize
}

MAC-ehs-AddReconfReordQ-r9 ::=			SEQUENCE {
	mac-ehs-QueueId						MAC-ehs-QueueId,
	reorderingReleaseTimer				T1-ReleaseTimer,
	reorderingResetTimer				Treset-ResetTimer						OPTIONAL,
	mac-ehsWindowSize					MAC-hs-WindowSize-r9
}

MAC-ehs-AddReconfReordQ-TDD128-v9c0ext ::=			SEQUENCE {
	mac-ehsWindowSize-extension					MAC-ehs-WindowSize-TDD128-v9c0ext		OPTIONAL
}

MAC-ehs-AddReconfReordQ-r11 ::=			SEQUENCE {
	mac-ehs-QueueId						MAC-ehs-QueueId,
	reorderingReleaseTimer				T1-ReleaseTimer,
	reorderingResetTimer				Treset-ResetTimer						OPTIONAL,
	mac-ehsWindowSize					MAC-hs-WindowSize-r11,
	-- For 1.28Mcps TDD only
	mac-ehsWindowSize-extension			MAC-ehs-WindowSize-TDD128-v9c0ext		OPTIONAL
}

MAC-ehs-DelReordQ-List ::=			SEQUENCE (SIZE(1..maxQueueIDs)) OF
										MAC-ehs-DelReordQ

MAC-ehs-DelReordQ ::=				SEQUENCE {
	mac-ehs-QueueId						MAC-ehs-QueueId
}

MAC-ehs-QueueIdDCHandHSDSCH ::=		SEQUENCE {
	dch-transport-ch-id					TransportChannelIdentity,
	hsdsch-mac-ehs-QueueId				MAC-ehs-QueueId
}

MAC-ehs-QueueId ::=					INTEGER (0..7)

MAC-hs-WindowSize ::=				ENUMERATED {
										mws4, mws6, mws8, mws12, mws16, mws24, mws32 }

MAC-hs-WindowSize-r9 ::=			ENUMERATED {
										mws4, mws6, mws8, mws12, mws16, mws24, mws32,
										mw64, mw128 }

MAC-ehs-WindowSize-TDD128-v9c0ext ::=		ENUMERATED {
										mws96, mws160, mws192, mws256 }

MAC-hs-WindowSize-r11 ::=			ENUMERATED {
										mws4, mws6, mws8, mws12, mws16, mws24, mws32,
										mws64, mws128, mws256, spare6, spare5, spare4,
										spare3, spare2, spare1 }

NumberOfTbSizeAndTTIList ::=		SEQUENCE (SIZE (1..maxTF)) OF SEQUENCE {
		numberOfTransportBlocks				NumberOfTransportBlocks,
		transmissionTimeInterval			TransmissionTimeInterval
}

MessType ::=						ENUMERATED {
										transportFormatCombinationControl }

MinimumTEBS-threshold ::=				ENUMERATED {
										pl2, pl4, pl8, pl16, pl32,
										pl64, pl128, pl256, pl512, pl1024,
										pl2k, pl4k, pl8k, pl16k, pl32k,
										pl64k, pl128k, pl256k, pl512k, pl1024k,
										spare12, spare11, spare10, spare9, spare8,
										spare7, spare6, spare5, spare4, spare3,
										spare2, spare1 }

Non-allowedTFC-List ::=				SEQUENCE (SIZE (1..maxTFC)) OF
										TFC-Value

NumberOfTransportBlocks ::=			CHOICE {
	zero								NULL,
	one									NULL,
	small								INTEGER (2..17),
	large								INTEGER (18..512)
}

OctetModeRLC-SizeInfoType1 ::=		CHOICE {
	-- Actual size = (8 * sizeType1) + 16
	sizeType1							INTEGER (0..31),
	sizeType2							SEQUENCE {
		-- Actual size = (32 * part1) + 272 + (part2 * 8)
		part1								INTEGER (0..23),
		part2								INTEGER (1..3)					OPTIONAL
	},
	sizeType3							SEQUENCE {
		-- Actual size = (64 * part1) + 1040 + (part2 * 8)
		part1								INTEGER (0..61),
		part2								INTEGER (1..7)					OPTIONAL
	}
}

OctetModeRLC-SizeInfoType2 ::=		CHOICE {
	-- Actual size = (sizeType1 * 8) + 48
	sizeType1							INTEGER (0..31),
	-- Actual size = (sizeType2 * 16) + 312
	sizeType2							INTEGER (0..63),
	-- Actual size = (sizeType3 *64) + 1384
	sizeType3							INTEGER (0..56)
}

PowerOffsetInfoShort ::=			SEQUENCE {
	referenceTFC						TFC-Value,
	modeSpecificInfo					CHOICE {
		fdd									SEQUENCE {
			gainFactorBetaC						GainFactor
		},
		tdd									NULL
	},
	gainFactorBetaD						GainFactor
}

PowerOffsetInformation ::=			SEQUENCE {
	gainFactorInformation				GainFactorInformation,
	-- PowerOffsetPp-m is always absent in TDD
	powerOffsetPp-m						PowerOffsetPp-m						OPTIONAL
}

PowerOffsetInformation-10msMode ::=			SEQUENCE {
	gainFactorInformation				GainFactorInformation-10msMode
}

PowerOffsetPp-m ::=					INTEGER (-5..10)

PreDefTransChConfiguration ::=		SEQUENCE {
	ul-CommonTransChInfo				UL-CommonTransChInfo,
	ul-AddReconfTrChInfoList			UL-AddReconfTransChInfoList,
	dl-CommonTransChInfo				DL-CommonTransChInfo,
	dl-TrChInfoList						DL-AddReconfTransChInfoList
}

QualityTarget ::=					SEQUENCE {
	bler-QualityValue					BLER-QualityValue
}

RateMatchingAttribute ::=			INTEGER (1..hiRM)


ReferenceTFC-ID ::=					INTEGER (0..3)

RestrictedTrChInfo ::=				SEQUENCE {
	ul-TransportChannelType				UL-TrCH-Type,
	restrictedTrChIdentity				TransportChannelIdentity,
	allowedTFI-List						AllowedTFI-List						OPTIONAL
}

RestrictedTrChInfoList ::=			SEQUENCE (SIZE (1..maxTrCH)) OF
										RestrictedTrChInfo

SemistaticTF-Information ::=		SEQUENCE {
	-- TABULAR: Transmission time interval has been included in the IE CommonTransChTFS.
	channelCodingType					ChannelCodingType,
	rateMatchingAttribute				RateMatchingAttribute,
	crc-Size							CRC-Size
}

SignalledGainFactors ::=			SEQUENCE {
	modeSpecificInfo					CHOICE {
		fdd									SEQUENCE {
			gainFactorBetaC						GainFactor
		},
		tdd									NULL
	},
	gainFactorBetaD						GainFactor,
	referenceTFC-ID						ReferenceTFC-ID						OPTIONAL
}

SplitTFCI-Signalling ::=			SEQUENCE {
	splitType							SplitType						OPTIONAL,
	tfci-Field2-Length					INTEGER (1..10)					OPTIONAL,
	tfci-Field1-Information				ExplicitTFCS-Configuration		OPTIONAL,
	tfci-Field2-Information				TFCI-Field2-Information			OPTIONAL
}

SplitType ::=						ENUMERATED {
										hardSplit, logicalSplit }

T1-ReleaseTimer ::=					ENUMERATED {
										rt10, rt20, rt30, rt40, rt50,
										rt60, rt70, rt80, rt90, rt100,
										rt120, rt140, rt160, rt200, rt300,
										rt400 }

TFC-Subset ::=						CHOICE {
	minimumAllowedTFC-Number			TFC-Value,
	allowedTFC-List						AllowedTFC-List,
	non-allowedTFC-List					Non-allowedTFC-List,
	restrictedTrChInfoList				RestrictedTrChInfoList,
	fullTFCS							NULL
}

TFC-SubsetList ::=					SEQUENCE (SIZE (1.. maxTFCsub)) OF SEQUENCE {
	modeSpecificInfo					CHOICE {
		fdd									NULL,
		tdd									SEQUENCE {
			tfcs-ID								TFCS-Identity				OPTIONAL
		}
	},
	tfc-Subset							TFC-Subset
}

TFC-Value ::=						INTEGER (0..1023)

TFCI-Field2-Information ::=			CHOICE {
	tfci-Range							TFCI-RangeList,
	explicit-config						ExplicitTFCS-Configuration
}

TFCI-Range ::=						SEQUENCE {
	maxTFCIField2Value					INTEGER (1..1023),
	tfcs-InfoForDSCH					TFCS-InfoForDSCH
}

TFCI-RangeList ::=					SEQUENCE (SIZE (1..maxPDSCH-TFCIgroups)) OF
										TFCI-Range

TFCS ::=							CHOICE {
	normalTFCI-Signalling				ExplicitTFCS-Configuration,
	-- dummy is not used in this version of specification, it should
	-- not be sent and if received the UE behaviour is not specified.
	dummy								SplitTFCI-Signalling
}

TFCS-r12 ::=							CHOICE {
	normalTFCI-Signalling				ExplicitTFCS-Configuration-r12
}

TFCS-Identity ::=					SEQUENCE {
	tfcs-ID								TFCS-IdentityPlain					DEFAULT 1,
	sharedChannelIndicator				BOOLEAN
}

TFCS-IdentityPlain ::=				INTEGER (1..8)

TFCS-InfoForDSCH ::=				CHOICE {
	ctfc2bit							INTEGER (0..3),
	ctfc4bit							INTEGER (0..15),
	ctfc6bit							INTEGER (0..63),
	ctfc8bit							INTEGER (0..255),
	ctfc12bit							INTEGER (0..4095),
	ctfc16bit							INTEGER (0..65535),
	ctfc24bit							INTEGER (0..16777215)
}

TFCS-ReconfAdd ::=					SEQUENCE{
	ctfcSize							CHOICE{
		ctfc2Bit							SEQUENCE (SIZE (1..maxTFC)) OF SEQUENCE {
			ctfc2								INTEGER (0..3),
			powerOffsetInformation				PowerOffsetInformation			OPTIONAL
		},
		ctfc4Bit							SEQUENCE (SIZE (1..maxTFC)) OF SEQUENCE {
			ctfc4 								INTEGER (0..15),
			powerOffsetInformation				PowerOffsetInformation			OPTIONAL
		},
		ctfc6Bit							SEQUENCE (SIZE (1..maxTFC)) OF SEQUENCE {
			ctfc6								INTEGER (0..63),
			powerOffsetInformation				PowerOffsetInformation			OPTIONAL
		},
		ctfc8Bit							SEQUENCE (SIZE (1..maxTFC)) OF SEQUENCE {
			ctfc8								INTEGER (0..255),
			powerOffsetInformation				PowerOffsetInformation			OPTIONAL
		},
		ctfc12Bit							SEQUENCE (SIZE(1..maxTFC)) OF SEQUENCE {
			ctfc12								INTEGER (0..4095),
 			powerOffsetInformation				PowerOffsetInformation			OPTIONAL
		},
		ctfc16Bit							SEQUENCE (SIZE (1..maxTFC)) OF SEQUENCE {
			ctfc16								INTEGER(0..65535),
			powerOffsetInformation				PowerOffsetInformation			OPTIONAL
		},
		ctfc24Bit							SEQUENCE (SIZE (1..maxTFC)) OF SEQUENCE {
			ctfc24								INTEGER(0..16777215),
			powerOffsetInformation				PowerOffsetInformation			OPTIONAL
		}
	}
}

TFCS-ReconfAdd-r12 ::=					SEQUENCE{
	ctfcSize							CHOICE{
		ctfc2Bit							SEQUENCE (SIZE (1..maxTFC)) OF SEQUENCE {
			ctfc2								INTEGER (0..3),
			powerOffsetInformation				PowerOffsetInformation			OPTIONAL,
			powerOffsetInformation-10msMode		PowerOffsetInformation-10msMode	OPTIONAL
		},
		ctfc4Bit							SEQUENCE (SIZE (1..maxTFC)) OF SEQUENCE {
			ctfc4 								INTEGER (0..15),
			powerOffsetInformation				PowerOffsetInformation			OPTIONAL,
			powerOffsetInformation-10msMode		PowerOffsetInformation-10msMode	OPTIONAL
		},
		ctfc6Bit							SEQUENCE (SIZE (1..maxTFC)) OF SEQUENCE {
			ctfc6								INTEGER (0..63),
			powerOffsetInformation				PowerOffsetInformation			OPTIONAL,
			powerOffsetInformation-10msMode		PowerOffsetInformation-10msMode	OPTIONAL
		},
		ctfc8Bit							SEQUENCE (SIZE (1..maxTFC)) OF SEQUENCE {
			ctfc8								INTEGER (0..255),
			powerOffsetInformation				PowerOffsetInformation			OPTIONAL,
			powerOffsetInformation-10msMode		PowerOffsetInformation-10msMode	OPTIONAL
		},
		ctfc12Bit							SEQUENCE (SIZE(1..maxTFC)) OF SEQUENCE {
			ctfc12								INTEGER (0..4095),
 			powerOffsetInformation				PowerOffsetInformation			OPTIONAL,
			powerOffsetInformation-10msMode		PowerOffsetInformation-10msMode	OPTIONAL
		},
		ctfc16Bit							SEQUENCE (SIZE (1..maxTFC)) OF SEQUENCE {
			ctfc16								INTEGER(0..65535),
			powerOffsetInformation				PowerOffsetInformation			OPTIONAL,
			powerOffsetInformation-10msMode		PowerOffsetInformation-10msMode	OPTIONAL
		},
		ctfc24Bit							SEQUENCE (SIZE (1..maxTFC)) OF SEQUENCE {
			ctfc24								INTEGER(0..16777215),
			powerOffsetInformation				PowerOffsetInformation			OPTIONAL,
			powerOffsetInformation-10msMode		PowerOffsetInformation-10msMode	OPTIONAL
		}
	}
}

TFCS-Removal ::=					SEQUENCE {
	tfci								INTEGER (0..1023)
}

TFCS-RemovalList ::=				SEQUENCE (SIZE (1..maxTFC)) OF
										TFCS-Removal

TimeDurationBeforeRetry ::=			INTEGER (1..256)

TM-SignallingInfo ::=				SEQUENCE {
	messType							MessType,
	tm-SignallingMode					CHOICE {
		mode1								NULL,
		mode2								SEQUENCE {
			-- in ul-controlledTrChList, TrCH-Type is always DCH
			ul-controlledTrChList				UL-ControlledTrChList
		}
	}
}

TransmissionTimeInterval ::=		ENUMERATED {
										tti10, tti20, tti40, tti80 }

TransmissionTimeValidity ::=		INTEGER (1..256)

TransportChannelConcatInfo ::=		SEQUENCE (SIZE (1..maxTrCHConcat)) OF
										TransportChannelIdentity

TransportChannelIdentity ::=		INTEGER (1..32)

TransportChannelIdentityDCHandDSCH ::=	SEQUENCE {
	dch-transport-ch-id				TransportChannelIdentity,
	dsch-transport-ch-id			TransportChannelIdentity
}


TransportFormatSet ::=				CHOICE {
	dedicatedTransChTFS					DedicatedTransChTFS,
	commonTransChTFS					CommonTransChTFS
}

TransportFormatSet-LCR ::=				CHOICE {
	dedicatedTransChTFS					DedicatedTransChTFS,
	commonTransChTFS-LCR				CommonTransChTFS-LCR
}

Treset-ResetTimer ::=				ENUMERATED {
										rt1, rt2, rt3, rt4 }

-- The maximum allowed size of UL-AddReconfTransChInfoList sequence is 16
UL-AddReconfTransChInfoList ::=		SEQUENCE (SIZE (1..maxTrCHpreconf)) OF
										UL-AddReconfTransChInformation

-- The maximum allowed size of UL-AddReconfTransChInfoList-r6 sequence is 32
UL-AddReconfTransChInfoList-r6 ::=	SEQUENCE (SIZE (1..maxTrCH)) OF
										UL-AddReconfTransChInformation-r6

-- The maximum allowed size of UL-AddReconfTransChInfoList-r7 sequence is 32
UL-AddReconfTransChInfoList-r7 ::=	SEQUENCE (SIZE (1..maxTrCH)) OF
										UL-AddReconfTransChInformation-r7

-- The maximum allowed size of UL-AddReconfTransChInfoList-r8 sequence is 32
UL-AddReconfTransChInfoList-r8 ::=	SEQUENCE (SIZE (1..maxTrCH)) OF
										UL-AddReconfTransChInformation-r8

-- The maximum allowed size of UL-AddReconfTransChInfoList-r14 sequence is 32
UL-AddReconfTransChInfoList-r14 ::=	SEQUENCE (SIZE (1..maxTrCH)) OF
										UL-AddReconfTransChInformation-r14

UL-AddReconfTransChInformation ::= SEQUENCE {
	ul-TransportChannelType				UL-TrCH-Type,
	transportChannelIdentity			TransportChannelIdentity,
	transportFormatSet					TransportFormatSet
}

UL-AddReconfTransChInformation-r6 ::= CHOICE {
	dch-usch							SEQUENCE {
		ul-TransportChannelType				UL-TrCH-Type,
		transportChannelIdentity			TransportChannelIdentity,
		transportFormatSet					TransportFormatSet
	},
	e-dch								SEQUENCE {
		tti									E-DCH-TTI,
		harq-Info							ENUMERATED { rv0, rvtable },
		addReconf-MAC-d-FlowList			E-DCH-AddReconf-MAC-d-FlowList	OPTIONAL
	}
}

UL-AddReconfTransChInformation-r7 ::= CHOICE {
	dch-usch							SEQUENCE {
		ul-TransportChannelType				UL-TrCH-Type,
		transportChannelIdentity			TransportChannelIdentity,
		transportFormatSet					TransportFormatSet
	},
	e-dch								SEQUENCE {
		modeSpecific						CHOICE {
			fdd									SEQUENCE {
				tti									E-DCH-TTI
			},
			tdd									NULL
		},
		harq-Info							ENUMERATED { rv0, rvtable },
		addReconf-MAC-d-FlowList			E-DCH-AddReconf-MAC-d-FlowList-r7	OPTIONAL
	}
}

UL-AddReconfTransChInformation-r8 ::= CHOICE {
	dch-usch							SEQUENCE {
		ul-TransportChannelType				UL-TrCH-Type,
		transportChannelIdentity			TransportChannelIdentity,
		transportFormatSet					TransportFormatSet
	},
	e-dch								SEQUENCE {
		ul-MAC-HeaderType					ENUMERATED { mac-iis }				OPTIONAL,
		modeSpecific						CHOICE {
			fdd									SEQUENCE {
				tti									E-DCH-TTI
			},
			tdd									NULL
		},
		harq-Info							ENUMERATED { rv0, rvtable },
		addReconf-MAC-d-FlowList			E-DCH-AddReconf-MAC-d-FlowList-r7	OPTIONAL
	}
}

UL-AddReconfTransChInformation-r14 ::= CHOICE {
	dch-usch							SEQUENCE {
		ul-TransportChannelType				UL-TrCH-Type,
		transportChannelIdentity			TransportChannelIdentity,
		transportFormatSet					TransportFormatSet
	},
	e-dch								SEQUENCE {
		ul-MAC-HeaderType					ENUMERATED { mac-iis }				OPTIONAL,
		modeSpecific						CHOICE {
			fdd									SEQUENCE {
				tti									E-DCH-TTI,
				secondaryTTI						E-DCH-TTI					OPTIONAL
			},
			tdd									NULL
		},
		harq-Info							ENUMERATED { rv0, rvtable },
		addReconf-MAC-d-FlowList			E-DCH-AddReconf-MAC-d-FlowList-r7	OPTIONAL
	}
}

UL-CommonTransChInfo ::=			SEQUENCE {
	-- TABULAR: tfc-subset is applicable to FDD only, TDD specifies tfc-subset in individual
	-- CCTrCH Info.
	tfc-Subset							TFC-Subset							OPTIONAL,
	prach-TFCS							TFCS								OPTIONAL,
	modeSpecificInfo					CHOICE {
		fdd									SEQUENCE {
			ul-TFCS							TFCS
		},
		tdd									SEQUENCE {

			individualUL-CCTrCH-InfoList		IndividualUL-CCTrCH-InfoList
																			OPTIONAL
		}
	}																		OPTIONAL
}

UL-CommonTransChInfo-r4 ::=			SEQUENCE {
	-- TABULAR: tfc-subset is applicable to FDD only, TDD specifies tfc-subset in individual
	-- CCTrCH Info.
	tfc-Subset							TFC-Subset							OPTIONAL,
	prach-TFCS							TFCS								OPTIONAL,
	modeSpecificInfo					CHOICE {
		fdd									SEQUENCE {
			ul-TFCS								TFCS
		},
		tdd									SEQUENCE {
			individualUL-CCTrCH-InfoList		IndividualUL-CCTrCH-InfoList		OPTIONAL
		}
	}																		OPTIONAL,
	tfc-SubsetList						TFC-SubsetList						OPTIONAL
}

UL-CommonTransChInfo-r12 ::=			SEQUENCE {
	-- TABULAR: tfc-subset is applicable to FDD only, TDD specifies tfc-subset in individual
	-- CCTrCH Info.
	tfc-Subset							TFC-Subset							OPTIONAL,
	prach-TFCS							TFCS								OPTIONAL,
	modeSpecificInfo					CHOICE {
		fdd									SEQUENCE {
			ul-TFCS								TFCS-r12
		},
		tdd									SEQUENCE {
			individualUL-CCTrCH-InfoList		IndividualUL-CCTrCH-InfoList		OPTIONAL
		}
	}																		OPTIONAL,
	tfc-SubsetList						TFC-SubsetList						OPTIONAL
}

-- In UL-ControlledTrChList, TrCH-Type is always DCH
UL-ControlledTrChList ::=			SEQUENCE (SIZE (1..maxTrCH)) OF
										TransportChannelIdentity

UL-DeletedTransChInfoList ::=		SEQUENCE (SIZE (1..maxTrCH)) OF
										UL-TransportChannelIdentity

UL-DeletedTransChInfoList-r6 ::=	SEQUENCE (SIZE (1..maxTrCH)) OF
										UL-TransportChannelIdentity-r6

UL-TransportChannelIdentity ::=		SEQUENCE {
	ul-TransportChannelType				UL-TrCH-Type,
	ul-TransportChannelIdentity			TransportChannelIdentity
}

UL-TransportChannelIdentity-r6 ::=	CHOICE {
	dch-usch							SEQUENCE {
		ul-TransportChannelType				UL-TrCH-Type,
		ul-TransportChannelIdentity			TransportChannelIdentity
	},
	e-dch								E-DCH-MAC-d-FlowIdentity
}

UL-TrCH-Type ::=					ENUMERATED {dch, usch}

USCH-TransportChannelsInfo ::=		SEQUENCE (SIZE (1..maxTrCH)) OF
										SEQUENCE {
	usch-TransportChannelIdentity			TransportChannelIdentity,
	usch-TFS								TransportFormatSet
}

-- ***************************************************
--
--     PHYSICAL CHANNEL INFORMATION ELEMENTS (10.3.6)
--
-- ***************************************************

ACK-NACK-repetitionFactor ::=		INTEGER(1..4)

ActivationDelay::=					ENUMERATED {
										radio-frames-0,
										radio-frames-1,
										radio-frames-2,
										radio-frames-3,
										radio-frames-4,
										radio-frames-5,
										spare2,
										spare1 }

AC-To-ASC-Mapping ::=				INTEGER (0..7)

AC-To-ASC-MappingTable ::=			SEQUENCE (SIZE (maxASCmap)) OF
										AC-To-ASC-Mapping

AccessServiceClass-FDD ::=			SEQUENCE {
	availableSignatureStartIndex		INTEGER (0..15),
	availableSignatureEndIndex			INTEGER (0..15),

	assignedSubChannelNumber			BIT STRING {
											b3(0),
											b2(1),
											b1(2),
											b0(3)
											}	 (SIZE(4))
}

AccessServiceClass-TDD ::=			SEQUENCE {
	channelisationCodeIndices			BIT STRING	{
											chCodeIndex7(0),
											chCodeIndex6(1),
											chCodeIndex5(2),
											chCodeIndex4(3),
											chCodeIndex3(4),
											chCodeIndex2(5),
											chCodeIndex1(6),
											chCodeIndex0(7)
											} (SIZE(8))				OPTIONAL,
	subchannelSize						CHOICE {
		size1								NULL,
		size2								SEQUENCE {
			-- subch0 means bitstring '01' in the tabular, subch1 means bitsring '10'
			subchannels							ENUMERATED	{ subch0, subch1 }	OPTIONAL
		},
		size4								SEQUENCE {
			subchannels							BIT STRING	{
													subCh3(0),
													subCh2(1),
													subCh1(2),
													subCh0(3)
													} (SIZE(4))		OPTIONAL
		},
		size8								SEQUENCE {
			subchannels							BIT STRING	{
													subCh7(0),
													subCh6(1),
													subCh5(2),
													subCh4(3),
													subCh3(4),
													subCh2(5),
													subCh1(6),
													subCh0(7)
													} (SIZE(8))		OPTIONAL
		}
	}
}

AccessServiceClass-TDD-r7 ::=			SEQUENCE {
	channelisationCodeIndices			BIT STRING	{
											chCodeIndex15(0),
											chCodeIndex14(1),
											chCodeIndex13(2),
											chCodeIndex12(3),
											chCodeIndex11(4),
											chCodeIndex10(5),
											chCodeIndex9(6),
											chCodeIndex8(7),
											chCodeIndex7(8),
											chCodeIndex6(9),
											chCodeIndex5(10),
											chCodeIndex4(11),
											chCodeIndex3(12),
											chCodeIndex2(13),
											chCodeIndex1(14),
											chCodeIndex0(15)
											} (SIZE(16))				OPTIONAL,
	subchannelSize						CHOICE {
		size1								NULL,
		size2								SEQUENCE {
			-- subch0 means bitstring '01' in the tabular, subch1 means bitsring '10'
			subchannels							ENUMERATED	{ subch0, subch1 }	OPTIONAL
		},
		size4								SEQUENCE {
			subchannels							BIT STRING	{
													subCh3(0),
													subCh2(1),
													subCh1(2),
													subCh0(3)
													} (SIZE(4))		OPTIONAL
		},
		size8								SEQUENCE {
			subchannels							BIT STRING	{
													subCh7(0),
													subCh6(1),
													subCh5(2),
													subCh4(3),
													subCh3(4),
													subCh2(5),
													subCh1(6),
													subCh0(7)
													} (SIZE(8))		OPTIONAL
		},
		size16								SEQUENCE {
			subchannels							BIT STRING	{
													subCh15(0),
													subCh14(1),
													subCh13(2),
													subCh12(3),
													subCh11(4),
													subCh10(5),
													subCh9(6),
													subCh8(7),
													subCh7(8),
													subCh6(9),
													subCh5(10),
													subCh4(11),
													subCh3(12),
													subCh2(13),
													subCh1(14),
													subCh0(15)
													} (SIZE(16))		OPTIONAL
		}
	}
}

AccessServiceClass-TDD-LCR-r4 ::=	SEQUENCE {
	availableSYNC-UlCodesIndics		    BIT STRING {
											sulCodeIndex7(0),
											sulCodeIndex6(1),
											sulCodeIndex5(2),
											sulCodeIndex4(3),
											sulCodeIndex3(4),
											sulCodeIndex2(5),
											sulCodeIndex1(6),
											sulCodeIndex0(7)
											} (SIZE(8))               OPTIONAL,
	subchannelSize						CHOICE {
		size1								NULL,
		size2								SEQUENCE {
			-- subch0 means bitstring '01' in the tabular, subch1 means bitsring '10'.
			subchannels							ENUMERATED	{ subch0, subch1 }	OPTIONAL
		},
		size4								SEQUENCE {
			subchannels							BIT STRING	{
													subCh3(0),
													subCh2(1),
													subCh1(2),
													subCh0(3)
													} (SIZE(4))			OPTIONAL
		},
		size8								SEQUENCE {
			subchannels							BIT STRING	{
													subCh7(0),
													subCh6(1),
													subCh5(2),
													subCh4(3),
													subCh3(4),
													subCh2(5),
													subCh1(6),
													subCh0(7)
													} (SIZE(8))			OPTIONAL
		}
	}

}

ActivationTimeOffset ::=				INTEGER (0 .. 255)

AdditionalPRACH-TF-and-TFCS-CCCH-IEs ::= SEQUENCE {
	powerOffsetInformation				PowerOffsetInformation,
	dynamicTFInformationCCCH			DynamicTFInformationCCCH
}

AdditionalPRACH-TF-and-TFCS-CCCH ::=	SEQUENCE {
	additionalPRACH-TF-and-TFCS-CCCH-IEs	AdditionalPRACH-TF-and-TFCS-CCCH-IEs	OPTIONAL
}

-- The order is the same as in the PRACH-SystemInformationList
AdditionalPRACH-TF-and-TFCS-CCCH-List ::=	SEQUENCE (SIZE (1..maxPRACH)) OF
										AdditionalPRACH-TF-and-TFCS-CCCH

AdditionalDLSecCellInfoListFDD ::=	SEQUENCE (SIZE (2)) OF
										AdditionalDLSecCellInfoFDD

AdditionalDLSecCellInfoListFDD-r11 ::=	SEQUENCE (SIZE (2)) OF
										AdditionalDLSecCellInfoFDD-r11

AdditionalDLSecCellInfoListFDD2 ::=	SEQUENCE (SIZE (4)) OF
										AdditionalDLSecCellInfoFDD-r11

AdditionalDLSecCellInfoHandoverToUtranListFDD ::=	SEQUENCE (SIZE (2)) OF
										AdditionalDLSecCellInfoFDD-HandoverToUtran

-- AdditionalDLSecCellInfoFDD is introduced to avoid a SEQUENCE of SEQUENCE, a convention in RAN2.
AdditionalDLSecCellInfoFDD ::=	SEQUENCE {
	dl-SecondaryCellInfoFDD					DL-SecondaryCellInfoFDD-r10				OPTIONAL
}

AdditionalDLSecCellInfoFDD-r11 ::=	SEQUENCE {
	dl-SecondaryCellInfoFDD					DL-SecondaryCellInfoFDD-r11				OPTIONAL
}

AdditionalDLSecCellInfoFDD-HandoverToUtran::=	SEQUENCE {
	dl-SecondaryCellInfoFDD					DL-SecondaryCellInfoFDD-HandoverToUtran				OPTIONAL
}

AdditionalSecondaryCellInfoForMixedTTIConfiguration ::=		SEQUENCE {
	eDPCCH-DPCCH-PowerOffset			E-DPCCH-DPCCH-PowerOffset			OPTIONAL,
	happyBit-DelayCondition				HappyBit-DelayCondition				OPTIONAL,
	e-TFC-Boost-Info					E-TFC-Boost-Info-r7					OPTIONAL,
	e-TFCI-TableIndex					E-TFCI-TableIndex					OPTIONAL,
	reference-E-TFCIs					E-DPDCH-Reference-E-TFCIList-r7		OPTIONAL,
	maxChannelisationCodes				E-DPDCH-MaxChannelisationCodes		OPTIONAL,
	schedulingInfoConfiguration			E-DPDCH-SchedulingInfoConfiguration	OPTIONAL
}

AICH-Info ::=						SEQUENCE {
	channelisationCode256				ChannelisationCode256,
	sttd-Indicator						BOOLEAN,
	aich-TransmissionTiming				AICH-TransmissionTiming
}

AICH-Info-Compressed ::=						SEQUENCE {
	channelisationCode256				ChannelisationCode256
}

AICH-PowerOffset ::=				INTEGER (-22..5)

AICH-TransmissionTiming ::=			ENUMERATED {
										e0, e1 }

AllocationPeriodInfo ::=			SEQUENCE {
	allocationActivationTime			INTEGER (0..255),
	allocationDuration					INTEGER (1..256)
}

-- Actual value Alpha = IE value * 0.125
Alpha ::=							INTEGER (0..8)

Antenna3And4 ::= SEQUENCE {
	antenna3And4-S-CPICH		Antenna3And4-S-CPICH	OPTIONAL,
	antenna3And4-D-CPICH		Antenna3And4-D-CPICH	OPTIONAL
}

Antenna3And4-S-CPICH ::= SEQUENCE {
	antenna3-S-CPICH			Antenna3-S-CPICH			OPTIONAL,
	antenna4-S-CPICH			Antenna4-S-CPICH			OPTIONAL,
	s-cpich-PowerOffset-Mimo	S-CPICH-PowerOffset-4x4MIMO	OPTIONAL
}

Antenna3And4-D-CPICH ::= SEQUENCE {
	antenna3-D-CPICH			Antenna3-D-CPICH			OPTIONAL,
	antenna4-D-CPICH			Antenna4-D-CPICH			OPTIONAL,
	d-cpich-PowerOffset-Mimo	D-CPICH-PowerOffset-4x4MIMO	OPTIONAL,
	initialD-CPICHStatus		ENUMERATED { activated }			OPTIONAL
}

Antenna3-D-CPICH ::= SEQUENCE {
	channelisationCode			ChannelisationCode256
}

Antenna4-D-CPICH ::= SEQUENCE {
	channelisationCode			ChannelisationCode256
}

Antenna3-S-CPICH ::= SEQUENCE {
	channelisationCode			ChannelisationCode256
}

Antenna4-S-CPICH ::= SEQUENCE {
	channelisationCode			ChannelisationCode256
}

AP-AICH-ChannelisationCode ::=		INTEGER (0..255)

AP-PreambleScramblingCode ::=		INTEGER (0..79)

AP-Signature ::=					INTEGER (0..15)

AP-Signature-VCAM ::=				SEQUENCE {
	ap-Signature						AP-Signature,
	availableAP-SubchannelList			AvailableAP-SubchannelList OPTIONAL
}

AP-Subchannel ::=					INTEGER (0..11)

ASCSetting-FDD ::=						SEQUENCE {
	-- TABULAR: accessServiceClass-FDD is MD in tabular description
	-- Default value is previous ASC
	-- If this is the first ASC, the default value is all available signature and sub-channels
	accessServiceClass-FDD					AccessServiceClass-FDD	OPTIONAL
}

ASCSetting-TDD ::=						SEQUENCE {
	-- TABULAR: accessServiceClass-TDD is MD in tabular description
	-- Default value is previous ASC
	-- If this is the first ASC, the default value is all available channelisation codes and
	-- all available sub-channels with subchannelSize=size1.
	accessServiceClass-TDD					AccessServiceClass-TDD	OPTIONAL
}

ASCSetting-TDD-r7 ::=						SEQUENCE {
	-- TABULAR: accessServiceClass-TDD is MD in tabular description
	-- Default value is previous ASC
	-- If this is the first ASC, the default value is all available channelisation codes and
	-- all available sub-channels with subchannelSize=size1.
	accessServiceClass-TDD						AccessServiceClass-TDD-r7	OPTIONAL
}

ASCSetting-TDD-LCR-r4 ::=						SEQUENCE {
	-- TABULAR: accessServiceClass-TDD-LCR is MD in tabular description
	-- Default value is previous ASC
	-- If this is the first ASC, the default value is all available SYNC_UL codes and
	-- all available sub-channels with subchannelSize=size1.
	accessServiceClass-TDD-LCR					AccessServiceClass-TDD-LCR-r4  	OPTIONAL
}

AvailableAP-Signature-VCAMList ::=	SEQUENCE (SIZE (1..maxPCPCH-APsig)) OF
										AP-Signature-VCAM

AvailableAP-SignatureList ::=		SEQUENCE (SIZE (1..maxPCPCH-APsig)) OF
										AP-Signature

AvailableAP-SubchannelList ::=		SEQUENCE (SIZE (1..maxPCPCH-APsubCh)) OF
										AP-Subchannel

AvailableMinimumSF-ListVCAM ::=		SEQUENCE (SIZE (1..maxPCPCH-SF)) OF
										AvailableMinimumSF-VCAM

AvailableMinimumSF-VCAM ::=			SEQUENCE {
	minimumSpreadingFactor				MinimumSpreadingFactor,
	nf-Max								NF-Max,
	maxAvailablePCPCH-Number			MaxAvailablePCPCH-Number,
	availableAP-Signature-VCAMList		AvailableAP-Signature-VCAMList
}

AvailableSignatures ::=			BIT STRING {
									signature15(0),
									signature14(1),
									signature13(2),
									signature12(3),
									signature11(4),
									signature10(5),
									signature9(6),
									signature8(7),
									signature7(8),
									signature6(9),
									signature5(10),
									signature4(11),
									signature3(12),
									signature2(13),
									signature1(14),
									signature0(15)
									}	 (SIZE(16))

AvailableSubChannelNumbers ::=		BIT STRING {
										subCh11(0),
										subCh10(1),
									 	subCh9(2),
									 	subCh8(3),
									 	subCh7(4),
									 	subCh6(5),
									 	subCh5(6),
									 	subCh4(7),
									 	subCh3(8),
									 	subCh2(9),
									 	subCh1(10),
									 	subCh0(11)
										} 	 (SIZE(12))

BEACON-PL-Est ::=					ENUMERATED { true }

BurstType ::=						ENUMERATED {
										type1, type2 }

-- Actual value Bler-Target = IE value * 0.05
Bler-Target ::=						INTEGER (-63..0)

CCTrCH-PowerControlInfo ::=			SEQUENCE {
	tfcs-Identity						TFCS-Identity						OPTIONAL,
	ul-DPCH-PowerControlInfo			UL-DPCH-PowerControlInfo
}

CCTrCH-PowerControlInfo-r4 ::=		SEQUENCE {
	tfcs-Identity						TFCS-Identity						OPTIONAL,
	ul-DPCH-PowerControlInfo			UL-DPCH-PowerControlInfo-r4
}

CCTrCH-PowerControlInfo-r5 ::=		SEQUENCE {
	tfcs-Identity						TFCS-Identity						OPTIONAL,
	ul-DPCH-PowerControlInfo			UL-DPCH-PowerControlInfo-r5
}

CCTrCH-PowerControlInfo-r7 ::=		SEQUENCE {
	tfcs-Identity						TFCS-Identity						OPTIONAL,
	ul-DPCH-PowerControlInfo			UL-DPCH-PowerControlInfo-r7
}

CD-AccessSlotSubchannel ::=			INTEGER (0..11)

CD-AccessSlotSubchannelList ::=		SEQUENCE (SIZE (1..maxPCPCH-CDsubCh)) OF
										CD-AccessSlotSubchannel

CD-CA-ICH-ChannelisationCode ::=	INTEGER (0..255)

CD-PreambleScramblingCode ::=		INTEGER (0..79)

CD-SignatureCode ::=				INTEGER (0..15)

CD-SignatureCodeList ::=			SEQUENCE (SIZE (1..maxPCPCH-CDsig)) OF
										CD-SignatureCode

CellAndChannelIdentity ::=			SEQUENCE {
	-- burstType may be set to either value and should be ignored by the receiver for 1.28 Mcps TDD.
	burstType							BurstType,
	midambleShift						MidambleShiftLong,
	timeslot							TimeslotNumber,
	cellParametersID					CellParametersID
	}

CellParametersID ::=				INTEGER (0..127)

Cfntargetsfnframeoffset ::=				INTEGER(0..255)

ChannelAssignmentActive ::=			CHOICE {
	notActive							NULL,
	isActive							AvailableMinimumSF-ListVCAM
}

ChannelisationCode256 ::=			INTEGER (0..255)

ChannelReqParamsForUCSM ::=			SEQUENCE {
	availableAP-SignatureList			AvailableAP-SignatureList,
	availableAP-SubchannelList			AvailableAP-SubchannelList			OPTIONAL
}

ClosedLoopTimingAdjMode ::=			ENUMERATED {
										slot1, slot2 }

CodeNumberDSCH ::=					INTEGER (0..255)

CodeRange ::=						SEQUENCE {
	pdsch-CodeMapList					PDSCH-CodeMapList
}

CodeResourceInformation-TDD128 ::=	SEQUENCE {
	start-code							HS-ChannelisationCode-LCR,
	stop-code							HS-ChannelisationCode-LCR
}

CodeWordSet ::=						ENUMERATED {
										longCWS,
										mediumCWS,
										shortCWS,
										ssdtOff }

Common-E-DCH-ResourceInfoList ::=	SEQUENCE {
	s-offset							INTEGER (0..9)						OPTIONAL,
	f-dpch-ChannelisationCodeNumber		INTEGER (0..255)					OPTIONAL,
	e-RGCH-Information					E-RGCH-Information-CommonEdch		OPTIONAL,
	e-hich-Info							E-HICH-Information-CommonEdch,
	ul-DPCH-CodeInfoForCommonEDCH		UL-DPCH-CodeInfoForCommonEDCH
}

Common-E-DCH-ResourceInfoListExt ::=	SEQUENCE {
	twoMsHarqConfiguration				TwoMsHarqConfiguration
}

Common-E-RNTI-Info ::=				SEQUENCE (SIZE (1..maxERUCCH)) OF
										SEQUENCE {
	starting-E-RNTI							E-RNTI,
	number-of-group							INTEGER (1..maxERNTIgroup),
	number-of-ENRTI-per-group				INTEGER (1..maxERNTIperGroup)
}

CommonEDCHResourceConfigInfoListExt::=			SEQUENCE {
	scheduledTransmissionConfiguration	ScheduledTransmissionConfiguration	OPTIONAL,
	cOffset								INTEGER (0..29)						OPTIONAL
}

	-- For FDD, the network should not include the IE CommonEDCHSystemInfo.
	-- Instead, the IE commonEDCHSystemInfoFDD should be used.
	-- If included, the UE behavior is unspecified.
CommonEDCHSystemInfo ::=			SEQUENCE {
	ul-InterferenceForCommonEDCH		UL-Interference								OPTIONAL,
	common-E-DCH-MAC-d-FlowList			Common-E-DCH-MAC-d-FlowList,
	modeSpecificInfo					CHOICE {
		dummy								SEQUENCE {},
		tdd									CHOICE {
			tdd768	NULL,
			tdd384	NULL,
			tdd128								SEQUENCE {
				e-RUCCH-Info						E-RUCCH-Info-TDD128,
				e-PUCH-Info							E-PUCH-Info-TDD128,
				e-hich-Information					E-HICH-Information-TDD128,
				e-agch-Information					E-AGCH-Information-TDD128,
				harq-Info							ENUMERATED { rv0, rvtable },
				ccch-transmission-Info				SEQUENCE {
					common-e-rnti-Info					Common-E-RNTI-Info,
					harq-MaximumNumberOfRetransmissions	INTEGER (0..7),
					harq-retransmission-timer			ENUMERATED {
															ms10, ms15, ms20, ms25,
															ms30, ms35, ms40, ms45,
															ms50, ms55, ms60, ms65,
															ms70, ms75, ms80, ms85,
															ms90, ms95, ms100, ms110,
															ms120, ms140, ms160 },
					harq-power-offset					INTEGER (0..6)
				}
			}
		}
	}
}

CommonEDCHSystemInfoFDD ::=			SEQUENCE {
	ul-InterferenceForCommonEDCH		UL-Interference					OPTIONAL,
	common-E-DCH-MAC-d-FlowList			Common-E-DCH-MAC-d-FlowList,
	prach-PreambleForEnhancedUplink		PRACH-PreambleForEnhancedUplink,
	initialServingGrantValue			INTEGER (0..37),
	e-dch-TTI							E-DCH-TTI,
	e-agch-Information					E-AGCH-Information,
	harq-Info							ENUMERATED { rv0, rvtable },
	ul-DPCHpowerControlInfoForCommonEDCH
										UL-DPCHpowerControlInfoForCommonEDCH,
	e-dpcch-Info						E-DPCCH-Info-r7,
	e-dpdch-Info						E-DPDCH-Info-r8,
	-- Actual value dl-FDPCH-TPCcommandErrorRate = IE value * 0.01
	dl-FDPCH-TPCcommandErrorRate		INTEGER (1..10),
	additional-E-DCH-TransmitBackoff	INTEGER (0..15),
	max-CCCH-ResourceAllocation			ENUMERATED {
											tti8, tti12, tti16, tti20, tti24, tti32,
											tti40, tti80 },
	max-PeriodForCollisionResolution	INTEGER (8..24),
	e-dch-TransmitContinuationOffset	ENUMERATED {
											tti0, tti4, tti8, tti16, tti24, tti40,
											tti80,infinity },
	ack-nack-support-on-HS-DPCCH		BOOLEAN,
	measurement-Feedback-Info			Measurement-Feedback-Info-r7		OPTIONAL,
	common-E-DCH-ResourceInfoList		SEQUENCE (SIZE (1..maxEDCHs)) OF
											Common-E-DCH-ResourceInfoList
}

CommonEDCHSystemInfoParamConcurrentTTI ::=			SEQUENCE {
	common-E-DCH-MAC-d-Flow-Info-List-ConcurrentTTI
										Common-E-DCH-MAC-d-Flow-Info-List-ConcurrentTTI	OPTIONAL,
	initialServingGrantValue				INTEGER (0..37)	OPTIONAL,
	e-agch-Information					E-AGCH-Information	OPTIONAL,
	ul-DPCHpowerControlInfoConcurrentTTI
										UL-DPCHpowerControlInfoConcurrentTTI	OPTIONAL,
	e-DPCCH-DPCCH-PowerOffset			E-DPCCH-DPCCH-PowerOffset	OPTIONAL,
	e-dpdch-Info						E-DPDCH-Info-r8,
	additional-E-DCH-TransmitBackoff	INTEGER (0..15)	OPTIONAL,
	max-CCCH-ResourceAllocation			ENUMERATED {
											tti8, tti12, tti16, tti20, tti24, tti32,
											tti40, tti80 }	OPTIONAL,
	max-PeriodForCollisionResolution	INTEGER (8..24)	OPTIONAL,
	e-dch-TransmitContinuationOffset	ENUMERATED {
											tti0, tti4, tti8, tti16, tti24, tti40,
											tti80,infinity }	OPTIONAL,
	measurement-Feedback-Info-ConcurrentTTI			Measurement-Feedback-Info-ConcurrentTTI		OPTIONAL
}

CommonERGCHChannelConfig ::=	SEQUENCE {
	channelisationCode					INTEGER (0..127)		OPTIONAL,
	signatureSequence					INTEGER (0..39)		OPTIONAL
}

CommonERGCHInfoFDD ::=		SEQUENCE {
	configurationInfo					CHOICE {
		continue							NULL,
		newConfiguration					SEQUENCE {
			eRGCHNeighbourCellList			BIT STRING (SIZE (maxCellMeas)),
			commonERGCHChannelConfigList	SEQUENCE (SIZE (1.. maxCellMeas)) OF
												CommonERGCHChannelConfig,
			minimumServingGrantValue			INTEGER (0..37) 			OPTIONAL,
			reportingRange						ReportingRange,
			filterCoefficient					FilterCoefficient					DEFAULT fc0
		}
	}
}

CommonTimeslotInfo ::=				SEQUENCE {
	-- TABULAR: secondInterleavingMode is MD, but since it can be encoded in a single
	-- bit it is not defined as OPTIONAL.
	secondInterleavingMode				SecondInterleavingMode,
	tfci-Coding							TFCI-Coding							OPTIONAL,
	puncturingLimit						PuncturingLimit,
	repetitionPeriodAndLength			RepetitionPeriodAndLength			OPTIONAL
}

CommonTimeslotInfoMBMS ::=			SEQUENCE {
	-- TABULAR: secondInterleavingMode is MD, but since it can be encoded in a single
	-- bit it is not defined as OPTIONAL.
	secondInterleavingMode				SecondInterleavingMode,
	tfci-Coding							TFCI-Coding							OPTIONAL,
	puncturingLimit						PuncturingLimit
}

CommonTimeslotInfoSCCPCH ::=		SEQUENCE {
	-- TABULAR: secondInterleavingMode is MD, but since it can be encoded in a single
	-- bit it is not defined as OPTIONAL.
	secondInterleavingMode				SecondInterleavingMode,
	tfci-Coding							TFCI-Coding							OPTIONAL,
	puncturingLimit						PuncturingLimit,
	repetitionPeriodLengthAndOffset		RepetitionPeriodLengthAndOffset		OPTIONAL
}

ConstantValue ::=					INTEGER (-35..-10)

ConstantValueTdd ::=				INTEGER (-35..10)

ControlChannelDRXCycle-TDD128 ::=	ENUMERATED {
										sub-frames-1, sub-frames-2, sub-frames-4, sub-frames-8,
										sub-frames-16, sub-frames-32, sub-frames-64, spare1 }

ControlChannelDRXInfo-TDD128-r8 ::=	SEQUENCE {
	controlChannelDrxOperation			CHOICE {
		continue							SEQUENCE {
			enablingDelay						EnablingDelay-TDD128			OPTIONAL
		},
		newOperation 					SEQUENCE {
			hS-SCCH-Drx-Info				HS-SCCH-DRX-Info-TDD128,
			e-AGCH-Drx-Info					E-AGCH-DRX-Info-TDD128	OPTIONAL,
			enablingDelay					EnablingDelay-TDD128
		}
	}
}

CPCH-PersistenceLevels ::=			SEQUENCE {
	cpch-SetID							CPCH-SetID,
	dynamicPersistenceLevelTF-List		DynamicPersistenceLevelTF-List
}

CPCH-PersistenceLevelsList ::=		SEQUENCE (SIZE (1..maxCPCHsets)) OF
										CPCH-PersistenceLevels

CPCH-SetInfo ::=					SEQUENCE {
	cpch-SetID							CPCH-SetID,
	transportFormatSet					TransportFormatSet,
	tfcs								TFCS,
	ap-PreambleScramblingCode			AP-PreambleScramblingCode,
	ap-AICH-ChannelisationCode			AP-AICH-ChannelisationCode,
	cd-PreambleScramblingCode			CD-PreambleScramblingCode,
	cd-CA-ICH-ChannelisationCode		CD-CA-ICH-ChannelisationCode,
	cd-AccessSlotSubchannelList			CD-AccessSlotSubchannelList			OPTIONAL,
	cd-SignatureCodeList				CD-SignatureCodeList				OPTIONAL,
	deltaPp-m							DeltaPp-m,
	ul-DPCCH-SlotFormat					UL-DPCCH-SlotFormat,
	n-StartMessage						N-StartMessage,
	n-EOT								N-EOT,
	-- TABULAR: VCAM info has been nested inside ChannelAssignmentActive,
	-- which in turn is mandatory since it's only a binary choice.
	channelAssignmentActive				ChannelAssignmentActive,
	cpch-StatusIndicationMode			CPCH-StatusIndicationMode,
	pcpch-ChannelInfoList				PCPCH-ChannelInfoList
}

CPCH-SetInfoList ::=				SEQUENCE (SIZE (1..maxCPCHsets)) OF
										CPCH-SetInfo

CPCH-StatusIndicationMode ::=		ENUMERATED {
										pa-mode,
										pamsf-mode }

CQI-CycleSwitchTimer ::=			ENUMERATED {
										sub-frames-4,
										sub-frames-8,
										sub-frames-16,
										sub-frames-32,
										sub-frames-64,
										sub-frames-128,
										sub-frames-256,
										sub-frames-512,
										sub-frames-Infinity,
										spare7,
										spare6,
										spare5,
										spare4,
										spare3,
										spare2,
										spare1 }

CQI-DTX-Timer ::=					ENUMERATED {
										sub-frames-0,
										sub-frames-1,
										sub-frames-2,
										sub-frames-4,
										sub-frames-8,
										sub-frames-16,
										sub-frames-32,
										sub-frames-64,
										sub-frames-128,
										sub-frames-256,
										sub-frames-512,
										sub-frames-Infinity,
										spare4,
										spare3,
										spare2,
										spare1 }

CQI-RepetitionFactor ::=			INTEGER(1..4)

CSICH-PowerOffset ::=				INTEGER (-10..5)

D-CPICH-PowerOffset-4x4MIMO ::=			INTEGER (-12..0)

DCH-Enhancements-Info-FDD ::=			SEQUENCE {
	configurationInfo		CHOICE {
		continue					NULL,
		newConfiguration			SEQUENCE {
			ulTransmissionMode			CHOICE {
				tenMSOnly					NULL,
				twentyMSOnly				NULL,
				tenORtwentyMS				SEQUENCE {
					ul-TransModeSwitchingParam		UL-TransModeSwitchingParam
				}
			},
			dlFETMode					CHOICE {
				basic						NULL,
				full						SEQUENCE {
					early-dch-QualityTarget	QualityTarget,
					early-dch-TargetSlot		INTEGER (11..28),
					trChConcatInfo				TransportChannelConcatInfo
				}
			}
		}
	}
}

-- DefaultDPCH-OffsetValueFDD and DefaultDPCH-OffsetValueTDD corresponds to
-- IE "Default DPCH Offset Value" depending on the mode.
-- Actual value DefaultDPCH-OffsetValueFDD = IE value * 512

DefaultDPCH-OffsetValueFDD ::=		INTEGER (0..599)

DefaultDPCH-OffsetValueTDD ::=		INTEGER (0..7)

DeltaPp-m ::=						INTEGER (-10..10)

DeltaCQI ::=						INTEGER (0..8)

DeltaCQI-r11 ::=					INTEGER (0..10)

DeltaNACK ::=						INTEGER (0..8)

DeltaNACK-r11 ::=					INTEGER (0..10)

DeltaACK ::=						INTEGER (0..8)

DeltaACK-r11 ::=					INTEGER (0..10)

-- Actual value DeltaSIR = IE value * 0.1
DeltaSIR ::=						INTEGER (0..30)

DesignatedNonServingHS-DSCHCellInfo ::=	SEQUENCE {
	primaryCPICH-Info					PrimaryCPICH-Info
}

DHS-Sync ::=						INTEGER (-20..10)

DL-CCTrCh ::=						SEQUENCE {
	tfcs-ID								TFCS-IdentityPlain					DEFAULT 1,
	timeInfo							TimeInfo,
	commonTimeslotInfo					CommonTimeslotInfo					OPTIONAL,
	dl-CCTrCH-TimeslotsCodes			DownlinkTimeslotsCodes				OPTIONAL,
	ul-CCTrChTPCList					UL-CCTrChTPCList					OPTIONAL
}

DL-CCTrCh-r4 ::=					SEQUENCE {
	tfcs-ID								TFCS-IdentityPlain					DEFAULT 1,
	timeInfo							TimeInfo,
	commonTimeslotInfo					CommonTimeslotInfo					OPTIONAL,
	tddOption							CHOICE {
		tdd384								SEQUENCE {
			dl-CCTrCH-TimeslotsCodes			DownlinkTimeslotsCodes	OPTIONAL
		},
		tdd128								SEQUENCE {
			dl-CCTrCH-TimeslotsCodes			DownlinkTimeslotsCodes-LCR-r4	OPTIONAL
		}
	},
	ul-CCTrChTPCList					UL-CCTrChTPCList		OPTIONAL
}

DL-CCTrCh-r7 ::=					SEQUENCE {
	tfcs-ID								TFCS-IdentityPlain					DEFAULT 1,
	timeInfo							TimeInfo,
	commonTimeslotInfo					CommonTimeslotInfo					OPTIONAL,
	tddOption							CHOICE {
		tdd384								SEQUENCE {
			dl-CCTrCH-TimeslotsCodes			DownlinkTimeslotsCodes-r7	OPTIONAL
		},
		tdd768								SEQUENCE {
			dl-CCTrCH-TimeslotsCodes			DownlinkTimeslotsCodes-VHCR		OPTIONAL
		},
		tdd128								SEQUENCE {
			dl-CCTrCH-TimeslotsCodes			DownlinkTimeslotsCodes-LCR-r4	OPTIONAL
		}
	},
	ul-CCTrChTPCList					UL-CCTrChTPCList		OPTIONAL
}

DL-CCTrChList ::=					SEQUENCE (SIZE (1..maxCCTrCH)) OF
										DL-CCTrCh

DL-CCTrChList-r7 ::=				SEQUENCE (SIZE (1..maxCCTrCH)) OF
										DL-CCTrCh-r7

DL-CCTrChList-r4 ::=				SEQUENCE (SIZE (1..maxCCTrCH)) OF
										DL-CCTrCh-r4

DL-CCTrChListToRemove ::=			SEQUENCE (SIZE (1..maxCCTrCH)) OF
										TFCS-IdentityPlain

DL-ChannelisationCode ::=			SEQUENCE {
	secondaryScramblingCode				SecondaryScramblingCode				OPTIONAL,
	sf-AndCodeNumber					SF512-AndCodeNumber,
	scramblingCodeChange				ScramblingCodeChange				OPTIONAL
}

DL-ChannelisationCodeList ::=		SEQUENCE (SIZE (1..maxDPCH-DLchan)) OF
										DL-ChannelisationCode

DL-CommonInformation ::=			SEQUENCE {
	dl-DPCH-InfoCommon					DL-DPCH-InfoCommon			OPTIONAL,
	modeSpecificInfo					CHOICE {
		fdd									SEQUENCE {
			defaultDPCH-OffsetValue				DefaultDPCH-OffsetValueFDD	OPTIONAL,
			dpch-CompressedModeInfo				DPCH-CompressedModeInfo		OPTIONAL,
			tx-DiversityMode					TX-DiversityMode			OPTIONAL,
			-- dummy is not used in this version of the specification, it should
			-- not be sent and if received it should be ignored.
			dummy								SSDT-Information			OPTIONAL
		},
		tdd									SEQUENCE {
			defaultDPCH-OffsetValue				DefaultDPCH-OffsetValueTDD	OPTIONAL
		}
	}
}

DL-CommonInformation-r4 ::=			SEQUENCE {
	dl-DPCH-InfoCommon					DL-DPCH-InfoCommon-r4		OPTIONAL,
	modeSpecificInfo					CHOICE {
		fdd									SEQUENCE {
			defaultDPCH-OffsetValue				DefaultDPCH-OffsetValueFDD	OPTIONAL,
			dpch-CompressedModeInfo				DPCH-CompressedModeInfo		OPTIONAL,
			tx-DiversityMode					TX-DiversityMode			OPTIONAL,
			-- dummy is not used in this version of the specification, it should
			-- not be sent and if received it should be ignored.
			dummy								SSDT-Information-r4			OPTIONAL
		},
		tdd									SEQUENCE {
			tddOption							CHOICE {
				tdd384								NULL,
				tdd128								SEQUENCE {
					tstd-Indicator						BOOLEAN
				}
			},
			defaultDPCH-OffsetValue				DefaultDPCH-OffsetValueTDD	OPTIONAL
		}
	}
}


DL-CommonInformation-r5 ::=			SEQUENCE {
	dl-DPCH-InfoCommon					DL-DPCH-InfoCommon-r4			OPTIONAL,
	modeSpecificInfo					CHOICE {
		fdd									SEQUENCE {
			defaultDPCH-OffsetValue				DefaultDPCH-OffsetValueFDD	OPTIONAL,
			dpch-CompressedModeInfo				DPCH-CompressedModeInfo		OPTIONAL,
			tx-DiversityMode					TX-DiversityMode			OPTIONAL,
			-- dummy is not used in this version of the specification, it should
			-- not be sent and if received it should be ignored.
			dummy								SSDT-Information-r4			OPTIONAL
		},
		tdd									SEQUENCE {
			tddOption							CHOICE {
				tdd384								NULL,
				tdd128								SEQUENCE {
					tstd-Indicator						BOOLEAN
				}
			},
			defaultDPCH-OffsetValue				DefaultDPCH-OffsetValueTDD	OPTIONAL
		}
	},
	mac-hsResetIndicator				ENUMERATED { true }			OPTIONAL
}

DL-CommonInformation-r6 ::=			SEQUENCE {
	dl-dpchInfoCommon					CHOICE {
		dl-DPCH-InfoCommon					DL-DPCH-InfoCommon-r6,
		dl-FDPCH-InfoCommon					DL-FDPCH-InfoCommon-r6
	}																		OPTIONAL,
	modeSpecificInfo					CHOICE {
		fdd									SEQUENCE {
			defaultDPCH-OffsetValue				DefaultDPCH-OffsetValueFDD	OPTIONAL,
			dpch-CompressedModeInfo				DPCH-CompressedModeInfo		OPTIONAL,
			tx-DiversityMode					TX-DiversityMode			OPTIONAL
		},
		tdd									SEQUENCE {
			tddOption							CHOICE {
				tdd384								NULL,
				tdd128								SEQUENCE {
					tstd-Indicator						BOOLEAN
				}
			},
			defaultDPCH-OffsetValue				DefaultDPCH-OffsetValueTDD	OPTIONAL
		}
	},
	mac-hsResetIndicator				ENUMERATED { true }			OPTIONAL,
	postVerificationPeriod				ENUMERATED { true }			OPTIONAL
}

DL-CommonInformation-r7 ::=			SEQUENCE {
	dl-dpchInfoCommon					CHOICE {
		dl-DPCH-InfoCommon					DL-DPCH-InfoCommon-r6,
		dl-FDPCH-InfoCommon					DL-FDPCH-InfoCommon-r6
	}																		OPTIONAL,
	modeSpecificInfo					CHOICE {
		fdd									SEQUENCE {
			defaultDPCH-OffsetValue				DefaultDPCH-OffsetValueFDD	OPTIONAL,
			dpch-CompressedModeInfo				DPCH-CompressedModeInfo		OPTIONAL,
			tx-DiversityMode					TX-DiversityMode			OPTIONAL
		},
		tdd									SEQUENCE {
			tddOption							CHOICE {
				tdd384								NULL,
				tdd768								NULL,
				tdd128								SEQUENCE {
					tstd-Indicator						BOOLEAN
				}
			},
			defaultDPCH-OffsetValue				DefaultDPCH-OffsetValueTDD	OPTIONAL
		}
	},
	mac-hsResetIndicator				ENUMERATED { true }			OPTIONAL,
	postVerificationPeriod				ENUMERATED { true }			OPTIONAL
}

DL-CommonInformation-r8 ::=			SEQUENCE {
	dl-dpchInfoCommon					CHOICE {
		dl-DPCH-InfoCommon					DL-DPCH-InfoCommon-r6,
		dl-FDPCH-InfoCommon					DL-FDPCH-InfoCommon-r6
	}																		OPTIONAL,
	modeSpecificInfo					CHOICE {
		fdd									SEQUENCE {
			defaultDPCH-OffsetValue				DefaultDPCH-OffsetValueFDD	OPTIONAL,
			dpch-CompressedModeInfo				DPCH-CompressedModeInfo-r8	OPTIONAL,
			tx-DiversityMode					TX-DiversityMode			OPTIONAL
		},
		tdd									SEQUENCE {
			tddOption							CHOICE {
				tdd384								NULL,
				tdd768								NULL,
				tdd128								SEQUENCE {
					tstd-Indicator						BOOLEAN
				}
			},
			defaultDPCH-OffsetValue				DefaultDPCH-OffsetValueTDD	OPTIONAL
		}
	},
	mac-hsResetIndicator				ENUMERATED { true }			OPTIONAL,
	postVerificationPeriod				ENUMERATED { true }			OPTIONAL
}

DL-CommonInformation-r10 ::=			SEQUENCE {
	dl-dpchInfoCommon					CHOICE {
		dl-DPCH-InfoCommon					DL-DPCH-InfoCommon-r6,
		dl-FDPCH-InfoCommon					DL-FDPCH-InfoCommon-r6
	}																		OPTIONAL,
	modeSpecificInfo					CHOICE {
		fdd									SEQUENCE {
			defaultDPCH-OffsetValue				DefaultDPCH-OffsetValueFDD	OPTIONAL,
			dpch-CompressedModeInfo				DPCH-CompressedModeInfo-r10	OPTIONAL,
			tx-DiversityMode					TX-DiversityMode			OPTIONAL
		},
		tdd									SEQUENCE {
			tddOption							CHOICE {
				tdd384								NULL,
				tdd768								NULL,
				tdd128								SEQUENCE {
					tstd-Indicator						BOOLEAN
				}
			},
			defaultDPCH-OffsetValue				DefaultDPCH-OffsetValueTDD	OPTIONAL
		}
	},
	mac-hsResetIndicator				ENUMERATED { true }			OPTIONAL,
	postVerificationPeriod				ENUMERATED { true }			OPTIONAL
}

DL-CommonInformation-r11 ::=			SEQUENCE {
	dl-dpchInfoCommon					CHOICE {
		dl-DPCH-InfoCommon					DL-DPCH-InfoCommon-r6,
		dl-FDPCH-InfoCommon					DL-FDPCH-InfoCommon-r6
	}																		OPTIONAL,
	modeSpecificInfo					CHOICE {
		fdd									SEQUENCE {
			defaultDPCH-OffsetValue				DefaultDPCH-OffsetValueFDD	OPTIONAL,
			dpch-CompressedModeInfo				DPCH-CompressedModeInfo-r10	OPTIONAL,
			tx-DiversityMode					TX-DiversityMode			OPTIONAL
		},
		tdd									SEQUENCE {
			tddOption							CHOICE {
				tdd384								NULL,
				tdd768								NULL,
				tdd128								SEQUENCE {
					tstd-Indicator						BOOLEAN
				}
			},
			defaultDPCH-OffsetValue				DefaultDPCH-OffsetValueTDD	OPTIONAL
		}
	},
	mac-hsResetIndicator				ENUMERATED { true }			OPTIONAL,
	postVerificationPeriod				ENUMERATED { true }			OPTIONAL,
	mac-hsResetIndicator-assisting				ENUMERATED { true }			OPTIONAL
}

DL-CommonInformation-r12 ::=			SEQUENCE {
	dl-dpchInfoCommon					CHOICE {
		dl-DPCH-InfoCommon					DL-DPCH-InfoCommon-r12,
		dl-FDPCH-InfoCommon					DL-FDPCH-InfoCommon-r6
	}																		OPTIONAL,
	modeSpecificInfo					CHOICE {
		fdd									SEQUENCE {
			defaultDPCH-OffsetValue				DefaultDPCH-OffsetValueFDD	OPTIONAL,
			dpch-CompressedModeInfo				DPCH-CompressedModeInfo-r10	OPTIONAL,
			tx-DiversityMode					TX-DiversityMode			OPTIONAL
		},
		tdd									SEQUENCE {
			tddOption							CHOICE {
				tdd384								NULL,
				tdd768								NULL,
				tdd128								SEQUENCE {
					tstd-Indicator						BOOLEAN
				}
			},
			defaultDPCH-OffsetValue				DefaultDPCH-OffsetValueTDD	OPTIONAL
		}
	},
	mac-hsResetIndicator				ENUMERATED { true }			OPTIONAL,
	postVerificationPeriod				ENUMERATED { true }			OPTIONAL,
	mac-hsResetIndicator-assisting				ENUMERATED { true }			OPTIONAL
}

DL-CommonInformationPost ::=		SEQUENCE {
	dl-DPCH-InfoCommon					DL-DPCH-InfoCommonPost
}

DL-CommonInformationPredef ::=		SEQUENCE {
	dl-DPCH-InfoCommon					DL-DPCH-InfoCommonPredef	OPTIONAL
}

DL-CompressedModeMethod ::=			ENUMERATED {
		-- dummy is not used in this version of the specification, it should
		-- not be sent and if received the UE behaviour is not specified.
										dummy, sf-2,
										higherLayerScheduling }

DL-DPCH-InfoCommon ::=				SEQUENCE {
	cfnHandling							CHOICE {
		maintain							NULL,
		initialise							SEQUENCE {
			-- IE dummy is not used in this version of the specification
			-- The IE should not be sent and if received it should be ignored
			dummy								Cfntargetsfnframeoffset				OPTIONAL
		}
	},
	modeSpecificInfo					CHOICE {
		fdd 								SEQUENCE {
			dl-DPCH-PowerControlInfo			DL-DPCH-PowerControlInfo			OPTIONAL,
			powerOffsetPilot-pdpdch				PowerOffsetPilot-pdpdch,
			dl-rate-matching-restriction		Dl-rate-matching-restriction		OPTIONAL,
			-- TABULAR: The number of pilot bits is nested inside the spreading factor.
			spreadingFactorAndPilot				SF512-AndPilot,
			positionFixedOrFlexible				PositionFixedOrFlexible,
			tfci-Existence						BOOLEAN
		},
		tdd									SEQUENCE {
			dl-DPCH-PowerControlInfo			DL-DPCH-PowerControlInfo			OPTIONAL
		}
	}
}

DL-DPCH-InfoCommon-r4 ::=			SEQUENCE {
	cfnHandling							CHOICE {
		maintain							NULL,
		initialise							SEQUENCE {
			-- IE dummy is not used in this version of the specification
			-- The IE should not be sent and if received it should be ignored
			dummy								Cfntargetsfnframeoffset				OPTIONAL
		}
	},
	modeSpecificInfo					CHOICE {
		fdd 								SEQUENCE {
			dl-DPCH-PowerControlInfo			DL-DPCH-PowerControlInfo			OPTIONAL,
			powerOffsetPilot-pdpdch				PowerOffsetPilot-pdpdch,
			dl-rate-matching-restriction		Dl-rate-matching-restriction		OPTIONAL,
			-- TABULAR: The number of pilot bits is nested inside the spreading factor.
			spreadingFactorAndPilot				SF512-AndPilot,
			positionFixedOrFlexible				PositionFixedOrFlexible,
			tfci-Existence						BOOLEAN
		},
		tdd									SEQUENCE {
			dl-DPCH-PowerControlInfo			DL-DPCH-PowerControlInfo			OPTIONAL
		}
	},
-- The IE mac-d-HFN-initial-value should be absent in the RRCConnectionSetup-r4-IEs or
-- RRCConnectionSetup-r5-IEs or HandoverToUTRANCommand-r4-IEs or HandoverToUTRANCommand-r5-IEs and
-- if the IE is included, the general error handling for conditional IEs applies.
	mac-d-HFN-initial-value				MAC-d-HFN-initial-value				OPTIONAL

}

DL-DPCH-InfoCommon-r6 ::=				SEQUENCE {
	cfnHandling								CHOICE {
		maintain								SEQUENCE {
			timingmaintainedsynchind				TimingMaintainedSynchInd			OPTIONAL
		},
		initialise								NULL
	},
	modeSpecificInfo						CHOICE {
		fdd 									SEQUENCE {
			dl-DPCH-PowerControlInfo				DL-DPCH-PowerControlInfo			OPTIONAL,
			powerOffsetPilot-pdpdch					PowerOffsetPilot-pdpdch,
			dl-rate-matching-restriction			Dl-rate-matching-restriction		OPTIONAL,
			-- TABULAR: The number of pilot bits is nested inside the spreading factor.
			spreadingFactorAndPilot					SF512-AndPilot,
			positionFixedOrFlexible					PositionFixedOrFlexible,
			tfci-Existence							BOOLEAN
		},
		tdd									SEQUENCE {
			dl-DPCH-PowerControlInfo			DL-DPCH-PowerControlInfo			OPTIONAL
		}
	},
	-- The IE mac-d-HFN-initial-value should be absent in the RRCConnectionSetup and the
	-- HandoverToUTRANCommand messages. If the IE is included, the general error handling
	-- for conditional IEs applies.
	mac-d-HFN-initial-value				MAC-d-HFN-initial-value				OPTIONAL
}

DL-DPCH-InfoCommon-r12 ::=				SEQUENCE {
	cfnHandling								CHOICE {
		maintain								SEQUENCE {
			timingmaintainedsynchind				TimingMaintainedSynchInd			OPTIONAL
		},
		initialise								NULL
	},
	modeSpecificInfo						CHOICE {
		fdd 									SEQUENCE {
			dl-DPCH-PowerControlInfo				DL-DPCH-PowerControlInfo			OPTIONAL,
			powerOffsetPilot-pdpdch					PowerOffsetPilot-pdpdch,
			dl-rate-matching-restriction			Dl-rate-matching-restriction		OPTIONAL,
			-- TABULAR: The number of pilot bits is nested inside the spreading factor.
			spreadingFactorAndPilot					SF512-AndPilot-r12,
			positionFixedOrFlexible					PositionFixedOrFlexible,
			tfci-Existence							BOOLEAN
		},
		tdd									SEQUENCE {
			dl-DPCH-PowerControlInfo			DL-DPCH-PowerControlInfo			OPTIONAL
		}
	},
	-- The IE mac-d-HFN-initial-value should be absent in the RRCConnectionSetup and the
	-- HandoverToUTRANCommand messages. If the IE is included, the general error handling
	-- for conditional IEs applies.
	mac-d-HFN-initial-value				MAC-d-HFN-initial-value				OPTIONAL
}

DL-DPCH-InfoCommonPost ::=			SEQUENCE {
	dl-DPCH-PowerControlInfo			DL-DPCH-PowerControlInfo				OPTIONAL
}

DL-DPCH-InfoCommonPredef ::=		SEQUENCE {
	modeSpecificInfo					CHOICE {
		fdd									SEQUENCE {
			-- TABULAR: The number of pilot bits is nested inside the spreading factor.
			spreadingFactorAndPilot				SF512-AndPilot,
			positionFixedOrFlexible				PositionFixedOrFlexible,
			tfci-Existence						BOOLEAN
		},
		tdd									SEQUENCE {
			commonTimeslotInfo					CommonTimeslotInfo
		}
	}
}

DL-DPCH-InfoPerRL ::=				CHOICE {
	fdd									SEQUENCE {
		pCPICH-UsageForChannelEst			PCPICH-UsageForChannelEst,
		dpch-FrameOffset					DPCH-FrameOffset,
		secondaryCPICH-Info					SecondaryCPICH-Info				OPTIONAL,
		dl-ChannelisationCodeList			DL-ChannelisationCodeList,
		tpc-CombinationIndex				TPC-CombinationIndex,
		-- dummy is not used in this version of the specification, it should
		-- not be sent and if received it should be ignored.
		dummy								SSDT-CellIdentity				OPTIONAL,
		closedLoopTimingAdjMode				ClosedLoopTimingAdjMode			OPTIONAL
	},
	tdd									SEQUENCE {
		dl-CCTrChListToEstablish			DL-CCTrChList					OPTIONAL,
		dl-CCTrChListToRemove				DL-CCTrChListToRemove			OPTIONAL
	}
}

DL-DPCH-InfoPerRL-r4 ::=			CHOICE {
	fdd									SEQUENCE {
		pCPICH-UsageForChannelEst			PCPICH-UsageForChannelEst,
		dpch-FrameOffset					DPCH-FrameOffset,
		secondaryCPICH-Info					SecondaryCPICH-Info				OPTIONAL,
		dl-ChannelisationCodeList			DL-ChannelisationCodeList,
		tpc-CombinationIndex				TPC-CombinationIndex,
		-- dummy is not used in this version of the specification, it should
		-- not be sent and if received it should be ignored.
		dummy								SSDT-CellIdentity				OPTIONAL,
		closedLoopTimingAdjMode				ClosedLoopTimingAdjMode			OPTIONAL
	},
	tdd									SEQUENCE {
		dl-CCTrChListToEstablish			DL-CCTrChList-r4				OPTIONAL,
		dl-CCTrChListToRemove				DL-CCTrChListToRemove			OPTIONAL
	}
}

DL-DPCH-InfoPerRL-r5 ::=			CHOICE {
	fdd									SEQUENCE {
		pCPICH-UsageForChannelEst			PCPICH-UsageForChannelEst,
		dpch-FrameOffset					DPCH-FrameOffset,
		secondaryCPICH-Info					SecondaryCPICH-Info				OPTIONAL,
		dl-ChannelisationCodeList			DL-ChannelisationCodeList,
		tpc-CombinationIndex				TPC-CombinationIndex,
		powerOffsetTPC-pdpdch				PowerOffsetTPC-pdpdch			OPTIONAL,
		-- dummy is not used in this version of the specification, it should
		-- not be sent and if received it should be ignored.
		dummy								SSDT-CellIdentity				OPTIONAL,
		closedLoopTimingAdjMode				ClosedLoopTimingAdjMode			OPTIONAL
	},
	tdd									SEQUENCE {
		dl-CCTrChListToEstablish			DL-CCTrChList-r4				OPTIONAL,
		dl-CCTrChListToRemove				DL-CCTrChListToRemove			OPTIONAL
	}
}

DL-DPCH-InfoPerRL-r6 ::=			CHOICE {
	fdd									SEQUENCE {
		pCPICH-UsageForChannelEst			PCPICH-UsageForChannelEst,
		dpch-FrameOffset					DPCH-FrameOffset,
		secondaryCPICH-Info					SecondaryCPICH-Info				OPTIONAL,
		dl-ChannelisationCodeList			DL-ChannelisationCodeList,
		tpc-CombinationIndex				TPC-CombinationIndex,
		powerOffsetTPC-pdpdch				PowerOffsetTPC-pdpdch			OPTIONAL,
		closedLoopTimingAdjMode				ClosedLoopTimingAdjMode			OPTIONAL
	},
	tdd									SEQUENCE {
		dl-CCTrChListToEstablish			DL-CCTrChList-r4				OPTIONAL,
		dl-CCTrChListToRemove				DL-CCTrChListToRemove			OPTIONAL
	}
}

DL-DPCH-InfoPerRL-r7 ::=			CHOICE {
	fdd									SEQUENCE {
		pCPICH-UsageForChannelEst			PCPICH-UsageForChannelEst,
		dpch-FrameOffset					DPCH-FrameOffset,
		secondaryCPICH-Info					SecondaryCPICH-Info				OPTIONAL,
		dl-ChannelisationCodeList			DL-ChannelisationCodeList,
		tpc-CombinationIndex				TPC-CombinationIndex,
		powerOffsetTPC-pdpdch				PowerOffsetTPC-pdpdch			OPTIONAL,
		closedLoopTimingAdjMode				ClosedLoopTimingAdjMode			OPTIONAL
	},
	tdd									SEQUENCE {
		dl-CCTrChListToEstablish			DL-CCTrChList-r7				OPTIONAL,
		dl-CCTrChListToRemove				DL-CCTrChListToRemove			OPTIONAL
	}
}

DL-DPCH-InfoPerRL-r12 ::=			CHOICE {
	fdd									SEQUENCE {
		pCPICH-UsageForChannelEst			PCPICH-UsageForChannelEst,
		dpch-FrameOffset					DPCH-FrameOffset,
		secondaryCPICH-Info					SecondaryCPICH-Info				OPTIONAL,
		dl-ChannelisationCodeList			DL-ChannelisationCodeList,
		tpc-CombinationIndex				TPC-CombinationIndex,
		powerOffsetTPC-pdpdch				PowerOffsetTPC-pdpdch			OPTIONAL,
		powerOffsetPO-SRB					PowerOffsetPO-SRB				OPTIONAL,
		closedLoopTimingAdjMode				ClosedLoopTimingAdjMode			OPTIONAL
	},
	tdd									SEQUENCE {
		dl-CCTrChListToEstablish			DL-CCTrChList-r7				OPTIONAL,
		dl-CCTrChListToRemove				DL-CCTrChListToRemove			OPTIONAL
	}
}


DL-DPCH-InfoPerRL-ASU ::=			CHOICE {
	fdd									SEQUENCE {
		pCPICH-UsageForChannelEst			PCPICH-UsageForChannelEst,
		dpch-FrameOffset					DPCH-FrameOffset,
		secondaryCPICH-Info					SecondaryCPICH-Info				OPTIONAL,
		dl-ChannelisationCodeList			DL-ChannelisationCodeList,
		tpc-CombinationIndex				TPC-CombinationIndex,
		powerOffsetTPC-pdpdch				PowerOffsetTPC-pdpdch			OPTIONAL,
		powerOffsetPO-SRB					PowerOffsetPO-SRB				OPTIONAL,
		closedLoopTimingAdjMode				ClosedLoopTimingAdjMode			OPTIONAL
	},
	tdd									SEQUENCE {
		dl-CCTrChListToEstablish			DL-CCTrChList-r4				OPTIONAL,
		dl-CCTrChListToRemove				DL-CCTrChListToRemove			OPTIONAL
	}
}

DL-FDPCH-InfoPerRL-r6 ::=			SEQUENCE {
	pCPICH-UsageForChannelEst			PCPICH-UsageForChannelEst,
	fdpch-FrameOffset					DPCH-FrameOffset,
	secondaryCPICH-Info					SecondaryCPICH-Info				OPTIONAL,
	secondaryScramblingCode				SecondaryScramblingCode			OPTIONAL,
	dl-ChannelisationCode				INTEGER (0..255),
	tpc-CombinationIndex				TPC-CombinationIndex
}

DL-FDPCH-InfoPerRL-r7 ::=			SEQUENCE {
	pCPICH-UsageForChannelEst			PCPICH-UsageForChannelEst,
	fdpch-FrameOffset					DPCH-FrameOffset,
	fdpch-SlotFormat					FDPCH-SlotFormat				OPTIONAL,
	secondaryCPICH-Info					SecondaryCPICH-Info				OPTIONAL,
	secondaryScramblingCode				SecondaryScramblingCode			OPTIONAL,
	dl-ChannelisationCode				INTEGER (0..255),
	tpc-CombinationIndex				TPC-CombinationIndex,
	sttdIndication						STTDIndication					OPTIONAL
}

DL-FDPCH-InfoPerRL-r13 ::=		SEQUENCE {
	pCPICH-UsageForChannelEst			PCPICH-UsageForChannelEst,
	fdpch-FrameOffset					DPCH-FrameOffset,
	fdpch-SlotFormat					FDPCH-SlotFormat						OPTIONAL,
	secondaryCPICH-Info				SecondaryCPICH-Info					OPTIONAL,
	secondaryScramblingCode			SecondaryScramblingCode				OPTIONAL,
	dl-ChannelisationCode				INTEGER (0..255),
	tpc-CombinationIndex				TPC-CombinationIndex,
	sttdIndication						STTDIndication							OPTIONAL,
	powerControlAlgorithm3-Config	PowerControlAlgorithm3-Config			OPTIONAL
}

DL-DPCH-InfoPerRL-PostFDD ::=								SEQUENCE {
		pCPICH-UsageForChannelEst				PCPICH-UsageForChannelEst,
		dl-ChannelisationCode					DL-ChannelisationCode,
		tpc-CombinationIndex					TPC-CombinationIndex
}

DL-DPCH-InfoPerRL-PostTDD ::=				SEQUENCE {
	dl-DPCH-TimeslotsCodes						DownlinkTimeslotsCodes
}

DL-DPCH-InfoPerRL-PostTDD-LCR-r4 ::=		SEQUENCE {
	dl-CCTrCH-TimeslotsCodes					DownlinkTimeslotsCodes-LCR-r4
}

DL-DPCH-PowerControlInfo ::=			SEQUENCE {
	modeSpecificInfo						CHOICE {
		fdd										SEQUENCE {
			dpc-Mode								DPC-Mode
		},
		tdd										SEQUENCE {
			tpc-StepSizeTDD							TPC-StepSizeTDD			OPTIONAL
		}
	}
}

DL-FDPCH-InfoCommon-r6 ::=			SEQUENCE {
	cfnHandling							CHOICE {
		maintain							SEQUENCE {
			timingmaintainedsynchind			TimingMaintainedSynchInd			OPTIONAL
		},
		initialise							NULL
	},
	dl-FDPCH-PowerControlInfo			DL-DPCH-PowerControlInfo			OPTIONAL,
	-- Actual value dl-FDPCH-TPCcommandErrorRate = IE value * 0.01
	-- dl-FDPCH-TPCcommandErrorRate values 11..16 are spare and shall not be used in this version of
	-- the protocol.
	-- In addition, this IE shall always be included otherwise the UE behaviour is unspecified.
	dl-FDPCH-TPCcommandErrorRate		INTEGER (1..16)		OPTIONAL
}

DL-FrameType ::=					ENUMERATED {
										dl-FrameTypeA, dl-FrameTypeB }

DL-HSPDSCH-Information ::=			SEQUENCE {
	hs-scch-Info					HS-SCCH-Info	OPTIONAL,
	measurement-feedback-Info		Measurement-Feedback-Info	OPTIONAL,
	modeSpecificInfo				CHOICE {
	tdd								CHOICE{
			tdd384							SEQUENCE {
				dl-HSPDSCH-TS-Configuration	DL-HSPDSCH-TS-Configuration	  	OPTIONAL
			},
			tdd128							SEQUENCE {
				hs-PDSCH-Midamble-Configuration-tdd128
						HS-PDSCH-Midamble-Configuration-TDD128				OPTIONAL
			}
		},
		fdd							NULL
	}
}

DL-HSPDSCH-Information-r6 ::=	SEQUENCE {
	hs-scch-Info					HS-SCCH-Info-r6							OPTIONAL,
	measurement-feedback-Info		Measurement-Feedback-Info				OPTIONAL,
	modeSpecificInfo				CHOICE {
		tdd								CHOICE {
			tdd384							SEQUENCE {
				dl-HSPDSCH-TS-Configuration		DL-HSPDSCH-TS-Configuration	OPTIONAL
			},
			tdd128							SEQUENCE {
				hs-PDSCH-Midamble-Configuration-tdd128
						HS-PDSCH-Midamble-Configuration-TDD128				OPTIONAL
			}
		},
		fdd							NULL
	}
}

DL-HSPDSCH-Information-r7 ::=	SEQUENCE {
	hs-scch-Info					HS-SCCH-Info-r7							OPTIONAL,
	measurement-feedback-Info		Measurement-Feedback-Info-r7			OPTIONAL,
	modeSpecificInfo				CHOICE {
		tdd								CHOICE {
			tdd384							SEQUENCE {
				dl-HSPDSCH-TS-Configuration		DL-HSPDSCH-TS-Configuration	OPTIONAL
			},
			tdd768							SEQUENCE {
				dl-HSPDSCH-TS-Configuration		DL-HSPDSCH-TS-Configuration-VHCR	OPTIONAL
			},
			tdd128							SEQUENCE {
				hs-PDSCH-Midamble-Configuration-tdd128
						HS-PDSCH-Midamble-Configuration-TDD128						OPTIONAL,
				dl-MultiCarrier-Information		DL-MultiCarrier-Information			OPTIONAL
			}
		},
		fdd								SEQUENCE {
			dl-64QAM-Configured				ENUMERATED { true }					OPTIONAL
		}
	}
}

DL-HSPDSCH-Information-r8 ::=	SEQUENCE {
	hs-scch-Info					HS-SCCH-Info-r7							OPTIONAL,
	measurement-feedback-Info		Measurement-Feedback-Info-r7			OPTIONAL,
	modeSpecificInfo				CHOICE {
		tdd								CHOICE {
			tdd384							SEQUENCE {
				dl-HSPDSCH-TS-Configuration		DL-HSPDSCH-TS-Configuration	OPTIONAL
			},
			tdd768							SEQUENCE {
				dl-HSPDSCH-TS-Configuration		DL-HSPDSCH-TS-Configuration-VHCR	OPTIONAL
			},
			tdd128							SEQUENCE {
				hs-PDSCH-Midamble-Configuration-tdd128
						HS-PDSCH-Midamble-Configuration-TDD128						OPTIONAL,
				dl-MultiCarrier-Information		DL-MultiCarrier-Information			OPTIONAL
			}
		},
		fdd								SEQUENCE {
			dl-64QAM-Configured				ENUMERATED { true }					OPTIONAL,
			hs-DSCH-TBSizeTable				HS-DSCH-TBSizeTable					OPTIONAL
		}
	}
}

DL-HSPDSCH-Information-r8-ext ::=	SEQUENCE {
	modeSpecificInfo				CHOICE {
		tdd								CHOICE {
			tdd384						NULL,
			tdd768						NULL,
			tdd128							SEQUENCE {
				outofSyncWindow					OutofSyncWindow					OPTIONAL
			}
		},
		fdd								NULL
	}
}

DL-HSPDSCH-Information-r8-ext2 ::=	SEQUENCE {
	hs-scch-Info						HS-SCCH-Info-r8-ext							OPTIONAL
}

DL-HSPDSCH-Information-r9 ::=	SEQUENCE {
	hs-scch-Info					HS-SCCH-Info-r9							OPTIONAL,
	measurement-feedback-Info		Measurement-Feedback-Info-r7			OPTIONAL,
	modeSpecificInfo				CHOICE {
		tdd								CHOICE {
			tdd384							SEQUENCE {
				dl-HSPDSCH-TS-Configuration		DL-HSPDSCH-TS-Configuration	OPTIONAL
			},
			tdd768							SEQUENCE {
				dl-HSPDSCH-TS-Configuration		DL-HSPDSCH-TS-Configuration-VHCR	OPTIONAL
			},
			tdd128							SEQUENCE {
				hs-PDSCH-Midamble-Configuration-tdd128
						HS-PDSCH-Midamble-Configuration-TDD128						OPTIONAL,
				dl-MultiCarrier-Information		DL-MultiCarrier-Information			OPTIONAL,
				tS0-Indicator					ENUMERATED { true }					OPTIONAL,
				outofSyncWindow								OutofSyncWindow			OPTIONAL
			}
		},
		fdd								SEQUENCE {
			dl-64QAM-Configured				ENUMERATED { true }					OPTIONAL,
			hs-DSCH-TBSizeTable				HS-DSCH-TBSizeTable					OPTIONAL
		}
	}
}

DL-HSPDSCH-Information-r11 ::=	SEQUENCE {
	hs-scch-Info					HS-SCCH-Info-r9							OPTIONAL,
	measurement-feedback-Info		Measurement-Feedback-Info-r11			OPTIONAL,
	modeSpecificInfo				CHOICE {
		tdd								CHOICE {
			tdd384							SEQUENCE {
				dl-HSPDSCH-TS-Configuration		DL-HSPDSCH-TS-Configuration	OPTIONAL
			},
			tdd768							SEQUENCE {
				dl-HSPDSCH-TS-Configuration		DL-HSPDSCH-TS-Configuration-VHCR	OPTIONAL
			},
			tdd128							SEQUENCE {
				hs-PDSCH-Midamble-Configuration-tdd128
						HS-PDSCH-Midamble-Configuration-TDD128						OPTIONAL,
				dl-MultiCarrier-Information		DL-MultiCarrier-Information			OPTIONAL,
				tS0-Indicator					ENUMERATED { true }					OPTIONAL,
				outofSyncWindow								OutofSyncWindow			OPTIONAL
			}
		},
		fdd								SEQUENCE {
			dl-64QAM-Configured				ENUMERATED { true }					OPTIONAL,
			hs-DSCH-TBSizeTable				HS-DSCH-TBSizeTable					OPTIONAL
		}
	}
}

DL-HSPDSCH-Information-r12 ::=	SEQUENCE {
	hs-scch-Info					HS-SCCH-Info-r9									OPTIONAL,
	measurement-feedback-Info		Measurement-Feedback-Info-r12					OPTIONAL,
	modeSpecificInfo				CHOICE {
		tdd								CHOICE {
			tdd384							SEQUENCE {
				dl-HSPDSCH-TS-Configuration		DL-HSPDSCH-TS-Configuration			OPTIONAL
			},
			tdd768							SEQUENCE {
				dl-HSPDSCH-TS-Configuration		DL-HSPDSCH-TS-Configuration-VHCR	OPTIONAL
			},
			tdd128							SEQUENCE {
				hs-PDSCH-Midamble-Configuration-tdd128
						HS-PDSCH-Midamble-Configuration-TDD128						OPTIONAL,
				dl-MultiCarrier-Information		DL-MultiCarrier-Information			OPTIONAL,
				tS0-Indicator					ENUMERATED { true }					OPTIONAL,
				outofSyncWindow								OutofSyncWindow			OPTIONAL,
				ts0ChannelizationCodes			DL-TS-ChannelisationCodesShort		OPTIONAL
			}
		},
		fdd								SEQUENCE {
			dl-64QAM-Configured				ENUMERATED { true }						OPTIONAL,
			hs-DSCH-TBSizeTable				HS-DSCH-TBSizeTable						OPTIONAL
		}
	}
}

OutofSyncWindow ::=						ENUMERATED {
											ms40, ms80, ms160, ms320,
											ms640, spare3, spare2, spare1 }

DL-HSPDSCH-MultiCarrier-Information ::=	SEQUENCE (SIZE (1..maxTDD128Carrier)) OF
											SEQUENCE {
		uarfcn-Carrier							UARFCN,
		harqInfo								HARQ-Info								OPTIONAL,
		hs-PDSCH-Midamble-Configuration			HS-PDSCH-Midamble-Configuration-TDD128	OPTIONAL,
		hs-SCCH-TDD128-MultiCarrier				SEQUENCE (SIZE (1..maxHSSCCHs)) OF
													HS-SCCH-TDD128-MultiCarrier			OPTIONAL
	}

-- The IE 'DL-HSPDSCH-TS-Configuration' applies to tdd-384 REL-5 onward
DL-HSPDSCH-TS-Configuration ::=		SEQUENCE (SIZE (1..maxTS-1)) OF
										SEQUENCE {
	timeslot								TimeslotNumber,
	midambleShiftAndBurstType				MidambleShiftAndBurstType-DL
}

-- The IE 'DL-HSPDSCH-TS-Configuration-VHCR' applies to tdd-768 REL-7 onward
DL-HSPDSCH-TS-Configuration-VHCR ::= SEQUENCE (SIZE (1..maxTS-1)) OF
										SEQUENCE {
	timeslot								TimeslotNumber,
	midambleShiftAndBurstType				MidambleShiftAndBurstType-DL-VHCR
}

DL-InformationPerRL ::=				SEQUENCE {
	modeSpecificInfo					CHOICE {
		fdd									SEQUENCE {
			primaryCPICH-Info					PrimaryCPICH-Info,
			-- dummy1 and dummy 2 are not used in this version of specification, they should
			-- not be sent and if received they should be ignored.
			dummy1								PDSCH-SHO-DCH-Info			OPTIONAL,
			dummy2								PDSCH-CodeMapping			OPTIONAL
		},
		tdd									PrimaryCCPCH-Info
	},
	dl-DPCH-InfoPerRL					DL-DPCH-InfoPerRL					OPTIONAL,
	-- dummy is not used in this version of the specification, it should
	-- not be sent and if received it should be ignored.
	dummy								SCCPCH-InfoForFACH					OPTIONAL
}

DL-InformationPerRL-r4 ::=			SEQUENCE {
	modeSpecificInfo					CHOICE {
		fdd									SEQUENCE {
			primaryCPICH-Info					PrimaryCPICH-Info,
			-- dummy1 and dummy 2 are not used in this version of specification, they should
			-- not be sent and if received they should be ignored.
			dummy1								PDSCH-SHO-DCH-Info			OPTIONAL,
			dummy2								PDSCH-CodeMapping			OPTIONAL
		},
		tdd									PrimaryCCPCH-Info-r4
	},
	dl-DPCH-InfoPerRL					DL-DPCH-InfoPerRL-r4				OPTIONAL,
	-- dummy is not used in this version of the specification, it should
	-- not be sent and if received it should be ignored.
	dummy								SCCPCH-InfoForFACH-r4				OPTIONAL,
	cell-id								CellIdentity						OPTIONAL
}

DL-InformationPerRL-r5 ::=			SEQUENCE {
	modeSpecificInfo					CHOICE {
		fdd									SEQUENCE {
			primaryCPICH-Info					PrimaryCPICH-Info,
			-- dummy1 and dummy 2 are not used in this version of specification, they should
			-- not be sent and if received they should be ignored.
			dummy1								PDSCH-SHO-DCH-Info			OPTIONAL,
			dummy2								PDSCH-CodeMapping			OPTIONAL,
			servingHSDSCH-RL-indicator			BOOLEAN
		},
		tdd									PrimaryCCPCH-Info-r4
	},
	dl-DPCH-InfoPerRL					DL-DPCH-InfoPerRL-r5				OPTIONAL,
	-- dummy is not used in this version of the specification, it should
	-- not be sent and if received it should be ignored.
	dummy								SCCPCH-InfoForFACH-r4				OPTIONAL,
	cell-id								CellIdentity						OPTIONAL
}

DL-InformationPerRL-r5bis ::=		SEQUENCE {
	modeSpecificInfo					CHOICE {
		fdd									SEQUENCE {
			primaryCPICH-Info					PrimaryCPICH-Info,
			-- dummy1 and dummy 2 are not used in this version of specification, they should
			-- not be sent and if received they should be ignored.
			dummy1								PDSCH-SHO-DCH-Info			OPTIONAL,
			dummy2								PDSCH-CodeMapping			OPTIONAL
		},
		tdd									PrimaryCCPCH-Info-r4
	},
	dl-DPCH-InfoPerRL					DL-DPCH-InfoPerRL-r5				OPTIONAL,
	-- dummy is not used in this version of the specification, it should
	-- not be sent and if received it should be ignored.
	dummy								SCCPCH-InfoForFACH-r4				OPTIONAL,
	cell-id								CellIdentity						OPTIONAL
}

DL-InformationPerRL-r6 ::=			SEQUENCE {
	modeSpecificInfo					CHOICE {
		fdd									SEQUENCE {
			primaryCPICH-Info					PrimaryCPICH-Info,
			servingHSDSCH-RL-indicator			BOOLEAN,
			servingEDCH-RL-indicator			BOOLEAN
		},
		tdd									PrimaryCCPCH-Info-r4
	},
	dl-dpchInfo							CHOICE {
		dl-DPCH-InfoPerRL					DL-DPCH-InfoPerRL-r6,
		dl-FDPCH-InfoPerRL					DL-FDPCH-InfoPerRL-r6
	}																		OPTIONAL,
	e-AGCH-Information					E-AGCH-Information					OPTIONAL,
	e-HICH-Info							CHOICE	{
		e-HICH-Information					E-HICH-Information,
		releaseIndicator					NULL
	}	OPTIONAL,
	e-RGCH-Info							CHOICE	{
		e-RGCH-Information					E-RGCH-Information,
		releaseIndicator					NULL
	}	OPTIONAL,
	cell-id								CellIdentity						OPTIONAL
}

DL-InformationPerRL-v6b0ext ::=		SEQUENCE {
		sttdIndication					STTDIndication						OPTIONAL
}

DL-InformationPerRL-r7 ::=			SEQUENCE {
	modeSpecificInfo					CHOICE {
		fdd									SEQUENCE {
			primaryCPICH-Info					PrimaryCPICH-Info,
			servingHSDSCH-RL-indicator			BOOLEAN,
			servingEDCH-RL-indicator			BOOLEAN
		},
		tdd									PrimaryCCPCH-Info-r4
	},
	dl-dpchInfo							CHOICE {
		dl-DPCH-InfoPerRL					DL-DPCH-InfoPerRL-r7,
		dl-FDPCH-InfoPerRL					DL-FDPCH-InfoPerRL-r7
	}																		OPTIONAL,
	e-AGCH-Information					E-AGCH-Information-r7				OPTIONAL,
	modeSpecificInfo2					CHOICE {
		fdd									SEQUENCE {
			e-HICH-Info							CHOICE {
				e-HICH-Information					E-HICH-Information,
				releaseIndicator					NULL
			}	OPTIONAL,
			e-RGCH-Info							CHOICE {
				e-RGCH-Information					E-RGCH-Information,
				releaseIndicator					NULL
			}	OPTIONAL
		},
		tdd									CHOICE {
			tdd384-tdd768						SEQUENCE {
				e-HICH-Info							E-HICH-Information-TDD384-768	OPTIONAL
			},
			tdd128								SEQUENCE {
				e-HICH-Info							E-HICH-Information-TDD128	OPTIONAL
			}
		}
	},
	cell-id								CellIdentity						OPTIONAL
}

DL-InformationPerRL-r8 ::=			SEQUENCE {
	modeSpecificInfo					CHOICE {
		fdd									SEQUENCE {
			primaryCPICH-Info					PrimaryCPICH-Info,
			servingHSDSCH-RL-indicator			BOOLEAN,
			servingEDCH-RL-indicator			BOOLEAN
		},
		tdd									PrimaryCCPCH-Info-r4
	},
	dl-dpchInfo							CHOICE {
		dl-DPCH-InfoPerRL					DL-DPCH-InfoPerRL-r7,
		dl-FDPCH-InfoPerRL					DL-FDPCH-InfoPerRL-r7
	}																		OPTIONAL,
	e-AGCH-Information					E-AGCH-Information-r8				OPTIONAL,
	modeSpecificInfo2					CHOICE {
		fdd									SEQUENCE {
			e-HICH-Info							CHOICE {
				e-HICH-Information					E-HICH-Information,
				releaseIndicator					NULL
			}	OPTIONAL,
			e-RGCH-Info							CHOICE {
				e-RGCH-Information					E-RGCH-Information,
				releaseIndicator					NULL
			}	OPTIONAL
		},
		tdd									CHOICE {
			tdd384-tdd768						SEQUENCE {
				e-HICH-Info							E-HICH-Information-TDD384-768	OPTIONAL
			},
			tdd128								SEQUENCE {
				e-HICH-Info							E-HICH-Information-TDD128	OPTIONAL
			}
		}
	},
	cell-id								CellIdentity						OPTIONAL
}

DL-InformationPerRL-r11 ::=			SEQUENCE {
	modeSpecificInfo					CHOICE {
		fdd									SEQUENCE {
			primaryCPICH-Info					PrimaryCPICH-Info,
			servingHSDSCH-RL-indicator			BOOLEAN,
			servingEDCH-RL-indicator			BOOLEAN
		},
		tdd									PrimaryCCPCH-Info-r4
	},
	dl-dpchInfo							CHOICE {
		dl-DPCH-InfoPerRL					DL-DPCH-InfoPerRL-r7,
		dl-FDPCH-InfoPerRL					DL-FDPCH-InfoPerRL-r7
	}																		OPTIONAL,
	e-AGCH-Information					E-AGCH-Information-r8				OPTIONAL,
	e-ROCH-Information					E-ROCH-Information					OPTIONAL,
	modeSpecificInfo2					CHOICE {
		fdd									SEQUENCE {
			e-HICH-Info							CHOICE {
				e-HICH-Information					E-HICH-Information-r11,
				releaseIndicator					NULL,
				secondaryReleaseIndicator			NULL
			}	OPTIONAL,
			e-RGCH-Info							CHOICE {
				e-RGCH-Information					E-RGCH-Information,
				releaseIndicator					NULL
			}	OPTIONAL,
			f-TPICH-Info							CHOICE {
				f-TPICH-Information					F-TPICH-Information,
				releaseIndicator					NULL
			}	OPTIONAL
		},
		tdd									CHOICE {
			tdd384-tdd768						SEQUENCE {
				e-HICH-Info							E-HICH-Information-TDD384-768	OPTIONAL
			},
			tdd128								SEQUENCE {
				e-HICH-Info							E-HICH-Information-TDD128		OPTIONAL
			}
		}
	},
	cell-id								CellIdentity						OPTIONAL
}

DL-InformationPerRL-r12 ::=			SEQUENCE {
	modeSpecificInfo					CHOICE {
		fdd									SEQUENCE {
			primaryCPICH-Info					PrimaryCPICH-Info,
			servingHSDSCH-RL-indicator		BOOLEAN,
			servingEDCH-RL-indicator			BOOLEAN
		},
		tdd									PrimaryCCPCH-Info-r4
	},
	dl-dpchInfo							CHOICE {
		dl-DPCH-InfoPerRL					DL-DPCH-InfoPerRL-r12,
		dl-FDPCH-InfoPerRL					DL-FDPCH-InfoPerRL-r7,
		radioLinkswithoutDPCHFDPCHInfo		RadioLinkswithoutDPCHFDPCHInfo
	}																		OPTIONAL,
	e-AGCH-Information					E-AGCH-Information-r8				OPTIONAL,
	e-ROCH-Information					E-ROCH-Information					OPTIONAL,
	modeSpecificInfo2					CHOICE {
		fdd									SEQUENCE {
			e-HICH-Info							CHOICE {
				e-HICH-Information					E-HICH-Information-r11,
				releaseIndicator					NULL,
				secondaryReleaseIndicator			NULL
			}	OPTIONAL,
			e-RGCH-Info							CHOICE {
				e-RGCH-Information					E-RGCH-Information,
				releaseIndicator					NULL
			}	OPTIONAL,
			f-TPICH-Info							CHOICE {
				f-TPICH-Information					F-TPICH-Information,
				releaseIndicator					NULL
			}	OPTIONAL
		},
		tdd									CHOICE {
			tdd384-tdd768						SEQUENCE {
				e-HICH-Info							E-HICH-Information-TDD384-768	OPTIONAL
			},
			tdd128								SEQUENCE {
				e-HICH-Info							E-HICH-Information-TDD128		OPTIONAL
			}
		}
	},
	cell-id								CellIdentity						OPTIONAL
}

DL-InformationPerRL-r13 ::=		SEQUENCE {
	modeSpecificInfo					CHOICE {
		fdd									SEQUENCE {
			primaryCPICH-Info					PrimaryCPICH-Info,
			servingHSDSCH-RL-indicator		BOOLEAN,
			servingEDCH-RL-indicator			BOOLEAN
		},
		tdd									PrimaryCCPCH-Info-r4
	},
	dl-dpchInfo						CHOICE {
		dl-DPCH-InfoPerRL					DL-DPCH-InfoPerRL-r12,
		dl-FDPCH-InfoPerRL					DL-FDPCH-InfoPerRL-r13,
		radioLinkswithoutDPCHFDPCHInfo	RadioLinkswithoutDPCHFDPCHInfo
	}																		OPTIONAL,
	e-AGCH-Information					E-AGCH-Information-r8				OPTIONAL,
	e-ROCH-Information					E-ROCH-Information					OPTIONAL,
	modeSpecificInfo2					CHOICE {
		fdd									SEQUENCE {
			e-HICH-Info							CHOICE {
				e-HICH-Information						E-HICH-Information-r11,
				releaseIndicator						NULL,
				secondaryReleaseIndicator				NULL
			}	OPTIONAL,
			e-RGCH-Info							CHOICE {
				e-RGCH-Information						E-RGCH-Information,
				releaseIndicator						NULL
			}	OPTIONAL,
			f-TPICH-Info							CHOICE {
				f-TPICH-Information					F-TPICH-Information,
				releaseIndicator						NULL
			}	OPTIONAL
		},
		tdd									CHOICE {
			tdd384-tdd768						SEQUENCE {
				e-HICH-Info							E-HICH-Information-TDD384-768	OPTIONAL
			},
			tdd128								SEQUENCE {
				e-HICH-Info							E-HICH-Information-TDD128		OPTIONAL
			}
		}
	},
	cell-id								CellIdentity						OPTIONAL
}

DL-InformationPerRL-List ::=		SEQUENCE (SIZE (1..maxRL)) OF
										DL-InformationPerRL

DL-InformationPerRL-List-r4 ::=		SEQUENCE (SIZE (1..maxRL)) OF
										DL-InformationPerRL-r4

DL-InformationPerRL-List-r5 ::=		SEQUENCE (SIZE (1..maxRL)) OF
										DL-InformationPerRL-r5

DL-InformationPerRL-List-r6 ::=		SEQUENCE (SIZE (1..maxRL)) OF
										DL-InformationPerRL-r6

DL-InformationPerRL-List-v6b0ext ::= SEQUENCE (SIZE (1..maxRL)) OF
										DL-InformationPerRL-v6b0ext

DL-InformationPerRL-List-r5bis ::=		SEQUENCE (SIZE (1..maxRL)) OF
											DL-InformationPerRL-r5bis

DL-InformationPerRL-List-r7 ::=		SEQUENCE (SIZE (1..maxRL)) OF
										DL-InformationPerRL-r7

DL-InformationPerRL-List-r8 ::=		SEQUENCE (SIZE (1..maxRL)) OF
										DL-InformationPerRL-r8

DL-InformationPerRL-List-r11 ::=	SEQUENCE (SIZE (1..maxRL)) OF
										DL-InformationPerRL-r11

DL-InformationPerRL-List-r12 ::=	SEQUENCE (SIZE (1..maxRL)) OF
										DL-InformationPerRL-r12

DL-InformationPerRL-List-r13 ::=	SEQUENCE (SIZE (1..maxRL)) OF
										DL-InformationPerRL-r13

DL-InformationPerRL-ListPostFDD ::=	SEQUENCE (SIZE (1..maxRL)) OF
										DL-InformationPerRL-PostFDD

DL-InformationPerRL-PostFDD ::=		SEQUENCE {
			primaryCPICH-Info					PrimaryCPICH-Info,
	dl-DPCH-InfoPerRL					DL-DPCH-InfoPerRL-PostFDD
}

DL-InformationPerRL-PostTDD ::=		SEQUENCE {
	primaryCCPCH-Info					PrimaryCCPCH-InfoPost,
	dl-DPCH-InfoPerRL					DL-DPCH-InfoPerRL-PostTDD
}

DL-InformationPerRL-PostTDD-LCR-r4 ::=	SEQUENCE {
	primaryCCPCH-Info					PrimaryCCPCH-InfoPostTDD-LCR-r4,
	dl-DPCH-InfoPerRL					DL-DPCH-InfoPerRL-PostTDD-LCR-r4
}

--for 1.28Mcps TDD Multi-Carrier
DL-MultiCarrier-Information ::=		SEQUENCE {
	tsn-Length							ENUMERATED { tsn-6bits, tsn-9bits }		OPTIONAL,
	multiCarrierNumber					INTEGER (1..maxTDD128Carrier)			OPTIONAL,
	dl-HSPDSCH-MultiCarrier-Information	DL-HSPDSCH-MultiCarrier-Information		OPTIONAL
}

DL-PDSCH-Information ::=			SEQUENCE {
	-- dummy1 and dummy 2 are not used in this version of specification, it should
	-- not be sent and if received it should be ignored.
	dummy1								PDSCH-SHO-DCH-Info					OPTIONAL,
	dummy2								PDSCH-CodeMapping					OPTIONAL
}

Dl-rate-matching-restriction ::=	SEQUENCE {
	restrictedTrCH-InfoList				RestrictedTrCH-InfoList				OPTIONAL
}

DL-SecondaryCellInfoFDD ::=			CHOICE {
	continue							NULL,
	newConfiguration					SEQUENCE {
		new-H-RNTI							H-RNTI,
		dl-64QAM-Configured					ENUMERATED { true }				OPTIONAL,
		hs-DSCH-TBSizeTable					HS-DSCH-TBSizeTable				OPTIONAL,
		primaryCPICH-Info					PrimaryCPICH-Info,
		dl-ScramblingCode					SecondaryScramblingCode			OPTIONAL,
		hS-SCCHChannelisationCodeInfo		SEQUENCE (SIZE (1..maxHSSCCHs)) OF
												HS-SCCH-Codes,
		measurementPowerOffset				MeasurementPowerOffset,
		uarfcn-DL							UARFCN
	}
}

DL-SecondaryCellInfoFDD-v890ext ::=	SEQUENCE {
	differentTxModeFromServingHS-DSCHCell			ENUMERATED { different }		OPTIONAL
}

DL-SecondaryCellInfoFDD-r9 ::=		SEQUENCE {
	configurationInfo					CHOICE {
		continue							NULL,
		newConfiguration					SEQUENCE {
			new-H-RNTI							H-RNTI,
			dl-64QAM-Configured					ENUMERATED { true }				OPTIONAL,
			hs-DSCH-TBSizeTable					HS-DSCH-TBSizeTable				OPTIONAL,
			primaryCPICH-Info					PrimaryCPICH-Info,
			dl-ScramblingCode					SecondaryScramblingCode			OPTIONAL,
			hS-SCCHChannelisationCodeInfo		SEQUENCE (SIZE (1..maxHSSCCHs)) OF
													HS-SCCH-Codes,
			measurementPowerOffset				MeasurementPowerOffset,
			uarfcn-DL							UARFCN,
			differentTxModeFromServingHS-DSCHCell	ENUMERATED { different }	OPTIONAL
		}
	},
	secondaryCellMIMOparameters			SecondaryCellMIMOparametersFDD	OPTIONAL
}

DL-SecondaryCellInfoFDD-r10 ::=		SEQUENCE {
	configurationInfo					CHOICE {
		continue							NULL,
		newConfiguration					SEQUENCE {
			new-H-RNTI							H-RNTI,
			dl-64QAM-Configured					ENUMERATED { true }				OPTIONAL,
			hs-DSCH-TBSizeTable					HS-DSCH-TBSizeTable				OPTIONAL,
			primaryCPICH-Info					PrimaryCPICH-Info,
			dl-ScramblingCode					SecondaryScramblingCode			OPTIONAL,
			hS-SCCHChannelisationCodeInfo		SEQUENCE (SIZE (1..maxHSSCCHs)) OF
													HS-SCCH-Codes,
			measurementPowerOffset				MeasurementPowerOffset,
			uarfcn-DL							UARFCN,
			differentTxModeFromServingHS-DSCHCell	ENUMERATED { different }	OPTIONAL
		}
	},
	secondaryCellMIMOparameters			SecondaryCellMIMOparametersFDD-r10	OPTIONAL
}

DL-SecondaryCellInfoFDD-r11 ::=		SEQUENCE {
	configurationInfo					CHOICE {
		continue							NULL,
		newConfiguration					SEQUENCE {
			new-H-RNTI							H-RNTI,
			dl-64QAM-Configured					ENUMERATED { true }				OPTIONAL,
			hs-DSCH-TBSizeTable					HS-DSCH-TBSizeTable				OPTIONAL,
			primaryCPICH-Info					PrimaryCPICH-Info,
			dl-ScramblingCode					SecondaryScramblingCode			OPTIONAL,
			hS-SCCHChannelisationCodeInfo		SEQUENCE (SIZE (1..maxHSSCCHs)) OF
													HS-SCCH-Codes,
			measurementPowerOffset				MeasurementPowerOffset,
			measurementPowerOffset1				MeasurementPowerOffset			OPTIONAL,
			uarfcn-DL							UARFCN,
			differentTxModeFromServingHS-DSCHCell	ENUMERATED { different }	OPTIONAL,
			multiflowConfigurationInfo			MultiflowConfigurationInfo		OPTIONAL
		}
	},
	secondaryCellMIMOparameters			SecondaryCellMIMOparametersFDD-r10	OPTIONAL,
	secondaryCell4x4MIMOparameters		SecondaryCell4x4MIMOparametersFDD	OPTIONAL
}

DL-SecondaryCellInfoFDD-HandoverToUtran ::=		SEQUENCE {
	configurationInfo					CHOICE {
		continue							NULL,
		newConfiguration					SEQUENCE {
			new-H-RNTI							H-RNTI,
			primaryCPICH-Info					PrimaryCPICH-Info,
			dl-ScramblingCode					SecondaryScramblingCode			OPTIONAL,
			hS-SCCHChannelisationCodeInfo		SEQUENCE (SIZE (1..maxHSSCCHs)) OF
													HS-SCCH-Codes,
			measurementPowerOffset				MeasurementPowerOffset,
			uarfcn-DL							UARFCN,
			differentTxModeFromServingHS-DSCHCell	ENUMERATED { different }	OPTIONAL
		}
	}
}

DL-TPC-PowerOffsetPerRL ::=		SEQUENCE {
		powerOffsetTPC-pdpdch				PowerOffsetTPC-pdpdch			OPTIONAL
}

-- NOTE: The radio links in the following list have a one-to-one mapping with the
-- radio links in the message.
DL-TPC-PowerOffsetPerRL-List ::=	SEQUENCE (SIZE (1..maxRL)) OF
										DL-TPC-PowerOffsetPerRL

DL-TS-ChannelisationCode ::=		ENUMERATED {
										cc16-1, cc16-2, cc16-3, cc16-4,
										cc16-5, cc16-6, cc16-7, cc16-8,
										cc16-9, cc16-10, cc16-11, cc16-12,
										cc16-13, cc16-14, cc16-15, cc16-16 }

DL-TS-ChannelisationCode-VHCR ::=	ENUMERATED {
										cc32-1, cc32-2, cc32-3, cc32-4,
										cc132-5, cc32-6, cc32-7, cc32-8,
										cc32-9, cc32-10, cc32-11, cc32-12,
										cc32-13, cc32-14, cc32-15, cc32-16,
										cc32-17, cc32-18, cc32-19, cc32-20,
										cc32-21, cc32-22, cc32-23, cc32-24,
										cc32-25, cc32-26, cc32-27, cc32-28,
										cc32-29, cc32-30, cc32-31, cc32-32 }

DL-TS-ChannelisationCodesShort ::=	SEQUENCE {
	codesRepresentation					CHOICE {
		consecutive							SEQUENCE {
			firstChannelisationCode				DL-TS-ChannelisationCode,
			lastChannelisationCode				DL-TS-ChannelisationCode
		},
		bitmap								BIT STRING {
												chCode16-SF16(0),
												chCode15-SF16(1),
												chCode14-SF16(2),
												chCode13-SF16(3),
												chCode12-SF16(4),
												chCode11-SF16(5),
												chCode10-SF16(6),
												chCode9-SF16(7),
												chCode8-SF16(8),
												chCode7-SF16(9),
												chCode6-SF16(10),
												chCode5-SF16(11),
												chCode4-SF16(12),
												chCode3-SF16(13),
												chCode2-SF16(14),
												chCode1-SF16(15)
												} 	(SIZE (16))
	}
}

DL-TS-ChannelisationCodesShort-VHCR ::=	SEQUENCE {
	codesRepresentation					CHOICE {
		consecutive							SEQUENCE {
			firstChannelisationCode				DL-TS-ChannelisationCode-VHCR,
			lastChannelisationCode				DL-TS-ChannelisationCode-VHCR
		},
		bitmap								BIT STRING {
												chCode32-SF32(0),
												chCode31-SF32(1),
												chCode30-SF32(2),
												chCode29-SF32(3),
												chCode28-SF32(4),
												chCode27-SF32(5),
												chCode26-SF32(6),
												chCode25-SF32(7),
												chCode24-SF32(8),
												chCode23-SF32(9),
												chCode22-SF32(10),
												chCode21-SF32(11),
												chCode20-SF32(12),
												chCode19-SF32(13),
												chCode18-SF32(14),
												chCode17-SF32(15),
												chCode16-SF32(16),
												chCode15-SF32(17),
												chCode14-SF32(18),
												chCode13-SF32(19),
												chCode12-SF32(20),
												chCode11-SF32(21),
												chCode10-SF32(22),
												chCode9-SF32(23),
												chCode8-SF32(24),
												chCode7-SF32(25),
												chCode6-SF32(26),
												chCode5-SF32(27),
												chCode4-SF32(28),
												chCode3-SF32(29),
												chCode2-SF32(30),
												chCode1-SF32(31)
												} 	(SIZE (32))
	}
}

DL-ChannelCodes-MBSFN-IMB384 ::=	SEQUENCE {
	firstChannelisationCode				INTEGER (1..15),
	lastChannelisationCode				INTEGER (1..15)						OPTIONAL
}

DLUL-HSPA-Information-r8 ::=			SEQUENCE {
	ul-EDCH-Information						UL-EDCH-Information-r8,
	dl-CommonInformation					DL-CommonInformation-r8,
	dl-InformationPerRL-List				DL-InformationPerRL-List-r7,
	dl-HSPDSCH-Information					DL-HSPDSCH-Information-r8
}

DLUL-HSPA-Information-r9 ::=			SEQUENCE {
	ul-EDCH-Information						UL-EDCH-Information-r9,
	dl-CommonInformation					DL-CommonInformation-r8,
	dl-InformationPerRL-List				DL-InformationPerRL-List-r7,
	dl-HSPDSCH-Information					DL-HSPDSCH-Information-r9
}

DLUL-HSPA-Information-r10 ::=			SEQUENCE {
	ul-EDCH-Information						UL-EDCH-Information-r9,
	dl-CommonInformation					DL-CommonInformation-r10,
	dl-InformationPerRL-List				DL-InformationPerRL-List-r7,
	dl-HSPDSCH-Information					DL-HSPDSCH-Information-r9
}

DownlinkAdditionalTimeslots ::=		SEQUENCE {
	parameters							CHOICE {
		sameAsLast							SEQUENCE {
			timeslotNumber						TimeslotNumber
		},
		newParameters						SEQUENCE {
			individualTimeslotInfo				IndividualTimeslotInfo,
			dl-TS-ChannelisationCodesShort		DL-TS-ChannelisationCodesShort
		}
	}
}

DownlinkAdditionalTimeslots-VHCR ::= SEQUENCE {
	parameters							CHOICE {
		sameAsLast							SEQUENCE {
			timeslotNumber						TimeslotNumber
		},
		newParameters						SEQUENCE {
			individualTimeslotInfo				IndividualTimeslotInfo-VHCR,
			dl-TS-ChannelisationCodesShort		DL-TS-ChannelisationCodesShort-VHCR
		}
	}
}

DownlinkAdditionalTimeslots-LCR-r4 ::=	SEQUENCE {
	parameters							CHOICE {
		sameAsLast							SEQUENCE {
			timeslotNumber						TimeslotNumber-LCR-r4
		},
		newParameters						SEQUENCE {
			individualTimeslotInfo				IndividualTimeslotInfo-LCR-r4,
			dl-TS-ChannelisationCodesShort		DL-TS-ChannelisationCodesShort
		}
	}
}

DownlinkAdditionalTimeslots-r7 ::=	SEQUENCE {
	parameters							CHOICE {
		sameAsLast							SEQUENCE {
			timeslotNumber						TimeslotNumber
		},
		newParameters						SEQUENCE {
			individualTimeslotInfo				IndividualTimeslotInfo-r7,
			dl-TS-ChannelisationCodesShort		DL-TS-ChannelisationCodesShort
		}
	}
}

DownlinkTimeslotsCodes ::=		SEQUENCE {
	firstIndividualTimeslotInfo			IndividualTimeslotInfo,
	dl-TS-ChannelisationCodesShort		DL-TS-ChannelisationCodesShort,
	moreTimeslots						CHOICE {
		noMore								NULL,
		additionalTimeslots					CHOICE {
			consecutive							INTEGER (1..maxTS-1),
			timeslotList						SEQUENCE (SIZE (1..maxTS-1)) OF
													DownlinkAdditionalTimeslots
		}
	}
}

DownlinkTimeslotsCodes-VHCR ::=		SEQUENCE {
	firstIndividualTimeslotInfo			IndividualTimeslotInfo-VHCR,
	dl-TS-ChannelisationCodesShort		DL-TS-ChannelisationCodesShort-VHCR,
	moreTimeslots						CHOICE {
		noMore								NULL,
		additionalTimeslots					CHOICE {
			consecutive							INTEGER (1..maxTS-1),
			timeslotList						SEQUENCE (SIZE (1..maxTS-1)) OF
													DownlinkAdditionalTimeslots-VHCR
		}
	}
}

DownlinkTimeslotsCodes-LCR-r4 ::=	SEQUENCE {
	firstIndividualTimeslotInfo			IndividualTimeslotInfo-LCR-r4,
	dl-TS-ChannelisationCodesShort		DL-TS-ChannelisationCodesShort,
	moreTimeslots						CHOICE {
		noMore								NULL,
		additionalTimeslots					CHOICE {
			consecutive							INTEGER (1..maxTS-LCR-1),
			timeslotList						SEQUENCE (SIZE (1..maxTS-LCR-1)) OF
													DownlinkAdditionalTimeslots-LCR-r4
		}
	}
}
DownlinkTimeslotsCodes-r7 ::=		SEQUENCE {
	firstIndividualTimeslotInfo			IndividualTimeslotInfo-r7,
	dl-TS-ChannelisationCodesShort		DL-TS-ChannelisationCodesShort,
	moreTimeslots						CHOICE {
		noMore								NULL,
		additionalTimeslots					CHOICE {
			consecutive							INTEGER (1..maxTS-1),
			timeslotList						SEQUENCE (SIZE (1..maxTS-1)) OF
													DownlinkAdditionalTimeslots-r7
		}
	}
}

DPC-Mode ::=						ENUMERATED {
										singleTPC,
										tpcTripletInSoft }

DPCCH2Info ::=	SEQUENCE {
	dpcch2TxPowerOffset			Dpcch2TxPowerOffset
}

DPCCH2InfoFDD ::=	SEQUENCE {
	configurationInfo			CHOICE {
		continue					NULL,
		newConfiguration			SEQUENCE {
			dpcch2Info					DPCCH2Info									OPTIONAL,
			f-dpchInfo					F-DPCHInfo									OPTIONAL,
			extended-E-DPCCH-DPCCHPO	Extended-E-DPCCH-DPCCH-PowerOffset			OPTIONAL,
			designatedNonServingHS-DSCHCellInfo	DesignatedNonServingHS-DSCHCellInfo	OPTIONAL
		}
	}
}

Dpcch2TxPowerOffset ::=				INTEGER (0..20)

-- Actual value DPCCH-PowerOffset = IE value * 2
DPCCH-PowerOffset ::=				INTEGER (-82..-3)

-- Actual value DPCCH-PowerOffset2 = 2 + (IE value * 4)
DPCCH-PowerOffset2 ::=				INTEGER (-28..-13)

DPCH-CompressedModeInfo ::=			SEQUENCE {
	tgp-SequenceList					TGP-SequenceList
}

DPCH-CompressedModeInfo-r8 ::=		SEQUENCE {
	tgp-SequenceList					TGP-SequenceList-r8
}

DPCH-CompressedModeInfo-r10 ::=		SEQUENCE {
	tgp-SequenceList					TGP-SequenceList-r10
}

DPCH-CompressedModeStatusInfo ::=	SEQUENCE {
	tgps-Reconfiguration-CFN			TGPS-Reconfiguration-CFN,
	tgp-SequenceShortList					SEQUENCE (SIZE (1..maxTGPS)) OF
											TGP-SequenceShort
}

DPCH-CompressedModeStatusInfo-r10 ::=	SEQUENCE {
	tgps-Reconfiguration-CFN			TGPS-Reconfiguration-CFN,
	tgp-SequenceShortList				SEQUENCE (SIZE (1..maxTGPS)) OF
										TGP-SequenceShort-r10
}

-- Actual value DPCH-FrameOffset = IE value * 256
DPCH-FrameOffset ::=				INTEGER (0..149)

FDPCH-SlotFormat ::=				INTEGER (0..9)

UE-DRX-Cycle-InactivityThreshold ::= ENUMERATED {
										sub-frames-0,
										sub-frames-1,
										sub-frames-2,
										sub-frames-4,
										sub-frames-8,
										sub-frames-16,
										sub-frames-32,
										sub-frames-64,
										sub-frames-128,
										sub-frames-256,
										sub-frames-512,
										spare5,
										spare4,
										spare3,
										spare2,
										spare1 }

DRX-Info ::=						SEQUENCE {
	ue-drx-Cycle						UE-DRX-Cycle,
	ue-drx-Cycle-InactivityThreshold	UE-DRX-Cycle-InactivityThreshold,
	ue-GrantMonitoring-InactivityThreshold
										UE-GrantMonitoring-InactivityThreshold,
	ue-drx-GrantMonitoring				BOOLEAN
}

DRX-Info-r12 ::=					SEQUENCE {
	ue-drx-Cycle						UE-DRX-Cycle,
	ue-drx-Cycle2						UE-DRX-Cycle2						OPTIONAL,
	ue-drx-Cycle-InactivityThreshold	UE-DRX-Cycle-InactivityThreshold,
	ue-drx-Cycle2-InactivityThreshold	UE-DRX-Cycle-InactivityThreshold	OPTIONAL,
	ue-GrantMonitoring-InactivityThreshold
										UE-GrantMonitoring-InactivityThreshold,
	ue-drx-GrantMonitoring				BOOLEAN
}

DSCH-Mapping ::=					SEQUENCE {
	maxTFCI-Field2Value					MaxTFCI-Field2Value,
	spreadingFactor						SF-PDSCH,
	codeNumber							CodeNumberDSCH,
	multiCodeInfo						MultiCodeInfo
}

DSCH-MappingList ::=				SEQUENCE (SIZE (1..maxPDSCH-TFCIgroups)) OF
										DSCH-Mapping

DSCH-RadioLinkIdentifier ::=		INTEGER (0..511)

DSCH-TransportChannelsInfo ::=		SEQUENCE (SIZE (1..maxTrCH)) OF
										SEQUENCE {
	dsch-transport-channel-identity			TransportChannelIdentity,
	dsch-TFS								TransportFormatSet
}

DTX-DRX-Info-r7 ::=					SEQUENCE {
	dtx-Info							DTX-Info							OPTIONAL,
	drx-Info							DRX-Info							OPTIONAL,
	uplink-DPCCHSlotFormatInformation	Uplink-DPCCH-Slot-Format-Information
}

DTX-DRX-Info-r12 ::=					SEQUENCE {
	dtx-Info							DTX-Info							OPTIONAL,
	dtx-Info-SecondaryUplinkFrequency	DTX-Info-SecondaryUplinkFrequency	OPTIONAL,
	drx-Info							DRX-Info-r12						OPTIONAL,
	uplink-DPCCHSlotFormatInformation	Uplink-DPCCH-Slot-Format-Information
}

DTX-E-DCH-TTI-10ms ::=				SEQUENCE {
	ue-dtx-Cycle1-10ms					UE-DTX-Cycle1-10ms,
	ue-dtx-Cycle2-10ms					UE-DTX-Cycle2-10ms,
	mac-dtx-Cycle-10ms					MAC-DTX-Cycle-10ms
}

DTX-E-DCH-TTI-2ms ::=				SEQUENCE {
	ue-dtx-Cycle1-2ms					UE-DTX-Cycle1-2ms,
	ue-dtx-Cycle2-2ms					UE-DTX-Cycle2-2ms,
	mac-dtx-Cycle-2ms					MAC-DTX-Cycle-2ms
}

DTX-Info ::=						SEQUENCE {
	e-dch-TTI-Length					CHOICE {
		dtx-e-dch-TTI-10ms					DTX-E-DCH-TTI-10ms,
		dtx-e-dch-TTI-2ms					DTX-E-DCH-TTI-2ms
	},
	ue-dtx-cycle2InactivityThreshold	UE-DTX-Cycle2InactivityThreshold,
	ue-dtx-cycle2DefaultSG				INTEGER (0..38)						OPTIONAL,
	-- if ue-dtx-long-preamble-length is not present, the value is '2 slots'
	ue-dtx-long-preamble-length			UE-DTX-long-preamble-length			OPTIONAL,
	mac-InactivityThreshold				MAC-InactivityThreshold,
	cqi-dtx-Timer						CQI-DTX-Timer,
	ue-dpcch-Burst1						UE-DPCCH-Burst,
	ue-dpcch-Burst2						UE-DPCCH-Burst
}

DTX-Info-SecondaryUplinkFrequency ::=	SEQUENCE {
	e-dch-TTI-Length					CHOICE {
		dtx-e-dch-TTI-10ms					NULL,
		dtx-e-dch-TTI-2ms					SEQUENCE {
			ue-dtx-Cycle1-2ms-Secondary				UE-DTX-Cycle1-2ms					OPTIONAL,
			ue-dtx-Cycle2-2ms-Secondary				UE-DTX-Cycle2-2ms-Secondary		}
	},
	ue-dtx-cycle2InactivityThreshold-Secondary		UE-DTX-Cycle2InactivityThreshold	OPTIONAL,
	-- if ue-dtx-long-preamble-length is not present, the value is '2 slots'
	ue-dtx-long-preamble-length-Secondary			UE-DTX-long-preamble-length			OPTIONAL,
	ue-dpcch-Burst1-Secondary						UE-DPCCH-Burst						OPTIONAL,
	ue-dpcch-Burst2-Secondary						UE-DPCCH-Burst						OPTIONAL
}

DurationTimeInfo ::=				INTEGER (1..4096)

DynamicPersistenceLevel ::=			INTEGER (1..8)

DynamicPersistenceLevelList ::=		SEQUENCE (SIZE (1..maxPRACH)) OF
										DynamicPersistenceLevel

DynamicPersistenceLevelTF-List ::= SEQUENCE (SIZE (1..maxTF-CPCH)) OF
										DynamicPersistenceLevel

DynamicTFInformationCCCH ::=		SEQUENCE {
	octetModeRLC-SizeInfoType2			OctetModeRLC-SizeInfoType2
}

E-AGCH-ChannelisationCode ::=		INTEGER (0..255)

E-AGCH-DRX-Info-TDD128 ::=			SEQUENCE {
	e-AGCH-DRX-InfoType					CHOICE {
		sameAsHS-SCCH						NULL,
		e-AGCH-DRX-Parameters				SEQUENCE {
			e-AGCH-DRX-Cycle					ControlChannelDRXCycle-TDD128,
			e-AGCH-InactivityMonitorThreshold	E-AGCH-InactivityMonitorThreshold-TDD128
																						OPTIONAL,
			e-AGCH-DRX-Offset 					INTEGER (0..63)
		}
	}
}

E-AGCH-InactivityMonitorThreshold-TDD128 ::= ENUMERATED {
										radio-frames-0, radio-frames-1, radio-frames-2,
										radio-frames-4, radio-frames-8, radio-frames-16,
										radio-frames-32, radio-frames-64, radio-frames-128,
										radio-frames-256, radio-frames-512,
										spare5, spare4, spare3, spare2, infinity }

E-AGCH-Individual ::=				SEQUENCE {
	tS-number							INTEGER (0..14),
	channelisation-code					DL-TS-ChannelisationCode,
	midambleShiftAndBurstType			MidambleShiftAndBurstType-EDCH
}

E-AGCH-Individual-VHCR ::=			SEQUENCE {
	tS-number							INTEGER (0..14),
	channelisation-code					DL-TS-ChannelisationCode-VHCR,
	midambleShiftAndBurstType			MidambleShiftAndBurstType-EDCH
}

E-AGCH-Individual-LCR ::=			SEQUENCE {
	timeslotNumber						TimeslotNumber-LCR-r4,
	firstChannelisationCode				HS-ChannelisationCode-LCR,
	secondChannelisationCode			HS-ChannelisationCode-LCR,
	midambleAllocationMode				CHOICE {
		defaultMidamble						NULL,
		commonMidamble						NULL,
		ueSpecificMidamble					INTEGER (0..15)
	},
	-- Actual value midambleConfiguration = IE value * 2
	midambleConfiguration				INTEGER (1..8)
}

E-AGCH-Information ::=				SEQUENCE {
	e-AGCH-ChannelisationCode			E-AGCH-ChannelisationCode
}

E-AGCH-Information-r7 ::=			SEQUENCE {
	modeSpecific						CHOICE {
		fdd									SEQUENCE {
			e-AGCH-ChannelisationCode			E-AGCH-ChannelisationCode
			},
		tdd									CHOICE {
			tdd384								SEQUENCE {
				long-Term-Grant-Indicator			BOOLEAN		OPTIONAL,
				length-of-TTRI-field				INTEGER (1..12),
				e-AGCH-Set-Config					E-AGCH-Set-Config,
				e-AGCH-BLER-Target					Bler-Target
			},
			tdd768								SEQUENCE {
				long-Term-Grant-Indicator			BOOLEAN		OPTIONAL,
				length-of-TTRI-field				INTEGER (1..12),
				e-AGCH-Set-Config					E-AGCH-Set-Config-VHCR,
				e-AGCH-BLER-Target					Bler-Target
			},
			tdd128								SEQUENCE {
				rdi-Indicator						BOOLEAN,
				tpc-StepSize						TPC-StepSizeTDD,
				e-AGCH-Set-Config					E-AGCH-Set-Config-LCR,
				e-AGCH-BLER-Target					Bler-Target
			}
		}
	}
}

E-AGCH-Information-r8 ::=			SEQUENCE {
	modeSpecific						CHOICE {
		fdd									SEQUENCE {
			e-AGCH-ChannelisationCode			E-AGCH-ChannelisationCode
			},
		tdd									CHOICE {
			tdd384								SEQUENCE {
				long-Term-Grant-Indicator			BOOLEAN							OPTIONAL,
				length-of-TTRI-field				INTEGER (1..12),
				e-AGCH-Set-Config					E-AGCH-Set-Config,
				e-AGCH-BLER-Target					Bler-Target
			},
			tdd768								SEQUENCE {
				long-Term-Grant-Indicator			BOOLEAN							OPTIONAL,
				length-of-TTRI-field				INTEGER (1..12),
				e-AGCH-Set-Config					E-AGCH-Set-Config-VHCR,
				e-AGCH-BLER-Target					Bler-Target
			},
			tdd128								SEQUENCE {
				rdi-Indicator						BOOLEAN,
				tpc-StepSize						TPC-StepSizeTDD,
				e-AGCH-Set-Config					E-AGCH-Set-Config-LCR,
				e-AGCH-BLER-Target					Bler-Target,
				e-AGCH-InactivityMonitorThreshold	E-AGCH-InactivityMonitorThreshold-TDD128
																							OPTIONAL
			}
		}
	}
}

E-AGCH-Information-TDD128 ::=		SEQUENCE {
	rdi-Indicator						BOOLEAN,
	tpc-StepSize						TPC-StepSizeTDD,
	e-AGCH-Set-Config					E-AGCH-Set-Config-LCR,
	e-AGCH-BLER-Target					Bler-Target
}

E-AGCH-Set-Config ::=				SEQUENCE (SIZE (1..maxNumE-AGCH)) OF
										E-AGCH-Individual

E-AGCH-Set-Config-VHCR ::=			SEQUENCE (SIZE (1..maxNumE-AGCH)) OF
										E-AGCH-Individual-VHCR

E-AGCH-Set-Config-LCR ::=			SEQUENCE (SIZE (1..maxNumE-AGCH)) OF
										E-AGCH-Individual-LCR

E-ROCH-ChannelisationCode ::=		INTEGER (0..255)

E-ROCH-Information ::=	SEQUENCE {
	e-ROCH-ChannelisationCode			E-ROCH-ChannelisationCode,
	e-roch-e-rnti							E-RNTI
}

E-DCH-MinimumSet-E-TFCI ::=			INTEGER (0..127)

E-DCH-ReconfigurationInfo ::=	SEQUENCE {
	e-DCH-RL-InfoNewServingCell			E-DCH-RL-InfoNewServingCell				OPTIONAL,
	e-DCH-RL-InfoOtherCellList			SEQUENCE (SIZE (1..maxEDCHRL)) OF
											E-DCH-RL-InfoOtherCell				OPTIONAL
}

E-DCH-ReconfigurationInfo-r7 ::=	SEQUENCE {
	e-DCH-RL-InfoNewServingCell			E-DCH-RL-InfoNewServingCell-r7			OPTIONAL,
	e-DCH-RL-InfoOtherCellList			SEQUENCE (SIZE (1..maxEDCHRL)) OF
											E-DCH-RL-InfoOtherCell				OPTIONAL
}

E-DCH-ReconfigurationInfo-r11 ::=	SEQUENCE {
	e-DCH-RL-InfoNewServingCell			E-DCH-RL-InfoNewServingCell-r11			OPTIONAL,
	e-DCH-RL-InfoOtherCellList			SEQUENCE (SIZE (1..maxEDCHRL)) OF
											E-DCH-RL-InfoOtherCell-r11			OPTIONAL
}

E-DCH-ReconfigurationInfo-SecULFrequency ::=		SEQUENCE {
	e-DCH-RL-InfoNewSecServingCell			E-DCH-RL-InfoNewSecServingCell			OPTIONAL,
	e-DCH-RL-InfoOtherCellList-SecULFreq	SEQUENCE (SIZE (1..maxEDCHRL)) OF
												E-DCH-RL-InfoOtherCell-SecULFreq		OPTIONAL
}

E-DCH-RL-InfoNewServingCell ::=		SEQUENCE {
	primaryCPICH-Info					PrimaryCPICH-Info,
	e-AGCH-Information					E-AGCH-Information,
	servingGrant						SEQUENCE {
		value								INTEGER (0..38)						OPTIONAL,
		primary-Secondary-GrantSelector		ENUMERATED { primary, secondary }
	}	OPTIONAL,
	e-DPCCH-DPCCH-PowerOffset			E-DPCCH-DPCCH-PowerOffset				OPTIONAL,
	reference-E-TFCIs					E-DPDCH-Reference-E-TFCIList			OPTIONAL,
	powerOffsetForSchedInfo				INTEGER (0..6)							OPTIONAL,
	threeIndexStepThreshold				INTEGER (0..37)							OPTIONAL,
	twoIndexStepThreshold				INTEGER (0..37)							OPTIONAL,
	e-HICH-Information					E-HICH-Information		OPTIONAL,
	e-RGCH-Info							CHOICE	{
		e-RGCH-Information					E-RGCH-Information,
		releaseIndicator					NULL
	}	OPTIONAL
}

E-DCH-RL-InfoNewServingCell-r7 ::=	SEQUENCE {
	primaryCPICH-Info					PrimaryCPICH-Info,
	e-AGCH-Information					E-AGCH-Information,
	servingGrant						SEQUENCE {
		value								INTEGER (0..38)						OPTIONAL,
		primary-Secondary-GrantSelector		ENUMERATED { primary, secondary }
	}	OPTIONAL,
	e-DPCCH-DPCCH-PowerOffset			E-DPCCH-DPCCH-PowerOffset				OPTIONAL,
	reference-E-TFCIs					E-DPDCH-Reference-E-TFCIList-r7			OPTIONAL,
	powerOffsetForSchedInfo				INTEGER (0..6)							OPTIONAL,
	threeIndexStepThreshold				INTEGER (0..37)							OPTIONAL,
	twoIndexStepThreshold				INTEGER (0..37)							OPTIONAL,
	e-HICH-Information					E-HICH-Information		OPTIONAL,
	e-RGCH-Info							CHOICE	{
		e-RGCH-Information					E-RGCH-Information,
		releaseIndicator					NULL
	}	OPTIONAL
}

E-DCH-RL-InfoNewServingCell-r11 ::=	SEQUENCE {
	primaryCPICH-Info					PrimaryCPICH-Info,
	e-AGCH-Information					E-AGCH-Information,
	e-ROCH-Information					E-ROCH-Information						OPTIONAL,
	servingGrant						SEQUENCE {
		value								INTEGER (0..38)						OPTIONAL,
		primary-Secondary-GrantSelector		ENUMERATED { primary, secondary }
	}	OPTIONAL,
	e-DPCCH-DPCCH-PowerOffset			E-DPCCH-DPCCH-PowerOffset				OPTIONAL,
	reference-E-TFCIs					E-DPDCH-Reference-E-TFCIList-r7			OPTIONAL,
	powerOffsetForSchedInfo				INTEGER (0..6)							OPTIONAL,
	threeIndexStepThreshold				INTEGER (0..37)							OPTIONAL,
	twoIndexStepThreshold				INTEGER (0..37)							OPTIONAL,
	e-HICH-Information					E-HICH-Information-r11					OPTIONAL,
	e-RGCH-Info							CHOICE	{
		e-RGCH-Information					E-RGCH-Information,
		releaseIndicator					NULL
	}	OPTIONAL
}

E-DCH-RL-InfoNewSecServingCell ::=	SEQUENCE {
	e-AGCH-Information					E-AGCH-Information,
	e-HICH-Information					E-HICH-Information		OPTIONAL,
	e-RGCH-Info							CHOICE	{
		e-RGCH-Information					E-RGCH-Information,
		releaseIndicator					NULL
	}	OPTIONAL
}

E-DCH-RL-InfoOtherCell ::=			SEQUENCE {
	primaryCPICH-Info					PrimaryCPICH-Info,
	e-HICH-Info							CHOICE {
		e-HICH-Information					E-HICH-Information,
		releaseIndicator					NULL
	}	OPTIONAL,
	e-RGCH-Info							CHOICE {
		e-RGCH-Information					E-RGCH-Information,
		releaseIndicator					NULL
	}	OPTIONAL
}

E-DCH-RL-InfoOtherCell-r11 ::=			SEQUENCE {
	primaryCPICH-Info					PrimaryCPICH-Info,
	e-HICH-Info							CHOICE {
		e-HICH-Information					E-HICH-Information-r11,
		releaseIndicator					NULL,
		secondaryReleaseIndicator			NULL
	}	OPTIONAL,
	e-RGCH-Info							CHOICE {
		e-RGCH-Information					E-RGCH-Information,
		releaseIndicator					NULL
	}	OPTIONAL
}

E-DCH-RL-InfoOtherCell-SecULFreq ::=	SEQUENCE {
	primaryCPICH-Info					PrimaryCPICH-Info,
	e-HICH-Information					E-HICH-Information		OPTIONAL,
	e-RGCH-Info							CHOICE	{
		e-RGCH-Information					E-RGCH-Information,
		releaseIndicator					NULL
	}	OPTIONAL
}

E-DCH-RL-InfoSameServingCell ::=	SEQUENCE {
	e-DPCCH-DPCCH-PowerOffset			E-DPCCH-DPCCH-PowerOffset				OPTIONAL,
	reference-E-TFCIs					E-DPDCH-Reference-E-TFCIList-r7			OPTIONAL
}

E-DCH-SPS-Information-TDD128 ::=	SEQUENCE {
	e-dch-SPS-Operation					CHOICE {
		continue							NULL,
		newOperation						E-DCH-SPS-NewOperation-TDD128
	}
}

E-DCH-SPS-NewOperation-TDD128 ::=	SEQUENCE {
	e-hich-Info							E-HICH-Information-For-SPS-TDD128,
	e-dch-TxPattern						E-DCH-TxPatternList-TDD128				OPTIONAL,
	initialSPSInfoForEDCH				SEQUENCE {
		n-E-UCCH							INTEGER (1..8),
		codeResourceInfo					UL-TS-ChannelisationCode,
		timeslotResourceRelatedInfo			BIT STRING (SIZE (5)),
		powerResourceRelatedInfo			INTEGER (1..32),
		activationTime						ActivationTime,
		subframeNum							INTEGER (0..1),
		initialTxPatternIndex				INTEGER (0..maxEDCHTxPattern-TDD128-1)
	}		OPTIONAL
}

E-DCH-TxPatternList-TDD128 ::=		SEQUENCE (SIZE (1..maxEDCHTxPattern-TDD128)) OF
										SEQUENCE {
	repetitionPeriodAndLength				RepetitionPeriodAndLengthForSPS
}

E-DPCCH-Info ::=					SEQUENCE {
	e-DPCCH-DPCCH-PowerOffset			E-DPCCH-DPCCH-PowerOffset,
	happyBit-DelayCondition				HappyBit-DelayCondition
}

E-DPCCH-Info-r7 ::=					SEQUENCE {
	e-DPCCH-DPCCH-PowerOffset			E-DPCCH-DPCCH-PowerOffset,
	happyBit-DelayCondition				HappyBit-DelayCondition,
	e-TFC-Boost-Info					E-TFC-Boost-Info-r7					OPTIONAL,
	e-DPDCH-PowerInterpolation			E-DPDCH-PowerInterpolation			OPTIONAL
}

E-DPCCH-DPCCH-PowerOffset ::=		INTEGER (0..8)

Extended-E-DPCCH-DPCCH-PowerOffset ::=		INTEGER (9..15)

E-DPDCH-Info ::=					SEQUENCE {
	e-TFCI-TableIndex					E-TFCI-TableIndex,
	e-DCH-MinimumSet-E-TFCI				E-DCH-MinimumSet-E-TFCI				OPTIONAL,
	reference-E-TFCIs					E-DPDCH-Reference-E-TFCIList,
	maxChannelisationCodes				E-DPDCH-MaxChannelisationCodes,
	pl-NonMax							E-DPDCH-PL-NonMax,
	schedulingInfoConfiguration			E-DPDCH-SchedulingInfoConfiguration,
	threeIndexStepThreshold				INTEGER (0..37)						OPTIONAL,
	twoIndexStepThreshold				INTEGER (0..37)						OPTIONAL
}

E-DPDCH-Info-r7 ::=					SEQUENCE {
	e-TFCI-TableIndex					E-TFCI-TableIndex,
	e-DCH-MinimumSet-E-TFCI				E-DCH-MinimumSet-E-TFCI				OPTIONAL,
	reference-E-TFCIs					E-DPDCH-Reference-E-TFCIList-r7,
	maxChannelisationCodes				E-DPDCH-MaxChannelisationCodes,
	pl-NonMax							E-DPDCH-PL-NonMax,
	schedulingInfoConfiguration			E-DPDCH-SchedulingInfoConfiguration,
	threeIndexStepThreshold				INTEGER (0..37)						OPTIONAL,
	twoIndexStepThreshold				INTEGER (0..37)						OPTIONAL
}

E-DPDCH-Info-r8 ::=					SEQUENCE {
	e-TFCI-TableIndex					E-TFCI-TableIndex,
	e-DCH-MinimumSet-E-TFCI				E-DCH-MinimumSet-E-TFCI				OPTIONAL,
	reference-E-TFCIs					E-DPDCH-Reference-E-TFCIList-r7,
	minReduced-E-DPDCH-GainFactor		MinReduced-E-DPDCH-GainFactor		OPTIONAL,
	maxChannelisationCodes				E-DPDCH-MaxChannelisationCodes,
	pl-NonMax							E-DPDCH-PL-NonMax,
	schedulingInfoConfiguration			E-DPDCH-SchedulingInfoConfiguration,
	threeIndexStepThreshold				INTEGER (0..37)						OPTIONAL,
	twoIndexStepThreshold				INTEGER (0..37)						OPTIONAL
}

E-DPDCH-PeriodicyOfSchedInfo ::=	ENUMERATED {
										everyEDCHTTI, ms4, ms10, ms20, ms50, ms100, ms200, ms500,
										ms1000 }

-- The actual value of E-DPDCH-PL-NonMax is: IE value * 0.04
E-DPDCH-PL-NonMax ::=				INTEGER (11..25)

E-DPDCH-PowerInterpolation ::=		BOOLEAN

E-DPDCH-Reference-E-TFCI ::=		SEQUENCE {
	reference-E-TFCI					INTEGER (0..127),
	reference-E-TFCI-PO					INTEGER (0..29)
}

E-DPDCH-Reference-E-TFCI-r7 ::=		SEQUENCE {
	reference-E-TFCI					INTEGER (0..127),
	reference-E-TFCI-PO-r7				INTEGER (0..31)
}

E-DPDCH-Reference-E-TFCIList ::=	SEQUENCE (SIZE (1..8)) OF E-DPDCH-Reference-E-TFCI

E-DPDCH-Reference-E-TFCIList-r7 ::=	SEQUENCE (SIZE (1..8)) OF E-DPDCH-Reference-E-TFCI-r7

E-DPDCH-SchedulingInfoConfiguration ::= SEQUENCE {
	periodicityOfSchedInfo-NoGrant		E-DPDCH-PeriodicyOfSchedInfo		OPTIONAL,
	periodicityOfSchedInfo-Grant		E-DPDCH-PeriodicyOfSchedInfo		OPTIONAL,
	powerOffsetForSchedInfo				INTEGER (0..6)
}

E-DPDCH-SchedulingTransmConfiguration ::= SEQUENCE {
	ms2-SchedTransmGrantHARQAlloc		BIT STRING (SIZE (8))				OPTIONAL,
	servingGrant						SEQUENCE {
		value								INTEGER (0..38),
		primary-Secondary-GrantSelector		ENUMERATED { primary, secondary }
	}		OPTIONAL
}

E-DPDCH-MaxChannelisationCodes ::=	ENUMERATED {
										sf256, sf128, sf64, sf32, sf16, sf8, sf4, sf4x2,
										sf2x2, sf4x2-and-sf2x2 }

E-HICH-ChannelisationCode ::=		INTEGER (0..127)

E-HICH-Information ::=				SEQUENCE {
	channelisationCode					E-HICH-ChannelisationCode,
	signatureSequence					E-HICH-RGCH-SignatureSequence
}

E-HICH-Information-r11 ::=				SEQUENCE {
	channelisationCode					E-HICH-ChannelisationCode,
	signatureSequence					E-HICH-RGCH-SignatureSequence,
	secondarySignatureSequence			E-HICH-RGCH-SignatureSequence			OPTIONAL
}

E-HICH-Information-CommonEdch ::=		SEQUENCE {
	channelisationCode					E-HICH-ChannelisationCode					OPTIONAL,
	signatureSequence					E-HICH-RGCH-SignatureSequence				OPTIONAL
}

E-HICH-Information-TDD384-768 ::=	SEQUENCE {
	n-E-HICH							INTEGER (4..44),
	tS-Number							INTEGER (0..14),
	modeSpecificInfo						CHOICE	{
		tdd384									DL-TS-ChannelisationCode,
		tdd768									DL-TS-ChannelisationCode-VHCR
	},
	burst-Type							ENUMERATED { type1, type2 },
	midamble-Allocation-Mode			ENUMERATED { default, common }
}

E-HICH-Information-LCR ::=			SEQUENCE {
	ei									INTEGER (0..3),
	timeslotNumber						TimeslotNumber-LCR-r4,
	channelisation-Code					HS-ChannelisationCode-LCR,
	midambleAllocationMode				CHOICE {
		defaultMidamble						NULL,
		ueSpecificMidamble					INTEGER (0..15)
	},
	-- Actual value midambleConfiguration = IE value * 2
	midambleConfiguration				INTEGER (1..8)
}

E-HICH-Information-TDD128 ::=		SEQUENCE {
	n-E-HICH							INTEGER (4..15),
	e-HICH-InfoList						E-HICH-Information-LCR-List
}

E-HICH-Information-LCR-List ::=		SEQUENCE (SIZE (1..maxNumE-HICH)) OF
										E-HICH-Information-LCR

E-HICH-RGCH-SignatureSequence ::=	INTEGER (0..39)

E-HICH-Information-For-SPS-TDD128 ::= SEQUENCE {
	configurationmode					CHOICE{
		implicit							SEQUENCE {
			ei									INTEGER (0..3)				OPTIONAL
		},
		explicit							SEQUENCE {
			timeslotNumber						TimeslotNumber-LCR-r4,
			channelisation-Code					HS-ChannelisationCode-LCR,
			midambleAllocationMode				CHOICE {
				defaultMidamble						NULL,
				ueSpecificMidamble					INTEGER (0..15)
			},
			-- Actual value midambleConfiguration = IE value * 2
			midambleConfiguration			INTEGER (1..8)
		}
	},
	signatureSequenceGroupIndex			INTEGER (0..19)
}


E-PUCH-Info ::=						SEQUENCE {
	e-TFCS-Info							E-TFCS-Info,
	modeSpecificInfo					CHOICE {
		tdd348-tdd768						SEQUENCE {
			noSlotsForTFCIandTPC				INTEGER (1..12),
			e-PUCH-ContantValue					INTEGER (-35..10),
			e-PUCH-TS-ConfigurationList			SEQUENCE (SIZE (1..maxTS-2)) OF E-PUCH-TS-Slots,
			e-PUCH-CodeHopping					BOOLEAN,
			e-PUCH-TPC-Step-Size				INTEGER (1..3),
			minimum-Allowed-Code-Rate			INTEGER (0..63),
			maximum-Allowed-Code-Rate			INTEGER (0..63)
		},
		tdd128								SEQUENCE {
			snpl-ReportType						ENUMERATED { type1, type2 }				OPTIONAL,
			prxdes-base							INTEGER (-112..-50),
			beaconPLEst							BOOLEAN									OPTIONAL,
			tpc-StepSize						TPC-StepSizeTDD,
			pebase-PowerControlGAP				PowerControlGAP							OPTIONAL,
			ul-SynchronisationParameters		UL-SynchronisationParameters-r4			OPTIONAL,
			e-PUCH-TS-ConfigurationList			SEQUENCE (SIZE (1..maxTS-LCR-1)) OF
													E-PUCH-TS-Slots-LCR,
			minimum-Allowed-Code-Rate			INTEGER (0..63),
			maximum-Allowed-Code-Rate			INTEGER (0..63),
			maximumNumOfRetransSchedInfo		INTEGER (0..15),
			retransTimerForSchedInfo			ENUMERATED { ms10, ms15, ms20, ms25, ms30, ms35,
													ms40, ms45, ms50, ms55, ms60, ms65, ms70, ms75,
													ms80, ms85, ms90, ms95, ms100, ms110, ms120,
													ms140, ms160, ms200, ms240,ms280, ms320, ms400,
													ms480, ms560 }
		}
	},
	-- For 3.84/7.68 TDD only, should be ignored for 1.28Mcps TDD mode
	powerOffsetForSchedInfo				INTEGER (0..6)									OPTIONAL
}

E-PUCH-Info-TDD128 ::=				SEQUENCE {
	e-TFCS-Info							E-TFCS-Info,
	snpl-ReportType						ENUMERATED { type1, type2 }					OPTIONAL,
	prxdes-base							INTEGER (-112..-50),
	beaconPLEst							BOOLEAN										OPTIONAL,
	tpc-StepSize						TPC-StepSizeTDD,
	pebase-PowerControlGAP				INTEGER (1..255)							OPTIONAL,
	ul-SynchronisationParameters		UL-SynchronisationParameters-r4				OPTIONAL,
	e-PUCH-TS-ConfigurationList			SEQUENCE (SIZE (1..maxTS-LCR-1)) OF
											E-PUCH-TS-Slots-LCR,
	minimum-Allowed-Code-Rate			INTEGER (0..63),
	maximum-Allowed-Code-Rate			INTEGER (0..63),
	maximumNumOfRetransSchedInfo		INTEGER (0..15),
	retransTimerForSchedInfo			ENUMERATED { ms10, ms15, ms20, ms25, ms30, ms35,
											ms40, ms45, ms50, ms55, ms60, ms65, ms70, ms75,
											ms80, ms85, ms90, ms95, ms100, ms110, ms120,
											ms140, ms160, ms200, ms240,ms280, ms320, ms400,
											ms480, ms560 },
	-- dummy is not used in this version of the specification, it should
	-- not be sent and if received it should be ignored.
	dummy								INTEGER (0..6)								OPTIONAL
}

E-PUCH-Info-MulticarrierEDCH-TDD128 ::=				SEQUENCE {
	e-PUCH-TS-ConfigurationList			SEQUENCE (SIZE (1..maxTS-LCR-1)) OF
											E-PUCH-TS-Slots-LCR
}

E-PUCH-TS-Slots ::=					SEQUENCE {
	ts-Number							INTEGER (0..14),
	midambleShiftAndBurstType			MidambleShiftAndBurstType-EDCH
}

E-PUCH-TS-Slots-LCR ::=				SEQUENCE {
	-- Note: For 1.28Mcps TDD operation, valid value for timeslotNumber is INTEGER (1..5)
	timeslotNumber						TimeslotNumber-LCR-r4,
	midambleAllocationMode				CHOICE {
		defaultMidamble						NULL,
		ueSpecificMidamble					INTEGER (0..15)
	},
	-- Actual value midambleConfiguration = IE value * 2
	midambleConfiguration				INTEGER (1..8)
}

E-RGCH-CombinationIndex ::=			INTEGER (0..5)

E-RGCH-Information ::=				SEQUENCE {
	signatureSequence					E-HICH-RGCH-SignatureSequence,
	rg-CombinationIndex					E-RGCH-CombinationIndex
}

E-RGCH-Information-CommonEdch ::=	SEQUENCE {
	signatureSequence					E-HICH-RGCH-SignatureSequence				OPTIONAL
}

E-RUCCH-AccessServiceClass ::=		PRACH-Partitioning-LCR-r4

E-RUCCH-Info ::=					SEQUENCE {
	modeSpecificInfo					CHOICE {
		tdd384-tdd768						SEQUENCE {
			e-RUCCH-ConstantValue				INTEGER (-35..10),
			e-RUCCH-PersistenceScalingFactor	PersistenceScalingFactor,
			t-RUCCH								ENUMERATED {ms40, ms80, ms120, ms160, ms200,
													ms240, ms280, ms320}				OPTIONAL,
			e-RUCCH-TS-Number					INTEGER (0..14)							OPTIONAL,
			e-RUCCH-Midamble					ENUMERATED {direct, direct-Inverted}	OPTIONAL,
			t-adv								ENUMERATED { sec1, sec2, sec4, sec8, sec16,
													sec32, sec128, infinity }			OPTIONAL,
			t-SCHED								ENUMERATED { zero, ms40, ms80, ms160, ms250,
													sec1, sec2, sec4 }					OPTIONAL,
			modeSpecificInfo					CHOICE {
				tdd384								CHOICE {
					sF16								SEQUENCE (SIZE (1..8)) OF SF16Codes,
					sF8									SEQUENCE (SIZE (1..8)) OF SF8Codes
					},
				tdd768							CHOICE {
					sF32								SEQUENCE (SIZE (1..16)) OF SF32Codes,
					sF816								SEQUENCE (SIZE (1..16)) OF SF16Codes2
				}
			}
		},
		tdd128								SEQUENCE {
			t-RUCCH								ENUMERATED { ms20, ms40, ms60, ms80, ms120,
													ms160, ms200, ms240, ms280, ms320,
													ms400, ms500, ms600, ms800, ms1000,
													ms2000 }							OPTIONAL,
			n-RUCCH								INTEGER (0..7)							OPTIONAL,
			t-WAIT								ENUMERATED { everyEDCHTTI, ms40, ms80, ms160,
													ms320, ms640, ms1000, ms2000 }		OPTIONAL,
			t-SI								ENUMERATED { everyEDCHTTI, ms20, ms40, ms60, ms80,
													ms160, ms200 }						OPTIONAL,
			extendedEstimationWindow			INTEGER (2..5)							OPTIONAL,
			e-RUCCH-AccessServiceClass			E-RUCCH-AccessServiceClass				OPTIONAL,
			e-RUCCH-PersistenceScalingFactor	PersistenceScalingFactorList			OPTIONAL,
			sync-UL-InfoForE-RUCCH				SYNC-UL-InfoForE-RUCCH					OPTIONAL,
			prach-information					PRACH-Information-LCR-List				OPTIONAL
		}
	}
}

E-RUCCH-Info-TDD128 ::=				SEQUENCE {
	t-RUCCH								ENUMERATED { ms20, ms40, ms60, ms80, ms120,
											ms160, ms200, ms240, ms280, ms320,
											ms400, ms500, ms600, ms800, ms1000,
											ms2000 }								OPTIONAL,
	n-RUCCH								INTEGER (0..7)								OPTIONAL,
	t-WAIT								ENUMERATED { everyEDCHTTI, ms40, ms80, ms160,
											ms320, ms640, ms1000, ms2000 }			OPTIONAL,
	t-SI								ENUMERATED { everyEDCHTTI, ms20, ms40, ms60, ms80,
											ms160, ms200 }							OPTIONAL,
	extendedEstimationWindow			INTEGER (2..5)								OPTIONAL,
	e-RUCCH-AccessServiceClass			E-RUCCH-AccessServiceClass					OPTIONAL,
	e-RUCCH-PersistenceScalingFactor	PersistenceScalingFactorList				OPTIONAL,
	sync-UL-InfoForE-RUCCH				SYNC-UL-InfoForE-RUCCH						OPTIONAL,
	prach-information					PRACH-Information-LCR-List					OPTIONAL
}

E-TFC-Boost-Info-r7 ::=			SEQUENCE {
	e-TFCI-Boost						INTEGER (0..127),
	delta-T2TP							INTEGER (0..6)						OPTIONAL
}

E-TFCI-TableIndex ::=				INTEGER (0..1)

E-TFCS-Info ::=						SEQUENCE {
	reference-Beta-QPSK-List			SEQUENCE (SIZE (1..8)) OF Reference-Beta-QPSK,
	reference-Beta-16QAM-List			SEQUENCE (SIZE (1..8)) OF Reference-Beta-16QAM
}

EARFCN ::=							INTEGER (0..65535)

EARFCNExtension ::=					INTEGER (65536..262143)

EARFCNExtension2 ::=				INTEGER (0..262143)

EARFCNRange ::= SEQUENCE {
-- If the IE earfcn is set to a value of 65535, then the EARFCN
--	value for that instance shall be read from the IE earfcnExt.
	earfcn							EARFCN,
	earfcnExt						EARFCNExtension					OPTIONAL
}

EnablingDelay ::=					ENUMERATED {
										radio-frames-0,
										radio-frames-1,
										radio-frames-2,
										radio-frames-4,
										radio-frames-8,
										radio-frames-16,
										radio-frames-32,
										radio-frames-64,
										radio-frames-128,
										spare7,
										spare6,
										spare5,
										spare4,
										spare3,
										spare2,
										spare1 }

EnablingDelay-TDD128 ::=			ENUMERATED {
										radio-frames-0, radio-frames-1, radio-frames-2,
										radio-frames-4, radio-frames-8, radio-frames-16,
										radio-frames-32, radio-frames-64, radio-frames-128,
										spare7, spare6, spare5, spare4, spare3, spare2,
										infinity }

EXT-UL-TimingAdvance ::=			SEQUENCE {
	modeSpecificInfo				CHOICE {
		tdd384							SEQUENCE {
			ex-ul-TimingAdvance			INTEGER (0..255)
		},
		tdd768							SEQUENCE {
			ex-ul-TimingAdvance			INTEGER (0..511)
		}
	}
}

F-DPCHInfo ::=			SEQUENCE {
	fdpch-SlotFormat					INTEGER (0..9)				OPTIONAL,
	codeNumber							INTEGER (0..255)			OPTIONAL,
	-- Actual value dl-FDPCH-TPCcommandErrorRate = IE value * 0.01
	dl-FDPCH-TPCcommandErrorRate		INTEGER (1..10)				OPTIONAL
}

FACH-PCH-Information ::=			SEQUENCE {
	transportFormatSet					TransportFormatSet,
	transportChannelIdentity			TransportChannelIdentity,
	ctch-Indicator						BOOLEAN
}

FACH-PCH-InformationList ::=		SEQUENCE (SIZE (1..maxFACHPCH)) OF
										FACH-PCH-Information

Fallback-R99-PRACH-info-IEs::=		SEQUENCE {
	cCCH-Fallback			BOOLEAN,
	dCCH-Fallback			BOOLEAN
}

Feedback-cycle ::=					ENUMERATED {
										fc0, fc2, fc4, fc8, fc10, fc20, fc40, fc80, fc160}

Feedback-cycle2 ::=					ENUMERATED {
										fc0, fc8, fc10, fc16,
										fc20, f32, fc40, f64,
										fc80, fc160, spare6, spare5,
										spare4, spare3, spare2, spare1}

Feedback-cycle-r7 ::=				ENUMERATED {
										fc0, fc2, fc4, fc8, fc10, fc20, fc40, fc80, fc160,
										fc16, fc32, fc64, spare4, spare3, spare2, spare1 }

FPACH-Info-r4 ::=						SEQUENCE {
	timeslot							TimeslotNumber-LCR-r4,
	channelisationCode					TDD-FPACH-CCode16-r4,
	midambleShiftAndBurstType			MidambleShiftAndBurstType-LCR-r4,
	wi									Wi-LCR
}

F-TPICH-InfoNewServingCell ::=	SEQUENCE {
	f-tpich-Information						F-TPICH-Information
}

F-TPICH-InfoOtherCell ::=			SEQUENCE {
	primaryCPICH-Info					PrimaryCPICH-Info,
	f-tpich-Info						CHOICE {
		f-tpich-Information				F-TPICH-Information,
		releaseIndicator					NULL
	}
}

F-TPICH-Information ::=		SEQUENCE {
	ftpich-SlotFormat					FTPICH-SlotFormat,
	ftpich-CodeNumber					INTEGER (0..255),
	ftpich-FrameOffset					FTPICH-FrameOffset
}

F-TPICH-ReconfigurationInfo ::=	SEQUENCE {
	f-tpich-InfoNewServingCell			F-TPICH-InfoNewServingCell				OPTIONAL,
	f-tpich-InfoOtherCellList			SEQUENCE (SIZE (1..maxRL)) OF
											F-TPICH-InfoOtherCell				OPTIONAL
}

-- Actual value FTPICH-FrameOffset = IE value * 256
FTPICH-FrameOffset ::=				INTEGER (0..149)

FTPICH-SlotFormat ::=				INTEGER (0..9)

FreqIndexListForEnhancedMeas ::=	SEQUENCE (SIZE (1..maxFreqMeasWithoutCM)) OF
										FrequencyIndexForEnhancedMeas

FreqIndexListForEnhancedMeas-r12 ::=	SEQUENCE (SIZE (1..maxFreqMeasWithoutCM)) OF
										FrequencyIndexForEnhancedMeas-r12

FrequencyInfo ::=					SEQUENCE {
	modeSpecificInfo					CHOICE {
		fdd									FrequencyInfoFDD,
		tdd									FrequencyInfoTDD	}
}

FrequencyInfoFDD ::=				SEQUENCE {
	uarfcn-UL							UARFCN				OPTIONAL,
	uarfcn-DL							UARFCN
}

FrequencyInfoTDD ::=				SEQUENCE {
	uarfcn-Nt							UARFCN
}

FrequencyIndexForEnhancedMeas ::=	INTEGER (0..maxCellMeas-1)

FrequencyIndexForEnhancedMeas-r12 ::=	INTEGER (0..maxCellMeas-ext-1)

HappyBit-DelayCondition ::=			ENUMERATED {
										ms2, ms10, ms20, ms50, ms100, ms200, ms500, ms1000 }

HARQ-Preamble-Mode ::=				INTEGER (0..1)

HS-ChannelisationCode-LCR ::=		ENUMERATED {
										cc16-1, cc16-2, cc16-3, cc16-4,
										cc16-5, cc16-6, cc16-7, cc16-8,
										cc16-9, cc16-10, cc16-11, cc16-12,
										cc16-13, cc16-14, cc16-15, cc16-16 }

HS-ChannelisationCodeSetInfo-LCR ::= SEQUENCE {
	startCode							HS-ChannelisationCode-LCR,
	stopCode							HS-ChannelisationCode-LCR
}

HS-DSCH-CommonSystemInformation ::=		SEQUENCE {
	ccch-MappingInfo						CommonRBMappingInfo,
	srb1-MappingInfo						CommonRBMappingInfo						OPTIONAL,
	common-MAC-ehs-ReorderingQueueList		Common-MAC-ehs-ReorderingQueueList,
	hs-scch-SystemInfo						HS-SCCH-SystemInfo,
	harq-SystemInfo							HARQ-Info,
	common-H-RNTI-information				SEQUENCE (SIZE (1..maxCommonHRNTI)) OF
												H-RNTI,
	bcchSpecific-H-RNTI						H-RNTI
}

HS-DSCH-CommonSystemInformation-TDD128 ::= SEQUENCE {
	ccch-MappingInfo						CommonRBMappingInfo,
	srb1-MappingInfo						CommonRBMappingInfo						OPTIONAL,
	common-MAC-ehs-ReorderingQueueList		Common-MAC-ehs-ReorderingQueueList,
	hs-scch-SystemInfo-tdd128				HS-SCCH-SystemInfo-TDD128,
	harq-SystemInfo							HARQ-Info,
	hs-pdsch-MidambleConfiguration			HS-PDSCH-Midamble-Configuration-TDD128,
	common-H-RNTI-information				SEQUENCE (SIZE (1..maxCommonHRNTI)) OF H-RNTI,
	bcchSpecific-H-RNTI						H-RNTI
}

HS-DSCH-DrxBurstFach ::=				ENUMERATED {
											f1, f2, f4, f8, f16, spare3, spare2, spare1 }

HS-DSCH-DrxCellfach-info ::=			SEQUENCE {
	t-321									T-321,
	hs-dsch-DrxCycleFach					HS-DSCH-DrxCycleFach,
	hs-dsch-DrxBurstFach					HS-DSCH-DrxBurstFach,
	drxInterruption-hs-dsch					BOOLEAN
}

HS-DSCH-DrxCellfach-info-TDD128 ::=		SEQUENCE {
	t-321									T-321,
	hs-dsch-DrxCycleFach					HS-DSCH-DrxCycleFach,
	hs-dsch-DrxBurstFach					HS-DSCH-DrxBurstFach
}

HS-DSCH-DrxCellfach-SecondDrx-info ::=	SEQUENCE {
	hs-dsch-SecondDrx-CycleFach		HS-DSCH-SecondDrx-CycleFach,
	drx-level							CHOICE	{
		one-level-DRX						SEQUENCE	{
			hs-dsch-Second-Rx-BurstFach				HS-DSCH-Second-Rx-BurstFach	OPTIONAL,
			t329										T-329							OPTIONAL
		},
		two-level-DRX						SEQUENCE	{
			t328									T-328								OPTIONAL,
			hs-dsch-First-Rx-BurstFach				HS-DSCH-First-Rx-BurstFach			OPTIONAL,
			hs-dsch-First-Drx-CycleFach				HS-DSCH-First-Drx-CycleFach	OPTIONAL,
			hs-dsch-Second-Rx-BurstFach				HS-DSCH-Second-Rx-BurstFach	OPTIONAL,
			t329									T-329								OPTIONAL
		}
	}
}

HS-DSCH-DrxCycleFach ::=				ENUMERATED {
											f4, f8, f16, f32 }

HS-DSCH-First-Drx-CycleFach ::=			ENUMERATED {
											f2, f4, f8, f16, f32, f64 }

HS-DSCH-First-Rx-BurstFach ::=			ENUMERATED {
											f0p4, f0p8 }

HS-DSCH-PagingSystemInformation ::=		SEQUENCE {
	dlScramblingCode						SecondaryScramblingCode					OPTIONAL,
	pich-ForHSDPASupportedPagingList		SEQUENCE (SIZE (1..maxSCCPCH)) OF
												PICH-ForHSDPASupportedPaging,
	numberOfPcchTransmissions				INTEGER(1..5),
	transportBlockSizeList					SEQUENCE (SIZE (1..2)) OF
												TransportBlockSizeIndex
}

HS-DSCH-PagingSystemInformation-TDD128 ::= SEQUENCE {
	pich-ForHsdschList						SEQUENCE (SIZE (1..maxSCCPCH)) OF
												PICH-ForHSDPASupportedPaging-TDD128,
	dtch-DCCH-reception-window-size			INTEGER (1..16),
	pcch-InformationList					PCCH-InformationList					OPTIONAL
}

HS-DSCH-RxPatternList-TDD128 ::=	SEQUENCE (SIZE (1..maxRxPatternForHSDSCH-TDD128)) OF
										SEQUENCE {
	repetitionPeriodAndLength				RepetitionPeriodAndLengthForSPS
}

HS-DSCH-Second-Rx-BurstFach ::=				ENUMERATED {
											f1, f2 }

HS-DSCH-SecondDrx-CycleFach ::=				ENUMERATED {
											f4, f8, f16, f32, f64, f128, f256, f512 }

HS-DSCH-TBSizeTable ::=					ENUMERATED { octetAligned }

HS-DSCH-TbsList-TDD128 ::=			SEQUENCE (SIZE (1..maxTbsForHSDSCH-TDD128)) OF
										SEQUENCE {
	hs-dsch-TBSizeIndex						INTEGER (1..63)
}

HS-DSCH-SPS-Information-TDD128 ::=	SEQUENCE {
	hs-dsch-SPS-Operation				CHOICE {
		continue							NULL,
		newOperation						HS-DSCH-SPS-NewOperation-TDD128
	}
}

HS-DSCH-SPS-NewOperation-TDD128 ::=	SEQUENCE {
	hs-dsch-TbsList						HS-DSCH-TbsList-TDD128					OPTIONAL,
	hs-dsch-RxPatternList				HS-DSCH-RxPatternList-TDD128			OPTIONAL,
	hARQInfoForSPS						SEQUENCE {
		numberOfProcesses					INTEGER (1..8),
		memorySize							HARQMemorySize
	}		OPTIONAL,
	hs-sich-List						HS-SICH-List-TDD128,
	initialSPSInfoForHSDSCH				SEQUENCE {
		timeslotInfo						BIT STRING (SIZE (5)),
		codeResourceInfo					HS-ChannelisationCodeSetInfo-LCR,
		activationTime						ActivationTime,
		sfnNum								INTEGER (0..1),
		initialRxPatternIndex				INTEGER (0..maxRxPatternForHSDSCH-TDD128-1),
		initialTfsIndex						INTEGER (0..maxTbsForHSDSCH-TDD128-1),
		modulation							ENUMERATED { modQPSK, mod16QAM },
		hs-sich-Index						INTEGER (0..maxHSSICH-TDD128-1)
	}		OPTIONAL
}

HS-DPCCHOverheadReduction ::=	SEQUENCE {
	hs-dpcch-ReductionType			ENUMERATED { reductionType1, reductionType2}		OPTIONAL,
	feedback-cycle2					Feedback-cycle2,
	cqi-CycleSwitchTimer			CQI-CycleSwitchTimer
}

HS-PDSCH-Midamble-Configuration-TDD128 ::=	SEQUENCE {
	midambleAllocationMode				CHOICE{
		defaultMidamble						NULL,
		commonMidamble						NULL,
		ueSpecificMidamble					INTEGER (0..15)
    },
	-- Actual value midambleConfiguration = IE value * 2
	midambleConfiguration				INTEGER (1..8)
}

HS-SCCH-Info ::=					SEQUENCE {
	modeSpecificInfo					CHOICE {
		fdd									SEQUENCE {
			hS-SCCHChannelisationCodeInfo		SEQUENCE (SIZE (1..maxHSSCCHs)) OF
													HS-SCCH-Codes,
			dl-ScramblingCode					SecondaryScramblingCode		OPTIONAL
		},
		tdd									CHOICE {
			tdd384								SEQUENCE {
                nack-ack-power-offset      		   INTEGER (-7..8),
                hs-SICH-PowerControl-Info  		   HS-SICH-Power-Control-Info-TDD384,
				hS-SCCH-SetConfiguration 		   SEQUENCE (SIZE (1..maxHSSCCHs)) OF
						HS-SCCH-TDD384
				},
			tdd128								SEQUENCE (SIZE (1..maxHSSCCHs)) OF
													HS-SCCH-TDD128
		}
	}
}

HS-SCCH-Info-r6 ::=					SEQUENCE {
	modeSpecificInfo					CHOICE {
		fdd									SEQUENCE {
			hS-SCCHChannelisationCodeInfo		SEQUENCE (SIZE (1..maxHSSCCHs)) OF
													HS-SCCH-Codes,
			dl-ScramblingCode					SecondaryScramblingCode			OPTIONAL
		},
		tdd									CHOICE {
			tdd384								SEQUENCE {
				nack-ack-power-offset				INTEGER (-7..8),
				hs-SICH-PowerControl-Info			HS-SICH-Power-Control-Info-TDD384,
				dhs-sync							DHS-Sync					OPTIONAL,
				bler-target							Bler-Target,
				hS-SCCH-SetConfiguration			SEQUENCE (SIZE (1..maxHSSCCHs)) OF
														HS-SCCH-TDD384-r6
				},
			tdd128								SEQUENCE {
				nack-ack-power-offset				INTEGER (-7..8),
				power-level-HSSICH					INTEGER (-120..-58),
				tpc-step-size						ENUMERATED { s1, s2, s3 , spare1 },
				bler-target							Bler-Target,
				hS-SCCH-SetConfiguration			SEQUENCE (SIZE (1..maxHSSCCHs)) OF
														HS-SCCH-TDD128-r6
			}
		}
	}
}

HS-SCCH-Info-r7 ::=					SEQUENCE {
	modeSpecificInfo					CHOICE {
		fdd									SEQUENCE {
			hS-SCCHChannelisationCodeInfo		SEQUENCE (SIZE (1..maxHSSCCHs)) OF
													HS-SCCH-Codes,
			dl-ScramblingCode					SecondaryScramblingCode			OPTIONAL
		},
		tdd									CHOICE {
			tdd384								SEQUENCE {
				nack-ack-power-offset				INTEGER (-7..8),
				hs-SICH-PowerControl-Info			HS-SICH-Power-Control-Info-TDD384,
				dhs-sync							DHS-Sync					OPTIONAL,
				bler-target							Bler-Target,
				hS-SCCH-SetConfiguration			SEQUENCE (SIZE (1..maxHSSCCHs)) OF
														HS-SCCH-TDD384-r6
				},
			tdd768								SEQUENCE {
				nack-ack-power-offset				INTEGER (-7..8),
				hs-SICH-PowerControl-Info			HS-SICH-Power-Control-Info-TDD768,
				dhs-sync							DHS-Sync					OPTIONAL,
				bler-target							Bler-Target,
				hS-SCCH-SetConfiguration			SEQUENCE (SIZE (1..maxHSSCCHs)) OF
														HS-SCCH-TDD768
				},
			tdd128								SEQUENCE {
				nack-ack-power-offset				INTEGER (-7..8),
				power-level-HSSICH					INTEGER (-120..-58),
				tpc-step-size						ENUMERATED { s1, s2, s3 , spare1 },
				bler-target							Bler-Target,
				powerControlGAP						PowerControlGAP					OPTIONAL,
				pathlossCompensationSwitch			BOOLEAN							OPTIONAL,
				hS-SCCH-SetConfiguration			SEQUENCE (SIZE (1..maxHSSCCHs)) OF
														HS-SCCH-TDD128-r6
			}
		}
	}
}

HS-SCCH-Info-r8-ext ::=					SEQUENCE {
	modeSpecificInfo						CHOICE {
		fdd										NULL,
		tdd										CHOICE {
			tdd384									NULL,
			tdd768									NULL,
			tdd128									SEQUENCE {
				hS-SCCH-tpc-step-size					ENUMERATED { s1, s2, s3, spare1 }	OPTIONAL
			}
		}
	}
}

HS-SCCH-Info-r9 ::=					SEQUENCE {
	modeSpecificInfo					CHOICE {
		fdd									SEQUENCE {
			hS-SCCHChannelisationCodeInfo		SEQUENCE (SIZE (1..maxHSSCCHs)) OF
													HS-SCCH-Codes,
			dl-ScramblingCode					SecondaryScramblingCode			OPTIONAL
		},
		tdd									CHOICE {
			tdd384								SEQUENCE {
				nack-ack-power-offset				INTEGER (-7..8),
				hs-SICH-PowerControl-Info			HS-SICH-Power-Control-Info-TDD384,
				dhs-sync							DHS-Sync					OPTIONAL,
				bler-target							Bler-Target,
				hS-SCCH-SetConfiguration			SEQUENCE (SIZE (1..maxHSSCCHs)) OF
														HS-SCCH-TDD384-r6
				},
			tdd768								SEQUENCE {
				nack-ack-power-offset				INTEGER (-7..8),
				hs-SICH-PowerControl-Info			HS-SICH-Power-Control-Info-TDD768,
				dhs-sync							DHS-Sync					OPTIONAL,
				bler-target							Bler-Target,
				hS-SCCH-SetConfiguration			SEQUENCE (SIZE (1..maxHSSCCHs)) OF
														HS-SCCH-TDD768
				},
			tdd128								SEQUENCE {
				nack-ack-power-offset				INTEGER (-7..8),
				power-level-HSSICH					INTEGER (-120..-58),
				tpc-step-size						ENUMERATED { s1, s2, s3, spare1 },
				bler-target							Bler-Target,
				hS-SCCH-tpc-step-size				ENUMERATED { s1, s2, s3, spare1 }	OPTIONAL,
				powerControlGAP						PowerControlGAP					OPTIONAL,
				pathlossCompensationSwitch			BOOLEAN							OPTIONAL,
				hS-SCCH-SetConfiguration			SEQUENCE (SIZE (1..maxHSSCCHs)) OF
														HS-SCCH-TDD128-r6
			}
		}
	}
}

HS-SCCH-DRX-InactivityThreshold-TDD128 ::= ENUMERATED {
											sub-frames-1, sub-frames-2, sub-frames-4,
											sub-frames-8, sub-frames-16, sub-frames-32,
											sub-frames-64, sub-frames-128, sub-frames-256,
											sub-frames-512,
											spare6, spare5, spare4, spare3, spare2,
											infinity }

HS-SCCH-DRX-Info-TDD128 ::=			SEQUENCE {
	hS-SCCH-DRX-Cycle					ControlChannelDRXCycle-TDD128,
	hS-SCCH-DRX-InactivityThreshold		HS-SCCH-DRX-InactivityThreshold-TDD128	OPTIONAL,
	hS-SCCH-DRX-Offset					INTEGER (0..63)
}

HS-SCCH-Codes ::=					INTEGER (0..127)

HS-SCCH-Less-NewOperation ::=		SEQUENCE {
	hs-pdsch-CodeIndex					INTEGER (1..15),
	hs-scch-LessTFS						HS-SCCH-LessTFSList
}

HS-SCCH-LessInfo-r7 ::=				SEQUENCE {
	hs-scchLessOperation				CHOICE {
		continue							NULL,
		newOperation						HS-SCCH-Less-NewOperation
	}
}

HS-SCCH-LessTFSList ::=				SEQUENCE (SIZE (1..maxHS-SCCHLessTrBlk)) OF
										SEQUENCE {
	hs-scch-LessTFSI						INTEGER (1..90),
	hs-scch-LessSecondCodeSupport			BOOLEAN
}

HS-SCCH-SystemInfo ::=				SEQUENCE {
	dl-ScramblingCode					SecondaryScramblingCode					OPTIONAL,
	hS-SCCHChannelisationCodeInfo		SEQUENCE (SIZE (1..maxHSSCCHs)) OF
											HS-SCCH-Codes
}

HS-SCCH-SystemInfo-TDD128 ::=		SEQUENCE {
	hs-SCCH-SetConfiguration			SEQUENCE (SIZE (1..maxHSSCCHs)) OF
											HS-SCCH-TDD128-r6,
	power-level-HSSICH					INTEGER (-120..-58),
	nack-ack-power-offset				INTEGER (-7..8),
	tpc-step-size						ENUMERATED { s1, s2, s3 , spare1 },
	bler-target							Bler-Target,
	power-control-gap					INTEGER (1..255)						OPTIONAL,
	pathloss-compensation-switch		BOOLEAN									OPTIONAL
}

HS-SCCH-TDD128 ::=				SEQUENCE {
	timeslotNumber						TimeslotNumber-LCR-r4,
	firstChannelisationCode				HS-ChannelisationCode-LCR,
	secondChannelisationCode			HS-ChannelisationCode-LCR,
	midambleAllocationMode				CHOICE {
		defaultMidamble						NULL,
		commonMidamble						NULL,
		ueSpecificMidamble					INTEGER(0..15)
	},
	-- Actual value midambleConfiguration = IE value * 2
	midambleConfiguration				INTEGER (1..8),
	bler-target							Bler-Target,
	hs-sich-configuration				HS-SICH-Configuration-TDD128
}

HS-SCCH-TDD128-r6 ::=				SEQUENCE {
	timeslotNumber						TimeslotNumber-LCR-r4,
	firstChannelisationCode				HS-ChannelisationCode-LCR,
	secondChannelisationCode			HS-ChannelisationCode-LCR,
	midambleAllocationMode				CHOICE {
		defaultMidamble						NULL,
		commonMidamble						NULL,
		ueSpecificMidamble					INTEGER(0..15)
	},
	-- Actual value midambleConfiguration = IE value * 2
	midambleConfiguration				INTEGER (1..8),
	hs-sich-configuration				HS-SICH-Configuration-TDD128-r6
}

--for TDD128 Multi-Carrier
HS-SCCH-TDD128-MultiCarrier ::=		SEQUENCE {
	uarfcn-HS-SCCH-Rx					UARFCN,
	timeslotNumber						TimeslotNumber-LCR-r4,
	firstChannelisationCode				HS-ChannelisationCode-LCR,
	secondChannelisationCode			HS-ChannelisationCode-LCR,
	midambleAllocationMode				CHOICE {
		defaultMidamble						NULL,
		commonMidamble						NULL,
		ueSpecificMidamble					INTEGER(0..15)
	},
	-- Actual value midambleConfiguration = IE value * 2
	midambleConfiguration				INTEGER (1..8),
	bler-target							Bler-Target,
	hs-sich-configuration				HS-SICH-Configuration-TDD128
}

HS-SICH-Configuration-TDD128 ::=	SEQUENCE {
	timeslotNumber						TimeslotNumber-LCR-r4,
	channelisationCode					HS-ChannelisationCode-LCR,
	midambleAllocationMode				CHOICE {
		defaultMidamble						NULL,
		ueSpecificMidamble					SEQUENCE {
			midambleShift						MidambleShiftLong
		}
	},
	-- Actual value midambleConfiguration = IE value * 2
	midambleConfiguration				INTEGER (1..8),
	nack-ack-power-offset				INTEGER (-7..8),
	power-level-HSSICH					INTEGER (-120..-58),
	tpc-step-size						ENUMERATED { s1, s2, s3 , spare1}
}

HS-SICH-Configuration-TDD128-r6 ::=	SEQUENCE {
	timeslotNumber						TimeslotNumber-LCR-r4,
	channelisationCode					HS-ChannelisationCode-LCR,
	midambleAllocationMode				CHOICE {
		defaultMidamble						NULL,
		ueSpecificMidamble					SEQUENCE {
			midambleShift						MidambleShiftLong
		}
	},
	-- Actual value midambleConfiguration = IE value * 2
	midambleConfiguration				INTEGER (1..8)
}

HS-SICH-List-TDD128 ::=				SEQUENCE (SIZE (1..maxHSSICH-TDD128)) OF
										CHOICE {
	implicit								SEQUENCE {
		hS-SCCH-Index							INTEGER (0..maxHSSCCHs-1)
	},
	explicit								SEQUENCE {
		hS-SICH-Info							HS-SICH-Configuration-TDD128-r6
	}
}

--The order of the list corresponds to the order of HS-SCCHs in HS-SCCH info
HS-SICH-ReferenceSignalInfoList ::=		SEQUENCE ( SIZE (1.. maxHSSCCHs)) OF
											SEQUENCE {
	-- Actual value midambleConfiguration = IE value * 2
	midambleConfiguration						INTEGER (1..8),
	midambleShift								INTEGER (0..15),
	timeSlot									INTEGER (1..5)
}

HS-SCCH-TDD384 ::=					SEQUENCE {
	timeslotNumber						TimeslotNumber,
	channelisationCode					DL-TS-ChannelisationCode,
	midambleAllocationMode				CHOICE {
		defaultMidamble						NULL,
		commonMidamble						NULL,
		ueSpecificMidamble					SEQUENCE {
			midambleShift						MidambleShiftLong
		}
	},
	midambleconfiguration				MidambleConfigurationBurstType1and3,
	bler-target							Bler-Target,
	hs-sich-configuration				HS-SICH-Configuration-TDD384
}

HS-SCCH-TDD384-r6 ::=				SEQUENCE {
	timeslotNumber						TimeslotNumber,
	channelisationCode					DL-TS-ChannelisationCode,
	midambleAllocationMode				CHOICE {
		defaultMidamble						NULL,
		commonMidamble						NULL,
		ueSpecificMidamble					SEQUENCE {
			midambleShift						MidambleShiftLong
		}
	},
	midambleconfiguration				MidambleConfigurationBurstType1and3,
	hs-sich-configuration				HS-SICH-Configuration-TDD384
}

HS-SCCH-TDD768 ::=				SEQUENCE {
	timeslotNumber						TimeslotNumber,
	channelisationCode					DL-TS-ChannelisationCode-VHCR,
	midambleAllocationMode				CHOICE {
		defaultMidamble						NULL,
		commonMidamble						NULL,
		ueSpecificMidamble					SEQUENCE {
			midambleShift						MidambleShiftLong
		}
	},
	midambleconfiguration				MidambleConfigurationBurstType1and3,
	hs-sich-configuration				HS-SICH-Configuration-TDD768
}

HS-SICH-Configuration-TDD384 ::=	SEQUENCE {
	timeslotNumber						TimeslotNumber,
	channelisationCode					DL-TS-ChannelisationCode,
	midambleAllocationMode				CHOICE {
		defaultMidamble						NULL,
		ueSpecificMidamble					SEQUENCE {
			midambleShift						MidambleShiftLong
		}
	},
	midambleconfiguration				MidambleConfigurationBurstType1and3
}

HS-SICH-Configuration-TDD768 ::=	SEQUENCE {
	timeslotNumber						TimeslotNumber,
	channelisationCode					DL-TS-ChannelisationCode-VHCR,
	midambleAllocationMode				CHOICE {
		defaultMidamble						NULL,
		ueSpecificMidamble					SEQUENCE {
			midambleShift						MidambleShiftLong
		}
	},
	midambleconfiguration				MidambleConfigurationBurstType1and3
}

HS-SICH-Power-Control-Info-TDD384 ::= SEQUENCE {
	-- Actual value ul-target-SIR = IE value * 0.5
	ul-target-SIR						INTEGER (-22..40),
	-- Note: IE 'ConstantValue' is used (instead of IE 'ConstantValueTDD') to keep
	-- compatibility with REL-5
	hs-sich-ConstantValue				ConstantValue
}

HS-SICH-Power-Control-Info-TDD768 ::= SEQUENCE {
	-- Actual value ul-target-SIR = IE value * 0.5
	ul-target-SIR						INTEGER (-22..40),
	-- Note: IE 'ConstantValue' is used (instead of IE 'ConstantValueTDD') to keep
	-- compatibility with REL-5
	hs-sich-ConstantValue				ConstantValue
}

IndividualTimeslotInfo ::=			SEQUENCE {
	timeslotNumber						TimeslotNumber,
	tfci-Existence						BOOLEAN,
	midambleShiftAndBurstType			MidambleShiftAndBurstType
}

IndividualTimeslotInfo-VHCR ::=			SEQUENCE {
	timeslotNumber						TimeslotNumber,
	tfci-Existence						BOOLEAN,
	midambleShiftAndBurstType-VHCR		MidambleShiftAndBurstType-VHCR
}

IndividualTimeslotInfo-LCR-r4 ::=	SEQUENCE {
	timeslotNumber						TimeslotNumber-LCR-r4,
	tfci-Existence						BOOLEAN,
	midambleShiftAndBurstType			MidambleShiftAndBurstType-LCR-r4,
	modulation							ENUMERATED { mod-QPSK, mod-8PSK },
	ss-TPC-Symbols						ENUMERATED { zero, one, sixteenOverSF },
	additionalSS-TPC-Symbols			INTEGER(1..15)		OPTIONAL
}

IndividualTimeslotInfo-LCR-r4-ext ::=		SEQUENCE {
-- timeslotNumber and tfci-Existence is taken from IndividualTimeslotInfo.
-- midambleShiftAndBurstType in IndividualTimeslotInfo shall be ignored.
	midambleShiftAndBurstType			MidambleShiftAndBurstType-LCR-r4,
	modulation							ENUMERATED { mod-QPSK, mod-8PSK },
	ss-TPC-Symbols						ENUMERATED { zero, one, sixteenOverSF }
}

IndividualTimeslotInfo-r7 ::=		SEQUENCE {
	timeslotNumber						TimeslotNumber,
	tfci-Existence						BOOLEAN,
	midambleShiftAndBurstType			MidambleShiftAndBurstType-r7
}

IndividualTS-Interference ::=		SEQUENCE {
	timeslot							TimeslotNumber,
	ul-TimeslotInterference				TDD-UL-Interference
}

IndividualTS-InterferenceList ::=	SEQUENCE (SIZE (1..maxTS)) OF
										IndividualTS-Interference

ITP ::=								ENUMERATED {
										mode0, mode1 }

NidentifyAbort ::=	INTEGER (1..128)

MAC-DTX-Cycle-10ms ::=				ENUMERATED {
										sub-frames-5,
										sub-frames-10,
										sub-frames-20,
										spare1 }

MAC-DTX-Cycle-2ms ::=				ENUMERATED {
										sub-frames-1,
										sub-frames-4,
										sub-frames-5,
										sub-frames-8,
										sub-frames-10,
										sub-frames-16,
										sub-frames-20,
										spare1 }

MAC-InactivityThreshold ::=			ENUMERATED {
										e-dch-tti-1,
										e-dch-tti-2,
										e-dch-tti-4,
										e-dch-tti-8,
										e-dch-tti-16,
										e-dch-tti-32,
										e-dch-tti-64,
										e-dch-tti-128,
										e-dch-tti-256,
										e-dch-tti-512,
										e-dch-tti-Infinity,
										spare5,
										spare4,
										spare3,
										spare2,
										spare1 }

MaxAllowedUL-TX-Power ::=			INTEGER (-50..33)

MaxAvailablePCPCH-Number ::=		INTEGER (1..64)
MaxPowerIncrease-r4 ::=				INTEGER (0..3)

MaxTFCI-Field2Value ::=				INTEGER (1..1023)

Measurement-Feedback-Info ::=		SEQUENCE {
	modeSpecificInfo				CHOICE {
		fdd								SEQUENCE {
			measurementPowerOffset			MeasurementPowerOffset,
			feedback-cycle					Feedback-cycle,
			cqi-RepetitionFactor			CQI-RepetitionFactor,
			deltaCQI						DeltaCQI
		},
		tdd								NULL
	}
}

Measurement-Feedback-Info-r7 ::= SEQUENCE {
	modeSpecificInfo				CHOICE {
		fdd								SEQUENCE {
			measurementPowerOffset			MeasurementPowerOffset,
			feedback-cycle					Feedback-cycle-r7,
			cqi-RepetitionFactor			CQI-RepetitionFactor,
			deltaCQI						DeltaCQI
		},
		tdd								NULL
	}
}

Measurement-Feedback-Info-r11 ::= SEQUENCE {
	modeSpecificInfo				CHOICE {
		fdd								SEQUENCE {
			measurementPowerOffset			MeasurementPowerOffset,
			feedback-cycle					Feedback-cycle-r7,
			cqi-RepetitionFactor			CQI-RepetitionFactor,
			cqi-RepetitionFactor-Assisting	CQI-RepetitionFactor			OPTIONAL,
			deltaCQI						DeltaCQI-r11
		},
		tdd								NULL
	}
}

Measurement-Feedback-Info-r12 ::= SEQUENCE {
	modeSpecificInfo				CHOICE {
		fdd								SEQUENCE {
			measurementPowerOffset			MeasurementPowerOffset,
			feedback-cycle					Feedback-cycle-r7,
			hs-DPCCHOverheadReduction		HS-DPCCHOverheadReduction		OPTIONAL,
			cqi-RepetitionFactor			CQI-RepetitionFactor,
			cqi-RepetitionFactor-Assisting	CQI-RepetitionFactor			OPTIONAL,
			deltaCQI						DeltaCQI-r11
		},
		tdd								NULL
	}
}

Measurement-Feedback-Info-ConcurrentTTI ::= SEQUENCE {
			feedback-cycle					Feedback-cycle-r7				OPTIONAL,
			cqi-RepetitionFactor			CQI-RepetitionFactor			OPTIONAL,
			deltaCQI						DeltaCQI						OPTIONAL
}

MidambleConfigurationBurstType1and3 ::= ENUMERATED {ms4, ms8, ms16}

MidambleConfigurationBurstType1 ::= ENUMERATED {ms4, ms8, ms16}

MidambleConfigurationBurstType2 ::=		ENUMERATED {ms3, ms6}

MidambleConfigurationBurstType2-VHCR ::=		ENUMERATED {ms4, ms8}

MidambleShiftAndBurstType ::=		SEQUENCE {
	burstType							CHOICE {
		type1								SEQUENCE {
			midambleConfigurationBurstType1and3	MidambleConfigurationBurstType1and3,
			midambleAllocationMode				CHOICE {
				defaultMidamble						NULL,
				commonMidamble						NULL,
				ueSpecificMidamble					SEQUENCE {
					midambleShift						MidambleShiftLong
				}
			}
		},
		type2								SEQUENCE {
			midambleConfigurationBurstType2		MidambleConfigurationBurstType2,
			midambleAllocationMode				CHOICE {
				defaultMidamble						NULL,
				commonMidamble						NULL,
				ueSpecificMidamble					SEQUENCE {
					midambleShift						MidambleShiftShort
				}
			}
		},
		type3								SEQUENCE {
			midambleConfigurationBurstType1and3	MidambleConfigurationBurstType1and3,
			midambleAllocationMode				CHOICE {
				defaultMidamble						NULL,
				ueSpecificMidamble					SEQUENCE {
					midambleShift						MidambleShiftLong
				}
			}
		}
	}
}

MidambleShiftAndBurstType-VHCR ::=	SEQUENCE {
	burstType							CHOICE {
		type1								SEQUENCE {
			midambleConfigurationBurstType1and3	MidambleConfigurationBurstType1and3,
			midambleAllocationMode				CHOICE {
				defaultMidamble						NULL,
				commonMidamble						NULL,
				ueSpecificMidamble					SEQUENCE {
					midambleShift						MidambleShiftLong
				}
			}
		},
		type2								SEQUENCE {
			midambleConfigurationBurstType2		MidambleConfigurationBurstType2-VHCR,
			midambleAllocationMode				CHOICE {
				defaultMidamble						NULL,
				commonMidamble						NULL,
				ueSpecificMidamble					SEQUENCE {
					midambleShift						MidambleShiftShort-VHCR
				}
			}
		},
		type3								SEQUENCE {
			midambleConfigurationBurstType1and3	MidambleConfigurationBurstType1and3,
			midambleAllocationMode				CHOICE {
				defaultMidamble						NULL,
				ueSpecificMidamble					SEQUENCE {
					midambleShift						MidambleShiftLong
				}
			}
		},
		-- mbsfnBurstType4 is only used DL
		mbsfnBurstType4						NULL
	}
}

MidambleShiftAndBurstType-r7 ::=	SEQUENCE {
	burstType							CHOICE {
		type1								SEQUENCE {
			midambleConfigurationBurstType1and3	MidambleConfigurationBurstType1and3,
			midambleAllocationMode				CHOICE {
				defaultMidamble						NULL,
				commonMidamble						NULL,
				ueSpecificMidamble					SEQUENCE {
					midambleShift						MidambleShiftLong
				}
			}
		},
		type2								SEQUENCE {
			midambleConfigurationBurstType2		MidambleConfigurationBurstType2,
			midambleAllocationMode				CHOICE {
				defaultMidamble						NULL,
				commonMidamble						NULL,
				ueSpecificMidamble					SEQUENCE {
					midambleShift						MidambleShiftShort
				}
			}
		},
		type3								SEQUENCE {
			midambleConfigurationBurstType1and3	MidambleConfigurationBurstType1and3,
			midambleAllocationMode				CHOICE {
				defaultMidamble						NULL,
				ueSpecificMidamble					SEQUENCE {
					midambleShift						MidambleShiftLong
				}
			}
		},
		-- mbsfnBurstType4 is only used DL
		mbsfnBurstType4						NULL
	}
}

MidambleShiftAndBurstType-DL ::=		SEQUENCE {
	burstType							CHOICE {
		type1								SEQUENCE {
			midambleConfigurationBurstType1and3	MidambleConfigurationBurstType1and3,
			midambleAllocationMode				CHOICE {
				defaultMidamble						NULL,
				commonMidamble						NULL,
				ueSpecificMidamble					SEQUENCE {
					midambleShift						MidambleShiftLong
				}
			}
		},
		type2								SEQUENCE {
			midambleConfigurationBurstType2		MidambleConfigurationBurstType2,
			midambleAllocationMode				CHOICE {
				defaultMidamble						NULL,
				commonMidamble						NULL,
				ueSpecificMidamble					SEQUENCE {
					midambleShift						MidambleShiftShort
				}
			}
		}
	}
}

MidambleShiftAndBurstType-DL-VHCR ::= SEQUENCE {
	burstType							CHOICE {
		type1								SEQUENCE {
			midambleConfigurationBurstType1and3	MidambleConfigurationBurstType1and3,
			midambleAllocationMode				CHOICE {
				defaultMidamble						NULL,
				commonMidamble						NULL,
				ueSpecificMidamble					SEQUENCE {
					midambleShift						MidambleShiftLong
				}
			}
		},
		type2								SEQUENCE {
			midambleConfigurationBurstType2		MidambleConfigurationBurstType2-VHCR,
			midambleAllocationMode				CHOICE {
				defaultMidamble						NULL,
				commonMidamble						NULL,
				ueSpecificMidamble					SEQUENCE {
					midambleShift						MidambleShiftShort-VHCR
				}
			}
		}
	}
}

MidambleShiftAndBurstType-LCR-r4 ::=	SEQUENCE {
	midambleAllocationMode				CHOICE {
		defaultMidamble						NULL,
		commonMidamble						NULL,
		ueSpecificMidamble					SEQUENCE {
			midambleShift						INTEGER (0..15)
		}
	},
	-- Actual value midambleConfiguration = IE value * 2
	midambleConfiguration				INTEGER (1..8)
}

MidambleShiftAndBurstType-EDCH ::=	SEQUENCE {
	burstType							CHOICE {
		type1								SEQUENCE {
			midambleConfigurationBurstType1		MidambleConfigurationBurstType1,
			midambleAllocationMode				CHOICE {
				defaultMidamble						NULL,
				commonMidamble						NULL,
				ueSpecificMidamble					SEQUENCE {
					midambleShift						MidambleShiftLong
				}
			}
		},
		type2								SEQUENCE {
			midambleConfigurationBurstType2		MidambleConfigurationBurstType2,
			midambleAllocationMode				CHOICE {
				defaultMidamble						NULL,
				commonMidamble						NULL,
				ueSpecificMidamble					SEQUENCE {
					midambleShift						MidambleShiftShort
				}
			}
		}
	}
}

MidambleShiftLong ::=				INTEGER (0..15)


MidambleShiftShort ::=				INTEGER (0..5)

MidambleShiftShort-VHCR ::=			INTEGER (0..7)

MIMO-N-M-Ratio ::=					ENUMERATED {
										mnm1-2, mnm2-3, mnm3-4, mnm4-5, mnm5-6,
										mnm6-7, mnm7-8, mnm8-9, mnm9-10, mnm1-1 }

MIMO-Operation ::=					ENUMERATED {
										start, continue }

MIMO-Parameters-r7 ::=				SEQUENCE {
	mimoOperation						MIMO-Operation,
	mimoN-M-Ratio						MIMO-N-M-Ratio					OPTIONAL,
	mimoPilotConfiguration				MIMO-PilotConfiguration			OPTIONAL
}

MIMO4x4-Parameters ::=				SEQUENCE {
    configurationInfo                   CHOICE {
		continue							NULL,
		newConfiguration					SEQUENCE {
			mimo4x4N-M-Ratio					MIMO-N-M-Ratio					OPTIONAL,
			mimo4x4PilotConfiguration			MIMO4x4-PilotConfiguration		OPTIONAL,
			precodingWeightSetRestriction		BIT STRING (SIZE (64))			OPTIONAL
		}
	}
}

MIMO-Parameters-v7f0ext ::=			MIMO-PilotConfiguration-v7f0ext

MIMO-Parameters-v7g0ext ::= SEQUENCE {
	precodingWeightSetRestriction		ENUMERATED { true }			OPTIONAL
}

MIMO-Parameters-r8 ::=				SEQUENCE {
	mimoOperation						MIMO-Operation,
	modeSpecificInfo					CHOICE {
		fdd									SEQUENCE {
			mimoN-M-Ratio						MIMO-N-M-Ratio					OPTIONAL,
			mimoPilotConfiguration				MIMO-PilotConfiguration			OPTIONAL
		},
		tdd									CHOICE {
			tdd128								SEQUENCE {
				mimoSFModeForHSPDSCHDualStream		ENUMERATED {sf1, sf1sf16},
				hs-sich-ReferenceSignalInfoList		HS-SICH-ReferenceSignalInfoList	OPTIONAL
			},
			tdd384-tdd768					NULL
		}
	}
}

MIMO-Parameters-r9 ::=				SEQUENCE {
	mimoOperation						MIMO-Operation,
	modeSpecificInfo					CHOICE {
		fdd									SEQUENCE {
			mimoN-M-Ratio						MIMO-N-M-Ratio						OPTIONAL,
			mimoPilotConfiguration				MIMO-PilotConfiguration-r9			OPTIONAL,
			precodingWeightSetRestriction		ENUMERATED { true }					OPTIONAL
		},
		tdd									CHOICE {
			tdd128								SEQUENCE {
				mimoSFModeForHSPDSCHDualStream		ENUMERATED {sf1, sf1sf16},
				hs-sich-ReferenceSignalInfoList		HS-SICH-ReferenceSignalInfoList	OPTIONAL
			},
			tdd384-tdd768					NULL
		}
	}
}

MIMO-PilotConfiguration ::=			SEQUENCE {
	secondCPICH-Pattern					CHOICE {
		normalPattern						NULL,
		diversityPattern					SEQUENCE {
			channelisationCode					ChannelisationCode256
		}
	}
}

MIMO-PilotConfiguration-v7f0ext ::=	SEQUENCE {
	s-cpich-PowerOffset-Mimo			S-CPICH-PowerOffset-MIMO			OPTIONAL
}

MIMO-PilotConfiguration-r9 ::=			SEQUENCE {
	secondCPICH-Pattern					CHOICE {
		normalPattern						NULL,
		diversityPattern					SEQUENCE {
			channelisationCode					ChannelisationCode256,
			s-cpich-PowerOffset-Mimo			S-CPICH-PowerOffset-MIMO	OPTIONAL
		}
	}
}

MIMO4x4-PilotConfiguration ::=	SEQUENCE {
	antenna2					MIMO-PilotConfiguration-r9	OPTIONAL,
	antenna3And4				Antenna3And4				OPTIONAL
}

MinimumSpreadingFactor ::=			ENUMERATED {
										sf4, sf8, sf16, sf32,
										sf64, sf128, sf256 }

MinReduced-E-DPDCH-GainFactor ::=	ENUMERATED {
										m8-15, m11-15, m15-15, m21-15, m30-15,
										m42-15, m60-15, m84-15 }

MultiCodeInfo ::=					INTEGER (1..16)

-- These IEs are applied for 1.28 Mcps TDD only
Multi-frequencyInfo-LCR-r7 ::=		SEQUENCE {
	-- If the secondary frequency is present, it indicates working frequency
	secondFrequencyInfo					FrequencyInfoTDD				OPTIONAL,
	fPachFrequencyInfo					FrequencyInfoTDD				OPTIONAL,
	--If a cell UpPCH uses other uplink service timeslot, it indicates the UpPCH position
	upPCHpositionInfo					UpPCHposition-LCR				OPTIONAL
}

MultiflowCellType ::= 				ENUMERATED { intra-nodeB, inter-nodeB }

MultiflowConfigurationInfo ::=		SEQUENCE {
	cellType							MultiflowCellType,
	timeReferenceCell					ENUMERATED { true }				OPTIONAL
}

MU-MIMO-Info-TDD128 ::=		CHOICE {
		continue						NULL,
		newConfiguration					SEQUENCE {
			mu-MIMO-Operation				MU-MIMO-Operation,
			standaloneMidambleInfo			StandaloneMidambleInfo-TDD128			OPTIONAL
	}
}

MU-MIMO-Operation ::=			ENUMERATED {
								uL, dL, uLandDL, spare }

N-EOT ::=							INTEGER (0..7)

N-GAP ::=							ENUMERATED {
										f2, f4, f8 }

N-PCH ::=							INTEGER (1..8)

N-StartMessage ::=					INTEGER (1..8)

NB01 ::=							INTEGER (0..50)

NewTiming ::=						SEQUENCE {
	enablingDelay						EnablingDelay,
	ue-dtx-drx-Offset					UE-DTX-DRX-Offset
}

NF-Max ::=							INTEGER (1..64)

NodeB-Trigger-HS-DPCCH-Transmission ::=		SEQUENCE {
	hs-dpcch-TransmitContinuationOffset		ENUMERATED {
													ms10, ms20, ms30, ms40, ms80, ms160,
													ms320, ms800}						OPTIONAL
}

Non-ScheduledTransGrantInfoTDD ::=	CHOICE {
	tdd384-768							SEQUENCE {
		timeslotResourceRelatedInfo			BIT STRING (SIZE (13)),
		powerResourceRelatedInfo			INTEGER (1..32),
		activationTime						ActivationTime,
		repetitionPeriodAndLength			RepetitionPeriodAndLength			OPTIONAL,
		codeResourceInfo					UL-TS-ChannelisationCode
	},
	tdd128								SEQUENCE {
		n-E-UCCH							INTEGER (1..8)		OPTIONAL,
		n-E-HICH							INTEGER (4..15)		OPTIONAL,
		timeslotResourceRelatedInfo			BIT STRING (SIZE (5)),
		powerResourceRelatedInfo			INTEGER (1..32),
		activationTime						ActivationTime,
		sfnNum								INTEGER (0..1),
		repetitionPeriodAndLength			RepetitionPeriodAndLength			OPTIONAL,
		codeResourceInfo					UL-TS-ChannelisationCode,
		e-HICH-Info							SEQUENCE {
			timeslotNumber						TimeslotNumber-LCR-r4,
			channelisation-Code					HS-ChannelisationCode-LCR,
			midambleAllocationMode				CHOICE {
				defaultMidamble						NULL,
				ueSpecificMidamble					INTEGER (0..15)
			},
			-- Actual value midambleConfiguration = IE value * 2
			midambleConfiguration				INTEGER (1..8),
			signatureSequenceGroupIndex			INTEGER (0..19)
		}
	}
}

Non-ScheduledTransGrantInfoTDD-ext ::= 	CHOICE {
	tdd384-768							NULL,
	tdd128									SEQUENCE {
		t-SI-nst								ENUMERATED {
													everyEDCHTTI, ms20, ms40, ms60, ms80, ms160,
													ms200 }							OPTIONAL
	}
}

Non-ScheduledTransGrantInfoTDD-r9 ::=	CHOICE {
	tdd384-768							SEQUENCE {
		timeslotResourceRelatedInfo			BIT STRING (SIZE (13)),
		powerResourceRelatedInfo			INTEGER (1..32),
		activationTime						ActivationTime,
		repetitionPeriodAndLength			RepetitionPeriodAndLength			OPTIONAL,
		codeResourceInfo					UL-TS-ChannelisationCode
	},
	tdd128								SEQUENCE {
		n-E-UCCH							INTEGER (1..8)		OPTIONAL,
		n-E-HICH							INTEGER (4..15)		OPTIONAL,
		timeslotResourceRelatedInfo			BIT STRING (SIZE (5)),
		powerResourceRelatedInfo			INTEGER (1..32),
		activationTime						ActivationTime,
		sfnNum								INTEGER (0..1),
		repetitionPeriodAndLength			RepetitionPeriodAndLength			OPTIONAL,
		codeResourceInfo					UL-TS-ChannelisationCode,
		e-HICH-Info							SEQUENCE {
			timeslotNumber						TimeslotNumber-LCR-r4,
			channelisation-Code					HS-ChannelisationCode-LCR,
			midambleAllocationMode				CHOICE {
				defaultMidamble						NULL,
				ueSpecificMidamble					INTEGER (0..15)
			},
			-- Actual value midambleConfiguration = IE value * 2
			midambleConfiguration				INTEGER (1..8),
			signatureSequenceGroupIndex			INTEGER (0..19)
		},
		t-SI-nst							ENUMERATED {
												everyEDCHTTI, ms20, ms40, ms60, ms80, ms160,
												ms200 }							OPTIONAL
	}
}

Non-rectResAllocInd-TDD128 ::=			ENUMERATED { true }

Non-rectResSpecTSset-TDD128 ::=			BIT STRING (SIZE (7))

NumberOfDPDCH ::=					INTEGER (1..maxDPDCH-UL)

NumberOfFBI-Bits ::=				INTEGER (1..2)

NumberOfTPC-Bits ::=				ENUMERATED { tpc4 }

OpenLoopPowerControl-TDD ::=		SEQUENCE {
	primaryCCPCH-TX-Power				PrimaryCCPCH-TX-Power,
	-- alpha, prach-ConstantValue, dpch-ConstantValue and pusch-ConstantValue
	-- shall be ignored in 1.28Mcps TDD mode.
	alpha								Alpha						OPTIONAL,
	prach-ConstantValue					ConstantValueTdd,
	dpch-ConstantValue					ConstantValueTdd,
	pusch-ConstantValue					ConstantValueTdd			OPTIONAL
}

OpenLoopPowerControl-IPDL-TDD-r4 ::=	SEQUENCE {
	ipdl-alpha							Alpha,
	maxPowerIncrease					MaxPowerIncrease-r4
}

OtherStateConfig ::=		SEQUENCE {
	otherStateConfigList		OtherStateConfigList				OPTIONAL,
	otherStateRemoveList		OtherStateRemoveList				OPTIONAL
}

OtherStateConfigList ::= 	SEQUENCE (SIZE(1..maxOtherStateConfig)) OF
										OtherStateConfigData

OtherStateConfigData ::=		SEQUENCE {
	otherStateConfigIdentity			OtherStateConfigIdentity,
	source-rrc-StateIndicator			RRC-StateIndicator,
	target-rrc-StateIndicator			RRC-StateIndicator,
	ura-Identity						URA-Identity					OPTIONAL,
	rntis			CHOICE {
		clear				NULL,
		continue			NULL,
		new					SEQUENCE {
					new-C-RNTI			C-RNTI,
					new-H-RNTI			H-RNTI,
					newPrimary-E-RNTI	E-RNTI
		}
	},
	configuration	CHOICE {
		id				INTEGER (0..maxRetrievConfig-1),
		full			RetrievableConfigData
	} OPTIONAL
}

OtherStateRemoveList ::=			SEQUENCE (SIZE (1..maxOtherStateConfig)) OF
										OtherStateConfigIdentity

OtherStateConfigIdentity ::=		INTEGER (0..maxOtherStateConfig-1)

PagingIndicatorLength ::=			ENUMERATED {
										pi4, pi8, pi16 }

PC-Preamble ::=						INTEGER (0..7)

PCCH-InformationList ::=			SEQUENCE {
	paging-associatedHspdschInfo		SEQUENCE (SIZE (1.. maxSCCPCH)) OF
											SEQUENCE {
		hs-pdsch-MidambleConfiguration			HS-PDSCH-Midamble-Configuration-TDD128,
		timeslotResourceRelatedInfo				BIT STRING (SIZE (6)),
		codeResourceInformation					CodeResourceInformation-TDD128
	},
	paging-sub-Channel-size				INTEGER (1..3),
	transportBlockSizeList				SEQUENCE (SIZE (1..2)) OF TransportBlockSizeIndex
}

PCP-Length ::=						ENUMERATED {
										as0, as8 }

PCPCH-ChannelInfo ::=				SEQUENCE {
	pcpch-UL-ScramblingCode				INTEGER (0..79),
	pcpch-DL-ChannelisationCode			INTEGER (0..511),
	pcpch-DL-ScramblingCode				SecondaryScramblingCode				OPTIONAL,
	pcp-Length							PCP-Length,
	ucsm-Info							UCSM-Info							OPTIONAL
}

PCPCH-ChannelInfoList ::=			SEQUENCE (SIZE (1..maxPCPCHs)) OF
										PCPCH-ChannelInfo

PCPICH-UsageForChannelEst ::=		ENUMERATED {
										mayBeUsed,
										shallNotBeUsed }

PDSCH-CapacityAllocationInfo ::=	SEQUENCE {
	-- pdsch-PowerControlInfo is conditional on new-configuration branch below, if this
	-- selected the IE is OPTIONAL otherwise it should not be sent
	pdsch-PowerControlInfo				PDSCH-PowerControlInfo				OPTIONAL,
	pdsch-AllocationPeriodInfo			AllocationPeriodInfo,
	configuration						CHOICE {
		old-Configuration					SEQUENCE {
			tfcs-ID								TFCS-IdentityPlain					DEFAULT 1,
			pdsch-Identity						PDSCH-Identity
		},
		new-Configuration					SEQUENCE {
			pdsch-Info							PDSCH-Info,
			pdsch-Identity						PDSCH-Identity				OPTIONAL
		}
	}
}

PDSCH-CapacityAllocationInfo-r4 ::=	SEQUENCE {
	pdsch-AllocationPeriodInfo			AllocationPeriodInfo,
	configuration						CHOICE {
		old-Configuration					SEQUENCE {
			tfcs-ID								TFCS-IdentityPlain					DEFAULT 1,
			pdsch-Identity						PDSCH-Identity
		},
		new-Configuration					SEQUENCE {
			pdsch-Info							PDSCH-Info-r4,
			pdsch-Identity						PDSCH-Identity				OPTIONAL,
			pdsch-PowerControlInfo				PDSCH-PowerControlInfo		OPTIONAL
		}
	}
}

PDSCH-CapacityAllocationInfo-r7 ::=	SEQUENCE {
	pdsch-AllocationPeriodInfo			AllocationPeriodInfo,
	configuration						CHOICE {
		old-Configuration					SEQUENCE {
			tfcs-ID								TFCS-IdentityPlain					DEFAULT 1,
			pdsch-Identity						PDSCH-Identity
		},
		new-Configuration					SEQUENCE {
			pdsch-Info							PDSCH-Info-r7,
			pdsch-Identity						PDSCH-Identity				OPTIONAL,
			pdsch-PowerControlInfo				PDSCH-PowerControlInfo		OPTIONAL
		}
	}
}

PDSCH-CodeInfo ::=					SEQUENCE {
	spreadingFactor						SF-PDSCH,
	codeNumber							CodeNumberDSCH,
	multiCodeInfo						MultiCodeInfo
}

PDSCH-CodeInfoList ::=				SEQUENCE (SIZE (1..maxTFCI-2-Combs)) OF
										PDSCH-CodeInfo

PDSCH-CodeMap ::=					SEQUENCE {
	spreadingFactor						SF-PDSCH,
	multiCodeInfo						MultiCodeInfo,
	codeNumberStart						CodeNumberDSCH,
	codeNumberStop						CodeNumberDSCH
}

PDSCH-CodeMapList ::=				SEQUENCE (SIZE (1..maxPDSCH-TFCIgroups)) OF
										PDSCH-CodeMap

PDSCH-CodeMapping ::=				SEQUENCE {
	dl-ScramblingCode					SecondaryScramblingCode				OPTIONAL,
	signallingMethod					CHOICE {
		codeRange							CodeRange,
		tfci-Range							DSCH-MappingList,
		explicit-config						PDSCH-CodeInfoList,
		replace								ReplacedPDSCH-CodeInfoList
	}
}

PDSCH-Identity ::=					INTEGER (1..hiPDSCHidentities)

PDSCH-Info ::=						SEQUENCE {
	tfcs-ID								TFCS-IdentityPlain					DEFAULT 1,
	commonTimeslotInfo					CommonTimeslotInfo					OPTIONAL,
	pdsch-TimeslotsCodes				DownlinkTimeslotsCodes				OPTIONAL
}

PDSCH-Info-r4 ::=						SEQUENCE {
	tfcs-ID								TFCS-IdentityPlain					DEFAULT 1,
	commonTimeslotInfo					CommonTimeslotInfo					OPTIONAL,
	tddOption							CHOICE {
		tdd384								SEQUENCE {
			pdsch-TimeslotsCodes				DownlinkTimeslotsCodes		OPTIONAL
		},
		tdd128								SEQUENCE {
			pdsch-TimeslotsCodes				DownlinkTimeslotsCodes-LCR-r4	OPTIONAL
		}
	}
}

PDSCH-Info-r7 ::=						SEQUENCE {
	tfcs-ID								TFCS-IdentityPlain					DEFAULT 1,
	commonTimeslotInfo					CommonTimeslotInfo					OPTIONAL,
	tddOption							CHOICE {
		tdd384								SEQUENCE {
			pdsch-TimeslotsCodes				DownlinkTimeslotsCodes		OPTIONAL
		},
		tdd768								SEQUENCE {
			pdsch-TimeslotsCodes				DownlinkTimeslotsCodes-VHCR		OPTIONAL
		},
		tdd128								SEQUENCE {
			pdsch-TimeslotsCodes				DownlinkTimeslotsCodes-LCR-r4	OPTIONAL
		}
	}
}

PDSCH-Info-LCR-r4 ::=				SEQUENCE {
	tfcs-ID								TFCS-IdentityPlain					DEFAULT 1,
	commonTimeslotInfo					CommonTimeslotInfo					OPTIONAL,
	pdsch-TimeslotsCodes				DownlinkTimeslotsCodes-LCR-r4		OPTIONAL
}

PDSCH-PowerControlInfo ::=			SEQUENCE {
	tpc-StepSizeTDD						TPC-StepSizeTDD						OPTIONAL,
	ul-CCTrChTPCList					UL-CCTrChTPCList					OPTIONAL
}

PDSCH-SHO-DCH-Info ::=				SEQUENCE {
	dsch-RadioLinkIdentifier			DSCH-RadioLinkIdentifier,
	rl-IdentifierList					RL-IdentifierList					OPTIONAL
}

PDSCH-SysInfo ::=					SEQUENCE {
	pdsch-Identity						PDSCH-Identity,
	pdsch-Info							PDSCH-Info,
	dsch-TFS							TransportFormatSet					OPTIONAL,
	dsch-TFCS							TFCS								OPTIONAL
}

PDSCH-SysInfo-VHCR-r7 ::=			SEQUENCE {
	pdsch-Identity						PDSCH-Identity,
	pdsch-Info							PDSCH-Info-r7,
	dsch-TransportChannelsInfo			DSCH-TransportChannelsInfo			OPTIONAL,
	dsch-TFCS							TFCS								OPTIONAL
}

PDSCH-SysInfo-HCR-r5 ::=			SEQUENCE {
	pdsch-Identity						PDSCH-Identity,
	pdsch-Info							PDSCH-Info,
	dsch-TransportChannelsInfo			DSCH-TransportChannelsInfo			OPTIONAL,
	dsch-TFCS							TFCS								OPTIONAL
}

PDSCH-SysInfo-LCR-r4 ::=			SEQUENCE {
	pdsch-Identity						PDSCH-Identity,
	pdsch-Info							PDSCH-Info-LCR-r4,
	dsch-TFS							TransportFormatSet					OPTIONAL,
	dsch-TFCS							TFCS								OPTIONAL
}

PDSCH-SysInfoList ::=				SEQUENCE (SIZE (1..maxPDSCH)) OF
										PDSCH-SysInfo

PDSCH-SysInfoList-VHCR-r7 ::=		SEQUENCE (SIZE (1..maxPDSCH)) OF PDSCH-SysInfo-VHCR-r7

PDSCH-SysInfoList-HCR-r5 ::=		SEQUENCE (SIZE (1..maxPDSCH)) OF PDSCH-SysInfo-HCR-r5

PDSCH-SysInfoList-LCR-r4 ::=		SEQUENCE (SIZE (1..maxPDSCH)) OF
										PDSCH-SysInfo-LCR-r4

PDSCH-SysInfoList-SFN ::=			SEQUENCE (SIZE (1..maxPDSCH)) OF
										SEQUENCE {
	pdsch-SysInfo							PDSCH-SysInfo,
	sfn-TimeInfo							SFN-TimeInfo					OPTIONAL
}

PDSCH-SysInfoList-SFN-HCR-r5 ::=			SEQUENCE (SIZE (1..maxPDSCH)) OF
										SEQUENCE {
	pdsch-SysInfo							PDSCH-SysInfo-HCR-r5,
	sfn-TimeInfo							SFN-TimeInfo					OPTIONAL
}

PDSCH-SysInfoList-SFN-LCR-r4 ::=	SEQUENCE (SIZE (1..maxPDSCH)) OF
										SEQUENCE {
	pdsch-SysInfo							PDSCH-SysInfo-LCR-r4,
	sfn-TimeInfo							SFN-TimeInfo					OPTIONAL
}

PersistenceScalingFactor ::=		ENUMERATED {
										psf0-9, psf0-8, psf0-7, psf0-6,
										psf0-5, psf0-4, psf0-3, psf0-2 }

PersistenceScalingFactorList ::=	SEQUENCE (SIZE (1..maxASCpersist)) OF
										PersistenceScalingFactor

PI-CountPerFrame ::=				ENUMERATED {
										e18, e36, e72, e144 }

PichChannelisationCodeList-LCR-r4 ::=	SEQUENCE (SIZE (1..2)) OF
											DL-TS-ChannelisationCode

PICH-ForHSDPASupportedPaging ::=		SEQUENCE {
	hsdpa-AssociatedPichInfo				PICH-Info,
	hs-pdschChannelisationCode				INTEGER(1..15)
}

PICH-ForHSDPASupportedPaging-TDD128 ::= CHOICE {
	implicit							SEQUENCE {
		occurrenceSequenceNumberOfPICH		OccurrenceSequenceNumberOfPICH		OPTIONAL
	},
	explicit							PICH-Info-LCR-r4
}

PICH-Info ::=						CHOICE {
	fdd									SEQUENCE {
		channelisationCode256				ChannelisationCode256,
		pi-CountPerFrame					PI-CountPerFrame,
		sttd-Indicator						BOOLEAN
	},
	tdd									SEQUENCE {
		channelisationCode					TDD-PICH-CCode					OPTIONAL,
		timeslot							TimeslotNumber					OPTIONAL,
		midambleShiftAndBurstType			MidambleShiftAndBurstType,
		repetitionPeriodLengthOffset		RepPerLengthOffset-PICH			OPTIONAL,
		pagingIndicatorLength				PagingIndicatorLength			DEFAULT pi4,
		n-GAP								N-GAP							DEFAULT f4,
		n-PCH								N-PCH							DEFAULT 2
	}
}

PICH-Info-HCR-VHCR-r7 ::=			SEQUENCE {
	channelisationCode					CHOICE {
		tdd384								TDD-PICH-CCode,
		tdd768								TDD768-PICH-CCode
	}		OPTIONAL,
	timeslot							TimeslotNumber					OPTIONAL,
	midambleShiftAndBurstType			MidambleShiftAndBurstType,
	repetitionPeriodLengthOffset		RepPerLengthOffset-PICH			OPTIONAL,
	pagingIndicatorLength				PagingIndicatorLength			DEFAULT pi4,
	n-GAP								N-GAP							DEFAULT f4,
	n-PCH								N-PCH							DEFAULT 2
}

PICH-Info-LCR-r4 ::=				SEQUENCE {
	timeslot							TimeslotNumber-LCR-r4				OPTIONAL,
	pichChannelisationCodeList-LCR-r4	PichChannelisationCodeList-LCR-r4,
	midambleShiftAndBurstType			MidambleShiftAndBurstType-LCR-r4,
	repetitionPeriodLengthOffset		RepPerLengthOffset-PICH				OPTIONAL,
	pagingIndicatorLength				PagingIndicatorLength			DEFAULT pi4,
	n-GAP								N-GAP							DEFAULT f4,
	n-PCH								N-PCH							DEFAULT 2
}

PICH-PowerOffset ::=				INTEGER (-10..5)

PilotBits128 ::=					ENUMERATED {
										pb4, pb8 }

PilotBits128-r12 ::=					ENUMERATED {
										pb0, pb4, pb8 }

PilotBits256 ::=					ENUMERATED {
										pb2, pb4, pb8 }

PilotBits256-r12 ::=					ENUMERATED {
										pb0, pb2, pb4, pb8 }

	-- Actual measurement power offset value = IE value * 0.5
MeasurementPowerOffset ::=			INTEGER (-12..26)

PLCCH-Info ::=					SEQUENCE {
	plcchSequenceNumber				INTEGER(1..14),
	timeslotNumber					TimeslotNumber-LCR-r4,
	channelisationCode				DL-TS-ChannelisationCode,
	tpcCommandTargetRate			TPC-CommandTargetRate
}

PositionFixedOrFlexible ::=		ENUMERATED {
										fixed,
										flexible }

PowerControlAlgorithm ::=			CHOICE {
	algorithm1							TPC-StepSizeFDD,
	algorithm2							NULL
}

PowerControlAlgorithm3-Config ::=	SEQUENCE {
	tpcSlotPosition						INTEGER (0..4)					OPTIONAL,
	tpcStepSize						TPC-StepSizeFDD					OPTIONAL,
	decimationFactor					ENUMERATED {slots3, slots5}		OPTIONAL
}

PowerControlGAP ::=				INTEGER (0..255)

PowerOffsetPilot-pdpdch ::=		INTEGER (0..24)

PowerOffsetPO-SRB ::=				INTEGER (0..24)

PowerOffsetTPC-pdpdch ::=			INTEGER (0..24)

PowerRampStep ::=					INTEGER (1..8)

PRACH-ChanCodes-LCR-r4 ::=		SEQUENCE (SIZE (1..4)) OF
										TDD-PRACH-CCode-LCR-r4

PRACH-ChanCodes-List-LCR ::=		SEQUENCE (SIZE (1..2)) OF
										TDD-PRACH-CCode-LCR-r4

PRACH-Definition-LCR-r4 ::=		SEQUENCE {
	timeslot							TimeslotNumber-PRACH-LCR-r4,
	prach-ChanCodes-LCR				PRACH-ChanCodes-LCR-r4,
	midambleShiftAndBurstType			MidambleShiftAndBurstType-LCR-r4,
	fpach-Info							FPACH-Info-r4
}

PRACH-Information-LCR ::=			SEQUENCE {
	timeslot							TimeslotNumber-PRACH-LCR-r4,
	prach-ChanCodes-list-LCR			PRACH-ChanCodes-List-LCR,
	midambleShiftAndBurstType			MidambleShiftAndBurstType-LCR-r4,
	fpach-Info							FPACH-Info-r4							OPTIONAL
}

PRACH-Information-LCR-List ::=	SEQUENCE (SIZE (1..maxPRACH-FPACH)) OF
										PRACH-Information-LCR

PRACH-Midamble ::=					ENUMERATED {
										direct,
										direct-Inverted }

PRACH-Partitioning ::=			CHOICE {
	fdd									SEQUENCE (SIZE (1..maxASC)) OF
	-- TABULAR: If only "NumASC+1" (with, NumASC+1 < maxASC) ASCSetting-FDD are listed,
	-- the remaining (NumASC+2 through maxASC) ASCs are unspecified.
											ASCSetting-FDD,
	tdd									SEQUENCE (SIZE (1..maxASC)) OF
	-- TABULAR: If only "NumASC+1" (with, NumASC+1 < maxASC) ASCSetting-TDD are listed,
	-- the remaining (NumASC+2 through maxASC) ASCs are unspecified.
											ASCSetting-TDD
}

PRACH-Partitioning-r7 ::=			CHOICE {
	fdd									SEQUENCE (SIZE (1..maxASC)) OF
	-- TABULAR: If only "NumASC+1" (with, NumASC+1 < maxASC) ASCSetting-FDD are listed,
	-- the remaining (NumASC+2 through maxASC) ASCs are unspecified.
											ASCSetting-FDD,
	tdd									SEQUENCE (SIZE (1..maxASC)) OF
	-- TABULAR: If only "NumASC+1" (with, NumASC+1 < maxASC) ASCSetting-TDD are listed,
	-- the remaining (NumASC+2 through maxASC) ASCs are unspecified.
											ASCSetting-TDD-r7
}

PRACH-Partitioning-LCR-r4 ::=		SEQUENCE (SIZE (1..maxASC)) OF
	-- TABULAR: If only "NumASC+1" (with, NumASC+1 < maxASC) ASCSetting-TDD-LCR-r4 are listed,
	-- the remaining (NumASC+2 through maxASC) ASCs are unspecified.
											ASCSetting-TDD-LCR-r4

PRACH-PowerOffset ::=				SEQUENCE {
	powerRampStep						PowerRampStep,
	preambleRetransMax					PreambleRetransMax
}

PRACH-PreambleForEnhancedUplink ::=	SEQUENCE {
	availableSignatures					AvailableSignatures				OPTIONAL,
	e-ai-Indication						BOOLEAN,
	preambleScramblingCodeWordNumber		PreambleScramblingCodeWordNumber	OPTIONAL,
	availableSubChannelNumbers			AvailableSubChannelNumbers		OPTIONAL,
	prach-Partitioning						PRACH-Partitioning-r7				OPTIONAL,
	persistenceScalingFactorList			PersistenceScalingFactorList		OPTIONAL,
	ac-To-ASC-MappingTable				AC-To-ASC-MappingTable			OPTIONAL,
	primaryCPICH-TX-Power					PrimaryCPICH-TX-Power				OPTIONAL,
	constantValue							ConstantValue						OPTIONAL,
	prach-PowerOffset						PRACH-PowerOffset					OPTIONAL,
	rach-TransmissionParameters			RACH-TransmissionParameters		OPTIONAL,
	aich-Info								AICH-Info							OPTIONAL,
	powerOffsetPp-e						INTEGER (-5..10)
}
PRACH-PreambleForEnhancedUplinkExt ::=	SEQUENCE {
	availableSignatures						AvailableSignatures,
	preambleScramblingCodeWordNumber			PreambleScramblingCodeWordNumber,
	aich-Info									AICH-Info-Compressed				OPTIONAL
}

PRACH-PreambleForEnhancedUplinkExtList ::=	SEQUENCE (SIZE (1..maxPRACH-EUL)) OF
													PRACH-PreambleForEnhancedUplinkExtWithWeight


PRACH-PreambleForEnhancedUplinkExtWithWeight ::=	SEQUENCE {
	prach-PreambleForEnhancedUplinkExt		PRACH-PreambleForEnhancedUplinkExt,
	-- Actual value weight = IE value * 0.2
	weight										INTEGER (1..5)		OPTIONAL
}

PRACH-RACH-Info ::=				SEQUENCE {
	modeSpecificInfo					CHOICE {
		fdd									SEQUENCE {
			availableSignatures					AvailableSignatures,
			availableSF							SF-PRACH,
			preambleScramblingCodeWordNumber		PreambleScramblingCodeWordNumber,
			puncturingLimit						PuncturingLimit,
			availableSubChannelNumbers			AvailableSubChannelNumbers
		},
		tdd									SEQUENCE {
			timeslot							TimeslotNumber,
			channelisationCodeList			TDD-PRACH-CCodeList,
			prach-Midamble						PRACH-Midamble
		}
	}
}

PRACH-RACH-Info-VHCR-r7 ::=		SEQUENCE {
	timeslot							TimeslotNumber,
	channelisationCodeList			TDD768-PRACH-CCodeList,
	prach-Midamble						PRACH-Midamble
}

PRACH-RACH-Info-LCR-v770ext ::=	SEQUENCE {
	e-RUCCH-Sync-UL-Codes-Bitmap		Sync-UL-Codes-Bitmap
}

PRACH-RACH-Info-LCR-r4 ::=		SEQUENCE {
	sync-UL-Info						SYNC-UL-Info-r4,
	prach-DefinitionList				SEQUENCE (SIZE (1..maxPRACH-FPACH)) OF
											PRACH-Definition-LCR-r4
}

PRACH-SystemInformation ::=		SEQUENCE {
	prach-RACH-Info					PRACH-RACH-Info,
	transportChannelIdentity			TransportChannelIdentity,
	rach-TransportFormatSet			TransportFormatSet					OPTIONAL,
	rach-TFCS							TFCS								OPTIONAL,
	prach-Partitioning					PRACH-Partitioning					OPTIONAL,
	persistenceScalingFactorList		PersistenceScalingFactorList		OPTIONAL,
	ac-To-ASC-MappingTable			AC-To-ASC-MappingTable			OPTIONAL,
	modeSpecificInfo					CHOICE {
		fdd									SEQUENCE {
			primaryCPICH-TX-Power				PrimaryCPICH-TX-Power			OPTIONAL,
			constantValue						ConstantValue					OPTIONAL,
			prach-PowerOffset					PRACH-PowerOffset				OPTIONAL,
			rach-TransmissionParameters		RACH-TransmissionParameters	OPTIONAL,
			aich-Info							AICH-Info						OPTIONAL
		},
		tdd									NULL
	}
}

PRACH-SystemInformation-VHCR-r7 ::=	SEQUENCE {
	prach-RACH-Info						PRACH-RACH-Info-VHCR-r7,
	prach-Partitioning						PRACH-Partitioning-r7				OPTIONAL
}

PRACH-SystemInformation-LCR-r4 ::=	SEQUENCE {
	prach-RACH-Info-LCR					PRACH-RACH-Info-LCR-r4,
	rach-TransportFormatSet-LCR			TransportFormatSet-LCR			OPTIONAL,
	prach-Partitioning-LCR				PRACH-Partitioning-LCR-r4			OPTIONAL
}

PRACH-SystemInformation-LCR-v770ext ::= SEQUENCE {
	prach-RACH-Info-LCR						PRACH-RACH-Info-LCR-v770ext
}

PRACH-SystemInformationList ::=	SEQUENCE (SIZE (1..maxPRACH)) OF
										PRACH-SystemInformation

PRACH-SystemInformationList-VHCR-r7 ::= SEQUENCE (SIZE (1..maxPRACH)) OF
												PRACH-SystemInformation-VHCR-r7

PRACH-SystemInformationList-LCR-r4 ::=	SEQUENCE (SIZE (1..maxPRACH)) OF
												PRACH-SystemInformation-LCR-r4

PRACH-SystemInformationList-LCR-v770ext ::= SEQUENCE (SIZE (1..maxPRACH)) OF
													PRACH-SystemInformation-LCR-v770ext

PreambleRetransMax ::=				INTEGER (1..64)

PreambleScramblingCodeWordNumber ::=	INTEGER (0..15)

PreDefPhyChConfiguration ::=		SEQUENCE {
	ul-DPCH-InfoPredef					UL-DPCH-InfoPredef,
	dl-CommonInformationPredef		DL-CommonInformationPredef	OPTIONAL
}

PreDefPhyChConfiguration-v770ext ::= SEQUENCE {
	ul-DPCH-InfoPredef						UL-DPCH-InfoPredef-v770ext
}

PrimaryCCPCH-Info ::=				CHOICE {
	fdd									SEQUENCE {
		tx-DiversityIndicator				BOOLEAN
	},
	tdd									SEQUENCE {
		-- syncCase should be ignored for 1.28Mcps TDD mode
		syncCase 							CHOICE {
			syncCase1							SEQUENCE {
				timeslot							TimeslotNumber
			},
			syncCase2							SEQUENCE {
				timeslotSync2						TimeslotSync2
			}
		}																	OPTIONAL,
		cellParametersID					CellParametersID				OPTIONAL,
		sctd-Indicator						BOOLEAN
	}
}

PrimaryCCPCH-Info-r4 ::=			CHOICE {
	fdd									SEQUENCE {
		tx-DiversityIndicator				BOOLEAN
	},
	tdd									SEQUENCE {
		tddOption							CHOICE {
			tdd384-tdd768						SEQUENCE {
				syncCase							CHOICE {
					syncCase1							SEQUENCE {
						timeslot							TimeslotNumber
					},
					syncCase2							SEQUENCE {
						timeslotSync2						TimeslotSync2
					}
				}															OPTIONAL
			},
			tdd128								SEQUENCE {
				tstd-Indicator						BOOLEAN
			}
		},
		cellParametersID					CellParametersID				OPTIONAL,
		sctd-Indicator						BOOLEAN
	}
}

PrimaryCCPCH-Info-LCR-r4 ::=		SEQUENCE {
	tstd-Indicator						BOOLEAN,
	cellParametersID					CellParametersID				OPTIONAL,
	sctd-Indicator						BOOLEAN
}

-- For 1.28Mcps TDD, the following IE includes elements for the PCCPCH Info additional to those
-- in PrimaryCCPCH-Info
PrimaryCCPCH-Info-LCR-r4-ext ::=	SEQUENCE {
	tstd-Indicator						BOOLEAN
}

PrimaryCCPCH-InfoPost ::=			SEQUENCE {
	syncCase 							CHOICE {
		syncCase1							SEQUENCE {
			timeslot							TimeslotNumber
		},
		syncCase2							SEQUENCE {
			timeslotSync2						TimeslotSync2
		}
	},
	cellParametersID					CellParametersID,
	sctd-Indicator						BOOLEAN
}

PrimaryCCPCH-InfoPostTDD-LCR-r4 ::=	SEQUENCE {
	tstd-Indicator							BOOLEAN,
	cellParametersID						CellParametersID,
	sctd-Indicator							BOOLEAN
}

PrimaryCCPCH-TX-Power ::=			INTEGER (6..43)

PrimaryCPICH-Info ::=				SEQUENCE {
	primaryScramblingCode				PrimaryScramblingCode
}

PrimaryCPICH-TX-Power ::=			INTEGER (-10..50)

PrimaryScramblingCode ::=			INTEGER (0..511)

PuncturingLimit ::=				ENUMERATED {
										pl0-40, pl0-44, pl0-48, pl0-52, pl0-56,
										pl0-60, pl0-64, pl0-68, pl0-72, pl0-76,
										pl0-80, pl0-84, pl0-88, pl0-92, pl0-96, pl1 }

PUSCH-CapacityAllocationInfo ::=	SEQUENCE {
	pusch-Allocation					CHOICE {
		pusch-AllocationPending				NULL,
		pusch-AllocationAssignment			SEQUENCE {
			pusch-AllocationPeriodInfo			AllocationPeriodInfo,
			pusch-PowerControlInfo				UL-TargetSIR				OPTIONAL,
			configuration						CHOICE {
				old-Configuration					SEQUENCE {
					tfcs-ID								TFCS-IdentityPlain			DEFAULT 1,
					pusch-Identity						PUSCH-Identity
				},
				new-Configuration					SEQUENCE {
					pusch-Info							PUSCH-Info,
					pusch-Identity						PUSCH-Identity		OPTIONAL
				}
			}
		}
	}
}

PUSCH-CapacityAllocationInfo-r4 ::=	SEQUENCE {
	pusch-Allocation					CHOICE {
		pusch-AllocationPending				NULL,
		pusch-AllocationAssignment			SEQUENCE {
			pusch-AllocationPeriodInfo			AllocationPeriodInfo,
			pusch-PowerControlInfo				PUSCH-PowerControlInfo-r4	OPTIONAL,
			configuration						CHOICE {
				old-Configuration					SEQUENCE {
					tfcs-ID								TFCS-IdentityPlain			DEFAULT 1,
					pusch-Identity						PUSCH-Identity
				},
				new-Configuration					SEQUENCE {
					pusch-Info							PUSCH-Info-r4,
					pusch-Identity						PUSCH-Identity		OPTIONAL
				}
			}
		}
	}
}

PUSCH-CapacityAllocationInfo-r7 ::=	SEQUENCE {
	pusch-Allocation						CHOICE {
		pusch-AllocationPending				NULL,
		pusch-AllocationAssignment			SEQUENCE {
			pusch-AllocationPeriodInfo			AllocationPeriodInfo,
			pusch-PowerControlInfo				PUSCH-PowerControlInfo-r7	OPTIONAL,
			configuration						CHOICE {
				old-Configuration					SEQUENCE {
					tfcs-ID								TFCS-IdentityPlain			DEFAULT 1,
					pusch-Identity						PUSCH-Identity
				},
				new-Configuration					SEQUENCE {
					pusch-Info							PUSCH-Info-VHCR,
					pusch-Identity						PUSCH-Identity		OPTIONAL
				}
			}
		}
	}
}

PUSCH-Identity ::=					INTEGER (1..hiPUSCHidentities)

PUSCH-Info ::=						SEQUENCE {
	tfcs-ID								TFCS-IdentityPlain					DEFAULT 1,
	commonTimeslotInfo					CommonTimeslotInfo					OPTIONAL,
	pusch-TimeslotsCodes				UplinkTimeslotsCodes				OPTIONAL
}

PUSCH-Info-r4 ::=					SEQUENCE {
	tfcs-ID								TFCS-IdentityPlain					DEFAULT 1,
	commonTimeslotInfo					CommonTimeslotInfo					OPTIONAL,
	tddOption							CHOICE {
		tdd384								SEQUENCE {
			pusch-TimeslotsCodes				UplinkTimeslotsCodes		OPTIONAL
		},
		tdd128								SEQUENCE {
			pusch-TimeslotsCodes				UplinkTimeslotsCodes-LCR-r4	OPTIONAL
		}
	}
}

PUSCH-Info-VHCR ::=				SEQUENCE {
	tfcs-ID								TFCS-IdentityPlain					DEFAULT 1,
	commonTimeslotInfo					CommonTimeslotInfo					OPTIONAL,
	pusch-TimeslotsCodes-VHCR			UplinkTimeslotsCodes-VHCR			OPTIONAL
}

PUSCH-Info-LCR-r4 ::=				SEQUENCE {
	tfcs-ID								TFCS-IdentityPlain					DEFAULT 1,
	commonTimeslotInfo					CommonTimeslotInfo					OPTIONAL,
	pusch-TimeslotsCodes				UplinkTimeslotsCodes-LCR-r4		OPTIONAL
}

PUSCH-PowerControlInfo-r4 ::=		SEQUENCE {
	-- The IE ul-TargetSIR corresponds to PRX-PUSCHdes for 1.28Mcps TDD
	-- Actual value PRX-PUSCHdes = (value of IE "ul-TargetSIR" - 120)
	ul-TargetSIR						UL-TargetSIR,
	tddOption							CHOICE {
		tdd384								NULL,
		tdd128								SEQUENCE {
			tpc-StepSize						TPC-StepSizeTDD				OPTIONAL
		}
	}
}

PUSCH-PowerControlInfo-r7 ::=		SEQUENCE {
	-- The IE ul-TargetSIR corresponds to PRX-PUSCHdes for 1.28Mcps TDD
	-- Actual value PRX-PUSCHdes = (value of IE "ul-TargetSIR" - 120)
	ul-TargetSIR						UL-TargetSIR,
	tddOption							CHOICE {
		tdd384								NULL,
		tdd768								NULL,
		tdd128								SEQUENCE {
			tpc-StepSize						TPC-StepSizeTDD				OPTIONAL
		}
	}
}

PUSCH-SysInfo ::=					SEQUENCE {
	pusch-Identity						PUSCH-Identity,
	pusch-Info							PUSCH-Info,
	usch-TFS							TransportFormatSet					OPTIONAL,
	usch-TFCS							TFCS								OPTIONAL
}

PUSCH-SysInfo-VHCR ::=			SEQUENCE {
	pusch-Identity						PUSCH-Identity,
	pusch-Info-VHCR					PUSCH-Info-VHCR,
	usch-TransportChannelsInfo		USCH-TransportChannelsInfo		OPTIONAL,
	usch-TFCS							TFCS								OPTIONAL
}

PUSCH-SysInfo-HCR-r5 ::=			SEQUENCE {
	pusch-Identity						PUSCH-Identity,
	pusch-Info							PUSCH-Info,
	usch-TransportChannelsInfo		USCH-TransportChannelsInfo		OPTIONAL,
	usch-TFCS							TFCS								OPTIONAL
}

PUSCH-SysInfo-LCR-r4 ::=			SEQUENCE {
	pusch-Identity						PUSCH-Identity,
	pusch-Info							PUSCH-Info-LCR-r4,
	usch-TFS							TransportFormatSet					OPTIONAL,
	usch-TFCS							TFCS								OPTIONAL
}

PUSCH-SysInfoList ::=				SEQUENCE (SIZE (1..maxPUSCH)) OF
										PUSCH-SysInfo

PUSCH-SysInfoList-HCR-r5 ::=		SEQUENCE (SIZE (1..maxPUSCH)) OF PUSCH-SysInfo-HCR-r5

PUSCH-SysInfoList-LCR-r4 ::=		SEQUENCE (SIZE (1..maxPUSCH)) OF
										PUSCH-SysInfo-LCR-r4

PUSCH-SysInfoList-SFN ::=			SEQUENCE (SIZE (1..maxPUSCH)) OF
										SEQUENCE {
	pusch-SysInfo							PUSCH-SysInfo,
	sfn-TimeInfo							SFN-TimeInfo					OPTIONAL
}

PUSCH-SysInfoList-SFN-HCR-r5 ::=	SEQUENCE (SIZE (1..maxPUSCH)) OF
										SEQUENCE {
	pusch-SysInfo							PUSCH-SysInfo-HCR-r5,
	sfn-TimeInfo							SFN-TimeInfo					OPTIONAL
}

PUSCH-SysInfoList-SFN-LCR-r4 ::=	SEQUENCE (SIZE (1..maxPUSCH)) OF
										SEQUENCE {
	pusch-SysInfo							PUSCH-SysInfo-LCR-r4,
	sfn-TimeInfo							SFN-TimeInfo					OPTIONAL
}

PUSCH-SysInfoList-SFN-VHCR ::=	SEQUENCE (SIZE (1..maxPUSCH)) OF
										SEQUENCE {
	pusch-SysInfo-VHCR						PUSCH-SysInfo-VHCR,
	sfn-TimeInfo							SFN-TimeInfo					OPTIONAL
}

RACH-TransmissionParameters ::=	SEQUENCE {
	mmax								INTEGER (1..32),
	nb01Min								NB01,
	nb01Max								NB01
}

RadioLinkswithoutDPCHFDPCHInfo ::=	SEQUENCE {
	frameOffset							DPCH-FrameOffset
}

ReducedScramblingCodeNumber ::=		INTEGER (0..8191)

Reference-Beta-QPSK ::=				SEQUENCE {
	reference-Code-Rate					INTEGER (0..10),
	reference-Beta							INTEGER (-15..16)
}

Reference-Beta-16QAM ::=			SEQUENCE {
	reference-Code-Rate				INTEGER (0..10),
	reference-Beta						INTEGER (-15..16)
}

RepetitionPeriodAndLength ::=		CHOICE {
	repetitionPeriod1					NULL,
	-- repetitionPeriod2 could just as well be NULL also.
	repetitionPeriod2					INTEGER (1..1),
	repetitionPeriod4					INTEGER (1..3),
	repetitionPeriod8					INTEGER (1..7),
	repetitionPeriod16					INTEGER (1..15),
	repetitionPeriod32					INTEGER (1..31),
	repetitionPeriod64					INTEGER (1..63)
}

RepetitionPeriodLengthAndOffset ::= CHOICE {
	repetitionPeriod1						NULL,
	repetitionPeriod2						SEQUENCE {
		length									NULL,
		offset									INTEGER (0..1)
	},
	repetitionPeriod4						SEQUENCE {
		length									INTEGER (1..3),
		offset									INTEGER (0..3)
	},
	repetitionPeriod8						SEQUENCE {
		length									INTEGER (1..7),
		offset									INTEGER (0..7)
	},
	repetitionPeriod16						SEQUENCE {
		length									INTEGER (1..15),
		offset									INTEGER (0..15)
	},
	repetitionPeriod32						SEQUENCE {
		length									INTEGER (1..31),
		offset									INTEGER (0..31)
	},
	repetitionPeriod64						SEQUENCE {
		length									INTEGER (1..63),
		offset									INTEGER (0..63)
	}
}

RepetitionPeriodAndLengthForSPS ::=	CHOICE {
	repetitionPeriod1						NULL,
	-- repetitionPeriod2 could just as well be NULL also.
	repetitionPeriod2						INTEGER (1..1),
	repetitionPeriod4						INTEGER (1..3),
	repetitionPeriod8						INTEGER (1..7),
	repetitionPeriod16						INTEGER (1..15),
	repetitionPeriod32						INTEGER (1..31)
}

ReplacedPDSCH-CodeInfo ::=		SEQUENCE {
	tfci-Field2						MaxTFCI-Field2Value,
	spreadingFactor					SF-PDSCH,
	codeNumber							CodeNumberDSCH,
	multiCodeInfo						MultiCodeInfo
}

ReplacedPDSCH-CodeInfoList ::=	SEQUENCE (SIZE (1..maxTFCI-2-Combs)) OF
										ReplacedPDSCH-CodeInfo

RepPerLengthOffset-PICH ::=		CHOICE {
	rpp4-2								INTEGER (0..3),
	rpp8-2								INTEGER (0..7),
	rpp8-4								INTEGER (0..7),
	rpp16-2								INTEGER (0..15),
	rpp16-4								INTEGER (0..15),
	rpp32-2								INTEGER (0..31),
	rpp32-4								INTEGER (0..31),
	rpp64-2								INTEGER (0..63),
	rpp64-4								INTEGER (0..63)
}

RepPerLengthOffset-MICH ::=		CHOICE {
	rpp4-2								INTEGER (0..3),
	rpp8-2								INTEGER (0..7),
	rpp8-4								INTEGER (0..7),
	rpp16-2								INTEGER (0..15),
	rpp16-4								INTEGER (0..15),
	rpp32-2								INTEGER (0..31),
	rpp32-4								INTEGER (0..31),
	rpp64-2								INTEGER (0..63),
	rpp64-4								INTEGER (0..63)
}

RestrictedTrCH ::=					SEQUENCE {
	dl-restrictedTrCh-Type			DL-TrCH-Type,
	restrictedDL-TrCH-Identity		TransportChannelIdentity,
	allowedTFIList						AllowedTFI-List
}

RestrictedTrCH-InfoList ::=		SEQUENCE (SIZE(1..maxTrCH)) OF
										RestrictedTrCH

RL-AdditionInformation ::=		SEQUENCE {
	primaryCPICH-Info					PrimaryCPICH-Info,
	dl-DPCH-InfoPerRL					DL-DPCH-InfoPerRL,
	-- dummy and dummy2 are not used in this version of specification
	-- and the IEs should be ignored.
	dummy								BOOLEAN,
	dummy2								SCCPCH-InfoForFACH					OPTIONAL
}

RL-AdditionInformation-r6 ::=		SEQUENCE {
	primaryCPICH-Info					PrimaryCPICH-Info,
	cell-Id								CellIdentity						OPTIONAL,
	dl-dpchInfo							CHOICE {
		dl-DPCH-InfoPerRL						DL-DPCH-InfoPerRL-r5,
		dl-FDPCH-InfoPerRL						DL-FDPCH-InfoPerRL-r6
	},
	e-HICH-Information					E-HICH-Information					OPTIONAL,
	e-RGCH-Information					E-RGCH-Information					OPTIONAL
}

RL-AdditionInformation-r7 ::=		SEQUENCE {
	primaryCPICH-Info					PrimaryCPICH-Info,
	cell-Id								CellIdentity						OPTIONAL,
	dl-dpchInfo							CHOICE {
		dl-DPCH-InfoPerRL						DL-DPCH-InfoPerRL-r5,
		dl-FDPCH-InfoPerRL						DL-FDPCH-InfoPerRL-r7
	},
	e-HICH-Information					E-HICH-Information					OPTIONAL,
	e-RGCH-Information					E-RGCH-Information					OPTIONAL
}

RL-AdditionInformation-r8 ::=		SEQUENCE {
	primaryCPICH-Info					PrimaryCPICH-Info,
	cell-Id								CellIdentity						OPTIONAL,
	dl-dpchInfo							CHOICE {
		dl-DPCH-InfoPerRL						DL-DPCH-InfoPerRL-r5,
		dl-FDPCH-InfoPerRL						DL-FDPCH-InfoPerRL-r7
	},
	e-HICH-Information					E-HICH-Information					OPTIONAL,
	e-RGCH-Information					E-RGCH-Information					OPTIONAL,
	targetCellPreconfigInfo			TargetCellPreconfigInfo			OPTIONAL
}

RL-AdditionInformation-r9 ::=		SEQUENCE {
	primaryCPICH-Info					PrimaryCPICH-Info,
	cell-Id								CellIdentity						OPTIONAL,
	dl-dpchInfo							CHOICE {
		dl-DPCH-InfoPerRL						DL-DPCH-InfoPerRL-r5,
		dl-FDPCH-InfoPerRL						DL-FDPCH-InfoPerRL-r7
	},
	e-HICH-Information					E-HICH-Information					OPTIONAL,
	e-RGCH-Information					E-RGCH-Information					OPTIONAL,
	targetCellPreconfigInfo			TargetCellPreconfigInfo-r9		OPTIONAL
}

RL-AdditionInformation-r10 ::=		SEQUENCE {
	primaryCPICH-Info					PrimaryCPICH-Info,
	cell-Id								CellIdentity						OPTIONAL,
	dl-dpchInfo							CHOICE {
		dl-DPCH-InfoPerRL						DL-DPCH-InfoPerRL-r5,
		dl-FDPCH-InfoPerRL						DL-FDPCH-InfoPerRL-r7
	},
	e-HICH-Information					E-HICH-Information					OPTIONAL,
	e-RGCH-Information					E-RGCH-Information					OPTIONAL,
	targetCellPreconfigInfo			TargetCellPreconfigInfo-r10		OPTIONAL
}

RL-AdditionInformation-vb50ext ::=	SEQUENCE {
	targetCellPreconfigInfo				TargetCellPreconfigInfo-vb50ext	OPTIONAL
}

RL-AdditionInformation-r11 ::=	SEQUENCE {
	primaryCPICH-Info					PrimaryCPICH-Info,
	cell-Id								CellIdentity						OPTIONAL,
	dl-dpchInfo							CHOICE {
		dl-DPCH-InfoPerRL						DL-DPCH-InfoPerRL-r5,
		dl-FDPCH-InfoPerRL						DL-FDPCH-InfoPerRL-r7
	},
	e-HICH-Information					E-HICH-Information-r11			OPTIONAL,
	e-RGCH-Information					E-RGCH-Information					OPTIONAL,
	f-TPICH-Information				F-TPICH-Information				OPTIONAL,
	targetCellPreconfigInfo			TargetCellPreconfigInfo-r11		OPTIONAL
}

RL-AdditionInformation-r12 ::=	SEQUENCE {
	primaryCPICH-Info					PrimaryCPICH-Info,
	cell-Id								CellIdentity						OPTIONAL,
	dl-dpchInfo							CHOICE {
		dl-DPCH-InfoPerRL						DL-DPCH-InfoPerRL-ASU,
		dl-FDPCH-InfoPerRL						DL-FDPCH-InfoPerRL-r7,
		radioLinkswithoutDPCHFDPCHInfo		RadioLinkswithoutDPCHFDPCHInfo
	},
	e-HICH-Information					E-HICH-Information-r11			OPTIONAL,
	e-RGCH-Information					E-RGCH-Information					OPTIONAL,
	f-TPICH-Information				F-TPICH-Information				OPTIONAL,
	targetCellPreconfigInfo			TargetCellPreconfigInfo-r12		OPTIONAL
}

RL-AdditionInformation-r13 ::=	SEQUENCE {
	primaryCPICH-Info					PrimaryCPICH-Info,
	cell-Id								CellIdentity						OPTIONAL,
	dl-dpchInfo						CHOICE {
		dl-DPCH-InfoPerRL					DL-DPCH-InfoPerRL-ASU,
		dl-FDPCH-InfoPerRL					DL-FDPCH-InfoPerRL-r13,
		radioLinkswithoutDPCHFDPCHInfo	RadioLinkswithoutDPCHFDPCHInfo
	},
	e-HICH-Information					E-HICH-Information-r11			OPTIONAL,
	e-RGCH-Information					E-RGCH-Information					OPTIONAL,
	f-TPICH-Information				F-TPICH-Information				OPTIONAL,
	targetCellPreconfigInfo			TargetCellPreconfigInfo-r13		OPTIONAL
}

RL-AdditionInformation-v6b0ext ::=	SEQUENCE {
		sttdIndication						STTDIndication					OPTIONAL
}

RL-AdditionInformation-v890ext ::=	SEQUENCE {
	targetCellPreconfigInfo				TargetCellPreconfigInfo-v890ext	OPTIONAL
}

RL-AdditionInformation-v950ext ::=	SEQUENCE {
	targetCellPreconfigInfo				TargetCellPreconfigInfo-v950ext	OPTIONAL
}

RL-AdditionInformationList ::=	SEQUENCE (SIZE (1..maxRL-1)) OF
										RL-AdditionInformation

RL-AdditionInformationList-r6 ::=	SEQUENCE (SIZE (1..maxRL-1)) OF
											RL-AdditionInformation-r6

RL-AdditionInformationList-r7 ::=	SEQUENCE (SIZE (1..maxRL-1)) OF
											RL-AdditionInformation-r7

RL-AdditionInformation-list-v6b0ext ::= SEQUENCE (SIZE (1..maxRL)) OF
												RL-AdditionInformation-v6b0ext

RL-AdditionInformationList-r8 ::=	SEQUENCE (SIZE(1..maxRL-1)) OF
											RL-AdditionInformation-r8

RL-AdditionInformationList-v890ext ::=	SEQUENCE (SIZE (1..maxRL-1)) OF
												RL-AdditionInformation-v890ext

RL-AdditionInformationList-r9 ::=	SEQUENCE (SIZE(1..maxRL-1)) OF
											RL-AdditionInformation-r9

RL-AdditionInformationList-v950ext ::=	SEQUENCE (SIZE(1..maxRL-1)) OF
												RL-AdditionInformation-v950ext

RL-AdditionInformationList-r10 ::=	SEQUENCE (SIZE(1..maxRL-1)) OF
											RL-AdditionInformation-r10

RL-AdditionInformationList-vb50ext ::=	SEQUENCE (SIZE(1..maxRL-1)) OF
												RL-AdditionInformation-vb50ext

RL-AdditionInformationList-r11 ::=	SEQUENCE (SIZE(1..maxRL-1)) OF
											RL-AdditionInformation-r11

RL-AdditionInformationList-r12 ::=	SEQUENCE (SIZE(1..maxRL-1)) OF
											RL-AdditionInformation-r12

RL-AdditionInformationList-r13 ::=	SEQUENCE (SIZE(1..maxRL-1)) OF
											RL-AdditionInformation-r13

RL-AdditionInformationList-SecULFreq ::=	SEQUENCE (SIZE(1..maxEDCHRL-1)) OF
												RL-AdditionInformation-SecULFreq

RL-AdditionInformationList-SecULFreq-r12 ::=	SEQUENCE (SIZE(1..maxEDCHRL-1)) OF
														RL-AdditionInformation-SecULFreq-r12

RL-AdditionInformationList-SecULFreq-r13 ::=	SEQUENCE (SIZE(1..maxEDCHRL-1)) OF
														RL-AdditionInformation-SecULFreq-r13

RL-AdditionInformation-SecULFreq ::=	SEQUENCE {
	primaryCPICH-Info						PrimaryCPICH-Info,
	cell-id									CellIdentity				OPTIONAL,
	dl-FDPCH-InfoPerRL 					DL-FDPCH-InfoPerRL-r7,
	e-HICH-Information						E-HICH-Information,
	e-RGCH-Information						E-RGCH-Information			OPTIONAL
}

RL-AdditionInformation-SecULFreq-r12 ::=	SEQUENCE {
	primaryCPICH-Info							PrimaryCPICH-Info,
	cell-id										CellIdentity				OPTIONAL,
	dl-FDPCH-InfoPerRL 						DL-FDPCH-InfoPerRL-r7,
	e-HICH-Information							E-HICH-Information,
	e-RGCH-Information							E-RGCH-Information			OPTIONAL,
	radioLinkswithoutDPCHFDPCHIndicator		NULL						OPTIONAL
}

RL-AdditionInformation-SecULFreq-r13 ::=	SEQUENCE {
	primaryCPICH-Info							PrimaryCPICH-Info,
	cell-id										CellIdentity				OPTIONAL,
	dl-FDPCH-InfoPerRL 						DL-FDPCH-InfoPerRL-r13,
	e-HICH-Information							E-HICH-Information,
	e-RGCH-Information							E-RGCH-Information			OPTIONAL,
	radioLinkswithoutDPCHFDPCHIndicator		NULL						OPTIONAL
}

RL-IdentifierList ::=				SEQUENCE (SIZE (1..maxRL)) OF
										PrimaryCPICH-Info

RL-RemovalInformationList ::=		SEQUENCE (SIZE (1..maxRL)) OF
										PrimaryCPICH-Info

RL-RemovalInformationList-SecULFreq ::= SEQUENCE (SIZE(1..maxEDCHRL)) OF
												PrimaryCPICH-Info

RPP ::=								ENUMERATED {
										mode0, mode1 }

S-Field ::=						ENUMERATED {
										e1bit, e2bits }

SCCPCH-ChannelisationCode ::=		ENUMERATED {
										cc16-1, cc16-2, cc16-3, cc16-4,
										cc16-5, cc16-6, cc16-7, cc16-8,
										cc16-9, cc16-10, cc16-11, cc16-12,
										cc16-13, cc16-14, cc16-15, cc16-16 }

SCCPCH-ChannelisationCode-VHCR ::=	ENUMERATED {
										cc32-1, cc32-2, cc32-3, cc32-4,
										cc32-5, cc32-6, cc32-7, cc32-8,
										cc32-9, cc32-10, cc32-11, cc32-12,
										cc32-13, cc32-14, cc32-15, cc32-16,
										cc32-17, cc32-18, cc32-19, cc32-20,
										cc32-21, cc32-22, cc32-23, cc32-24,
										cc32-25, cc32-26, cc32-27, cc32-28,
										cc32-29, cc32-30, cc32-31, cc32-32 }

SCCPCH-ChannelisationCodeList ::=	SEQUENCE (SIZE (1..16)) OF
											SCCPCH-ChannelisationCode

SCCPCH-ChannelisationCodeList-VHCR ::=	SEQUENCE (SIZE (1..32)) OF
												SCCPCH-ChannelisationCode-VHCR

SCCPCH-InfoForFACH ::=			SEQUENCE {
	secondaryCCPCH-Info				SecondaryCCPCH-Info,
	tfcs								TFCS,
	modeSpecificInfo					CHOICE {
		fdd									SEQUENCE {
			fach-PCH-InformationList			FACH-PCH-InformationList,
			sib-ReferenceListFACH				SIB-ReferenceListFACH
		},
		tdd									SEQUENCE {
			fach-PCH-InformationList			FACH-PCH-InformationList
		}
	}
}

SCCPCH-InfoForFACH-r4 ::=			SEQUENCE {
	secondaryCCPCH-Info				SecondaryCCPCH-Info-r4,
	tfcs								TFCS,
	fach-PCH-InformationList			FACH-PCH-InformationList,
	modeSpecificInfo					CHOICE {
		fdd									SEQUENCE {
			sib-ReferenceListFACH				SIB-ReferenceListFACH
		},
		tdd									NULL
	}
}

SCCPCH-SystemInformation ::=		SEQUENCE {
	secondaryCCPCH-Info				SecondaryCCPCH-Info,
	tfcs								TFCS								OPTIONAL,
	fach-PCH-InformationList			FACH-PCH-InformationList			OPTIONAL,
	pich-Info							PICH-Info							OPTIONAL
}

SCCPCH-SystemInformation-LCR-r4-ext ::=	SEQUENCE {
	secondaryCCPCH-LCR-Extensions			SecondaryCCPCH-Info-LCR-r4-ext,
	-- pich-Info in the SCCPCH-SystemInformation IE shall be absent,
	-- and instead the following used.
	pich-Info									PICH-Info-LCR-r4			OPTIONAL
}

SCCPCH-SystemInformation-HCR-VHCR-r7 ::=	SEQUENCE {
	secondaryCCPCH-Info						SecondaryCCPCH-Info-HCR-VHCR-r7,
	tfcs										TFCS								OPTIONAL,
	fach-PCH-InformationList					FACH-PCH-InformationList			OPTIONAL,
	pich-Info									PICH-Info-HCR-VHCR-r7				OPTIONAL
}

SCCPCH-SystemInformationList ::=	SEQUENCE (SIZE (1..maxSCCPCH)) OF
										SCCPCH-SystemInformation

SCCPCH-SystemInformationList-HCR-VHCR-r7 ::=	SEQUENCE (SIZE (1..maxSCCPCH)) OF
														SCCPCH-SystemInformation-HCR-VHCR-r7

-- SCCPCH-SystemInformationList-LCR-r4-ext includes elements additional to those in
-- SCCPCH-SystemInformationList for the 1.28Mcps TDD. The order of the IEs
-- indicates which SCCPCH-SystemInformation-LCR-r4-ext IE extends which
-- SCCPCH-SystemInformation IE.
SCCPCH-SystemInformationList-LCR-r4-ext ::=	SEQUENCE (SIZE (1..maxSCCPCH)) OF
													SCCPCH-SystemInformation-LCR-r4-ext

-- The SCCPCH-SystemInformation-MBMS-r6 is used for an S-CCPCH dedicated for MBMS purposes.
SCCPCH-SystemInformation-MBMS-r6 ::=	SEQUENCE {
	secondaryCCPCHInfo-MBMS				SecondaryCCPCHInfo-MBMS-r6,
	transportFormatCombinationSet		TFCS,
	fachCarryingMCCH						SEQUENCE {
		mcch-transportFormatSet				TransportFormatSet,
		mcch-ConfigurationInfo				MBMS-MCCH-ConfigurationInfo-r6
	},
	fachCarryingMTCH-List					MBMS-FACHCarryingMTCH-List			OPTIONAL,
	-- If schedulingInformation is provided
	fachCarryingMSCH						SEQUENCE {
		msch-transportFormatSet				TransportFormatSet,
		-- dummy is not used in this version of the specification, it should
		-- not be sent and if received it should be ignored.
		dummy									MBMS-MSCH-ConfigurationInfo-r6
	}		OPTIONAL
}

-- The SCCPCH-SystemInformation-MBMS-r7 is used for an S-CCPCH dedicated for MBMS purposes.
SCCPCH-SystemInformation-MBMS-r7 ::=	SEQUENCE {
	secondaryCCPCHInfo-MBMS				SecondaryCCPCHInfo-MBMS-r7,
	transportFormatCombinationSet		TFCS,
	fachCarryingMCCH						SEQUENCE {
		mcch-transportFormatSet				TransportFormatSet,
		mcch-ConfigurationInfo				MBMS-MCCH-ConfigurationInfo-r6
	},
	fachCarryingMTCH-List					MBMS-FACHCarryingMTCH-List			OPTIONAL,
	-- If schedulingInformation is provided
	fachCarryingMSCH						SEQUENCE {
		msch-transportFormatSet				TransportFormatSet
	}		OPTIONAL
}

S-CPICH-PowerOffset-MIMO ::=			INTEGER (-6..0)

S-CPICH-PowerOffset-4x4MIMO ::=		INTEGER (-12..0)

ScheduledTransmissionConfiguration ::=	SEQUENCE {
	common-E-DCH-ResourceInfoListExt			SEQUENCE (SIZE (1..maxEDCHs)) OF
										Common-E-DCH-ResourceInfoListExt
}

ScramblingCodeChange ::=			ENUMERATED {
										codeChange, noCodeChange }

ScramblingCodeType ::=			ENUMERATED {
										shortSC,
										longSC }

SecondaryCCPCH-Info ::=		SEQUENCE {
	modeSpecificInfo				CHOICE {
		fdd								SEQUENCE {
			-- dummy1 is not used in this version of the specification and should be ignored.
			dummy1							PCPICH-UsageForChannelEst,
			-- dummy2 is not used in this version of the specification.  It should not
			-- be sent and if received it should be ignored.
			dummy2							SecondaryCPICH-Info				OPTIONAL,
			secondaryScramblingCode			SecondaryScramblingCode			OPTIONAL,
			sttd-Indicator					BOOLEAN,
			sf-AndCodeNumber				SF256-AndCodeNumber,
			pilotSymbolExistence			BOOLEAN,
			tfci-Existence					BOOLEAN,
			positionFixedOrFlexible		PositionFixedOrFlexible,
			timingOffset					TimingOffset					DEFAULT 0
		},
		tdd 							SEQUENCE {
			-- TABULAR: the offset is included in CommonTimeslotInfoSCCPCH
			commonTimeslotInfo				CommonTimeslotInfoSCCPCH,
			individualTimeslotInfo		IndividualTimeslotInfo,
			channelisationCode				SCCPCH-ChannelisationCodeList
		}
	}
}

SecondaryCCPCH-Info-r4 ::=	SEQUENCE {
	modeSpecificInfo				CHOICE {
		fdd								SEQUENCE {
			secondaryScramblingCode		SecondaryScramblingCode			OPTIONAL,
			sttd-Indicator					BOOLEAN,
			sf-AndCodeNumber				SF256-AndCodeNumber,
			pilotSymbolExistence			BOOLEAN,
			tfci-Existence					BOOLEAN,
			positionFixedOrFlexible		PositionFixedOrFlexible,
			timingOffset					TimingOffset					DEFAULT 0
		},
		tdd 							SEQUENCE {
			-- TABULAR: the offset is included in CommonTimeslotInfoSCCPCH
			commonTimeslotInfo				CommonTimeslotInfoSCCPCH,
			tddOption						CHOICE {
				tdd384							SEQUENCE {
					individualTimeslotInfo		IndividualTimeslotInfo
				},
				tdd128							SEQUENCE {
					individualTimeslotInfo		IndividualTimeslotInfo-LCR-r4
				}
			},
			channelisationCode				SCCPCH-ChannelisationCodeList
		}
	}
}

SecondaryCCPCH-Info-HCR-VHCR-r7 ::=	SEQUENCE {
	modeSpecificInfo						CHOICE {
		tdd384									SEQUENCE {
			individualTimeslotInfo				IndividualTimeslotInfo-r7,
			channelisationCode						SCCPCH-ChannelisationCodeList
		},
		tdd768									SEQUENCE {
			individualTimeslotInfo				IndividualTimeslotInfo-VHCR,
			channelisationCode						SCCPCH-ChannelisationCodeList-VHCR
		}
	}
}

SecondaryCCPCH-Info-LCR-r4-ext ::=	SEQUENCE {
	individualTimeslotLCR-Ext				IndividualTimeslotInfo-LCR-r4-ext
}

SecondaryCCPCHFrameType2Info ::=	SEQUENCE {
	subFrameNumber						INTEGER (0..4),
	dl-ChannelisationCodes			DL-ChannelCodes-MBSFN-IMB384,
	modulation							CHOICE {
		modQPSK								NULL,
		mod16QAM							SEQUENCE {
			cpich-SecCCPCH-PowerOffset			INTEGER (-11..4)
		}
	}
}

SecondaryCCPCHInfo-MBMS-r6 ::=		SEQUENCE {
	modeSpecificInfo						CHOICE {
		fdd										SEQUENCE {
			secondaryScramblingCode				SecondaryScramblingCode		OPTIONAL,
			sttd-Indicator							BOOLEAN,
			sf-AndCodeNumber						SF256-AndCodeNumber,
			timingOffset							TimingOffset					DEFAULT 0
		},
		tdd384									SEQUENCE {
			commonTimeslotInfoMBMS				CommonTimeslotInfoMBMS,
			downlinkTimeslotsCodes				DownlinkTimeslotsCodes
		},
		tdd128									SEQUENCE {
			commonTimeslotInfoMBMS				CommonTimeslotInfoMBMS,
			downlinkTimeslotsCodes				DownlinkTimeslotsCodes-LCR-r4
		}
	}
}

SecondaryCCPCHInfo-MBMS-r7 ::=		SEQUENCE {
	modeSpecificInfo						CHOICE {
		-- The CHOICE fdd is used for both "fdd" and "3.84 Mcps TDD MBSFN IMB"
		fdd										SEQUENCE {
			-- The IE secondaryScramblingCode is not applicable for "3.84 Mcps TDD MBSFN IMB"
			secondaryScramblingCode				SecondaryScramblingCode			OPTIONAL,
			-- The IE sttd-Indicator is not applicable for cells operating in MBSFN mode,
			-- the UE behaviour is unspecified
			sttd-Indicator							BOOLEAN,
			sf-AndCodeNumber						SF256-AndCodeNumber,
			-- The IE timingOffset is not applicable for "3.84 Mcps TDD MBSFN IMB"
			timingOffset							TimingOffset					DEFAULT 0,
			modulation								CHOICE {
				modQPSK									NULL,
				-- The CHOICE mod16QAM is not applicable for MCCH in "3.84 Mcps TDD MBSFN IMB"
				mod16QAM								INTEGER (-11..4)
			}	OPTIONAL
		},
		tdd384									SEQUENCE {
			commonTimeslotInfoMBMS				CommonTimeslotInfoMBMS,
			downlinkTimeslotsCodes				DownlinkTimeslotsCodes-r7,
			modulation								ENUMERATED { modQPSK, mod16QAM }
		},
		tdd768									SEQUENCE {
			commonTimeslotInfoMBMS				CommonTimeslotInfoMBMS,
			downlinkTimeslotsCodes				DownlinkTimeslotsCodes-VHCR,
			modulation								ENUMERATED { modQPSK, mod16QAM }
		},
		tdd128									SEQUENCE {
			commonTimeslotInfoMBMS				CommonTimeslotInfoMBMS,
			downlinkTimeslotsCodes				DownlinkTimeslotsCodes-LCR-r4,
			mbsfnSpecialTimeSlot					TimeSlotLCR-ext					OPTIONAL,
			modulation								ENUMERATED { modQPSK, mod16QAM }
		}
	}
}

SecondaryCCPCHInfoDiff-MBMS ::=		SEQUENCE {
	secondaryScramblingCode				SecondaryScramblingCode		OPTIONAL,
	sttd-Indicator							BOOLEAN,
	sf-AndCodeNumber						SF256-AndCodeNumber			OPTIONAL,
	timingOffset							TimingOffset					OPTIONAL
}

SecondaryCPICH-Info ::=				SEQUENCE {
	secondaryDL-ScramblingCode			SecondaryScramblingCode		OPTIONAL,
	channelisationCode						ChannelisationCode256
}

SecondaryScramblingCode ::=			INTEGER (1..15)

SecondaryCellMIMOparametersFDD ::=	CHOICE {
	continue								NULL,
	newConfiguration						SEQUENCE {
			mimoN-M-Ratio						MIMO-N-M-Ratio					OPTIONAL,
			mimoPilotConfiguration			MIMO-PilotConfiguration-r9	OPTIONAL
	}
}

SecondaryCellMIMOparametersFDD-v950ext ::=	SEQUENCE {
	precodingWeightSetRestriction				ENUMERATED { true }		OPTIONAL
}

SecondaryCellMIMOparametersFDD-r10 ::=	CHOICE {
	continue									NULL,
	newConfiguration							SEQUENCE {
			mimoN-M-Ratio							MIMO-N-M-Ratio					OPTIONAL,
			mimoPilotConfiguration				MIMO-PilotConfiguration-r9	OPTIONAL,
			precodingWeightSetRestriction			ENUMERATED { true }			OPTIONAL
	}
}

SecondaryCell4x4MIMOparametersFDD ::=	SEQUENCE {
	configurationInfo							CHOICE {
		continue									NULL,
		newConfiguration							SEQUENCE {
			mimoN-M-Ratio								MIMO-N-M-Ratio					OPTIONAL,
			mimoPilotConfiguration					MIMO4x4-PilotConfiguration	OPTIONAL,
			precodingWeightSetRestriction				BIT STRING (SIZE (64))		OPTIONAL
		}
	}
}

SecondInterleavingMode ::=		ENUMERATED {
										frameRelated, timeslotRelated }

ServingCellChangeMACreset ::=		BOOLEAN

ServingCellChangeMsgType ::=		ENUMERATED {
										radioBearerSetup,
										radioBearerReconfiguration,
										transportChannelReconfiguration,
										physicalChannelReconfiguration }

ServingCellChangeParameters ::=	SEQUENCE {
	servingCellChangeMACreset			ServingCellChangeMACreset,
	servingCellChangeMsgType			ServingCellChangeMsgType,
	servingCellChangeTrId				ServingCellChangeTrId
}

ServingCellChangeParameters-r12 ::=	SEQUENCE {
	servingCellChangeMACreset				ServingCellChangeMACreset,
	servingCellChangeMsgType				ServingCellChangeMsgType,
	servingCellChangeTrId					ServingCellChangeTrId,
	enhancedServingCellChangeforEvent1CsupportIndicator	ENUMERATED { true }	OPTIONAL
}
ServingCellChangeTrId ::=			INTEGER (0..3)

SF8Codes ::=						ENUMERATED {
										cc8-1, cc8-2, cc8-3, cc8-4, cc8-5, cc8-6,  cc8-7, cc8-8}

SF16Codes ::=						ENUMERATED {
										cc16-1, cc16-2, cc16-3, cc16-4, cc16-5, cc16-6, cc16-7,
										cc16-8}

SF16Codes2 ::=						ENUMERATED {
										cc16-1, cc16-2, cc16-3, cc16-4, cc16-5, cc16-6, cc16-7,
										cc16-8, cc16-9, cc16-10, cc16-11, cc16-12, cc16-13, cc16-14,
										cc16-15, cc16-16}

SF32Codes ::=						ENUMERATED {
										cc32-1, cc32-2, cc32-3, cc32-4, cc32-5, cc32-6, cc32-7,
										cc32-8, cc32-9, cc32-10, cc32-11, cc32-12, cc32-13, cc32-14,
										cc32-15, cc32-16}

-- SF256-AndCodeNumber encodes both "Spreading factor" and "Code Number"
SF256-AndCodeNumber ::=			CHOICE {
	sf4									INTEGER (0..3),
	sf8									INTEGER (0..7),
	sf16								INTEGER (0..15),
	sf32								INTEGER (0..31),
	sf64								INTEGER (0..63),
	sf128								INTEGER (0..127),
	sf256								INTEGER (0..255)
}

-- SF512-AndCodeNumber encodes both "Spreading factor" and "Code Number"
SF512-AndCodeNumber ::=			CHOICE {
	sf4									INTEGER (0..3),
	sf8									INTEGER (0..7),
	sf16								INTEGER (0..15),
	sf32								INTEGER (0..31),
	sf64								INTEGER (0..63),
	sf128								INTEGER (0..127),
	sf256								INTEGER (0..255),
	sf512								INTEGER (0..511)
}

-- SF512-AndPilot encodes both "Spreading factor" and "Number of bits for Pilot bits"
SF512-AndPilot ::=					CHOICE {
	sfd4								NULL,
	sfd8								NULL,
	sfd16								NULL,
	sfd32								NULL,
	sfd64								NULL,
	sfd128								PilotBits128,
	sfd256								PilotBits256,
	sfd512								NULL
}

SF512-AndPilot-r12 ::=			CHOICE {
	sfd4								NULL,
	sfd8								NULL,
	sfd16								NULL,
	sfd32								NULL,
	sfd64								NULL,
	sfd128								PilotBits128-r12,
	sfd256								PilotBits256-r12,
	sfd512								NULL
}

SF-PDSCH ::=						ENUMERATED {
										sfp4, sfp8, sfp16, sfp32,
										sfp64, sfp128, sfp256 }

SF-PRACH ::=						ENUMERATED {
										sfpr32, sfpr64, sfpr128, sfpr256 }

SFN-TimeInfo ::=					SEQUENCE {
	activationTimeSFN					INTEGER (0..4095),
	physChDuration						DurationTimeInfo
}

-- actual scheduling value = 2(signalled value +1) and is the periodicity of sending
-- special burst frames
SpecialBurstScheduling ::=		INTEGER (0..7)

SpreadingFactor ::=				ENUMERATED {
										sf4, sf8, sf16, sf32,
										sf64, sf128, sf256 }

SPS-Information-TDD128-r8 ::=		SEQUENCE {
	e-dch-SPS-Info						E-DCH-SPS-Information-TDD128			OPTIONAL,
	hs-dsch-SPS-Info					HS-DSCH-SPS-Information-TDD128		OPTIONAL
}

SRB-delay ::=						INTEGER (0..7)

SSDT-CellIdentity ::=				ENUMERATED {
										ssdt-id-a, ssdt-id-b, ssdt-id-c,
										ssdt-id-d, ssdt-id-e, ssdt-id-f,
										ssdt-id-g, ssdt-id-h }

SSDT-Information ::=				SEQUENCE {
	s-Field								S-Field,
	codeWordSet						CodeWordSet
}

SSDT-Information-r4 ::=			SEQUENCE {
	s-Field								S-Field,
	codeWordSet						CodeWordSet,
	ssdt-UL-r4							SSDT-UL									OPTIONAL
}

SSDT-UL ::=						ENUMERATED {
										ul, ul-AndDL }

StandaloneMidambleInfo-TDD128 ::=	SEQUENCE {
		-- Actual value midambleConfiguration = IE value * 2
	midambleConfiguration					INTEGER (1..8),
	midambleShift							INTEGER (0..15),
	timeSlotInformation					BIT STRING (SIZE (5)),
	activationTime							ActivationTime,
	subframeNum							INTEGER (0..1),
	repetitionPeriod						ENUMERATED {
												v1, v2, v4, v8,
												v16, v32, v64, spare},
	referenceBeta							INTEGER (-15..16)	OPTIONAL
}

STTDIndication ::=					ENUMERATED { true }

SynchronisationParameters-r4 ::=	SEQUENCE {
	sync-UL-CodesBitmap				BIT STRING {
											code7(0),
											code6(1),
											code5(2),
											code4(3),
											code3(4),
											code2(5),
											code1(6),
											code0(7)
											} (SIZE (8)),
	fpach-Info							FPACH-Info-r4,
	-- Actual value prxUpPCHdes = IE value - 120
	prxUpPCHdes						INTEGER (0..62),
	sync-UL-Procedure					SYNC-UL-Procedure-r4	OPTIONAL
}

Sync-UL-Codes-Bitmap ::=			BIT STRING {
										code7(0),
										code6(1),
										code5(2),
										code4(3),
										code3(4),
										code2(5),
										code1(6),
										code0(7)
									} (SIZE (8))

SYNC-UL-Procedure-r4 ::=			SEQUENCE {
	max-SYNC-UL-Transmissions			ENUMERATED { tr1, tr2, tr4, tr8 },
	powerRampStep						INTEGER (0..3)
}

SYNC-UL-Info-r4 ::=				SEQUENCE {
	sync-UL-Codes-Bitmap				Sync-UL-Codes-Bitmap,
	-- Actual value prxUpPCHdes = IE value - 120
	prxUpPCHdes						INTEGER (0..62),
	powerRampStep						INTEGER (0..3),
	max-SYNC-UL-Transmissions			ENUMERATED { tr1, tr2, tr4, tr8 },
	mmax								INTEGER(1..32)
}

SYNC-UL-InfoForE-RUCCH ::=		SEQUENCE {
	prxUpPCHdes						INTEGER (0..62)						OPTIONAL,
	powerRampStep						INTEGER (0..3)							OPTIONAL,
	max-SYNC-UL-Transmissions			ENUMERATED { tr1, tr2, tr4, tr8 }	OPTIONAL,
	e-RUCCH-Sync-UL-Codes-Bitmap		Sync-UL-Codes-Bitmap,
	mmax								INTEGER(1..32)
}

TargetCellPreconfigInfo ::=		SEQUENCE {
	activationTimeOffset				ActivationTimeOffset				OPTIONAL,
	new-H-RNTI							H-RNTI,
	newPrimary-E-RNTI					E-RNTI								OPTIONAL,
	newSecondary-E-RNTI				E-RNTI								OPTIONAL,
	serving-HSDSCH-CellInformation	Serving-HSDSCH-CellInformation-r8,
	e-dch-ReconfigurationInfo			E-DCH-ReconfigurationInfo-r7,
	dtx-drx-TimingInfo					DTX-DRX-TimingInfo-r7				OPTIONAL,
	dtx-drx-Info						DTX-DRX-Info-r7					OPTIONAL,
	hs-scch-LessInfo					HS-SCCH-LessInfo-r7				OPTIONAL,
	mimoParameters						MIMO-Parameters-r8					OPTIONAL,
	dl-SecondaryCellInfoFDD			DL-SecondaryCellInfoFDD			OPTIONAL
}

TargetCellPreconfigInfo-v890ext ::=		MIMO-Parameters-v7f0ext

TargetCellPreconfigInfo-r9 ::=	SEQUENCE {
	activationTimeOffset				ActivationTimeOffset				OPTIONAL,
	new-H-RNTI							H-RNTI,
	newPrimary-E-RNTI					E-RNTI								OPTIONAL,
	newSecondary-E-RNTI				E-RNTI								OPTIONAL,
	serving-HSDSCH-CellInformation	Serving-HSDSCH-CellInformation-r9,
	e-dch-ReconfigurationInfo			E-DCH-ReconfigurationInfo-r7,
	dtx-drx-TimingInfo					DTX-DRX-TimingInfo-r7				OPTIONAL,
	dtx-drx-Info						DTX-DRX-Info-r7					OPTIONAL,
	hs-scch-LessInfo					HS-SCCH-LessInfo-r7				OPTIONAL,
	mimoParameters						MIMO-Parameters-r9					OPTIONAL,
	dl-SecondaryCellInfoFDD			DL-SecondaryCellInfoFDD-r9		OPTIONAL,
	ul-SecondaryCellInfoFDD			UL-SecondaryCellInfoFDD			OPTIONAL,
	e-dch-ReconfigurationInfo-SecULFrequency
								E-DCH-ReconfigurationInfo-SecULFrequency	OPTIONAL
}

TargetCellPreconfigInfo-v950ext ::=		SecondaryCellMIMOparametersFDD-v950ext

TargetCellPreconfigInfo-r10 ::=		SEQUENCE {
	activationTimeOffset					ActivationTimeOffset			OPTIONAL,
	new-H-RNTI							H-RNTI,
	newPrimary-E-RNTI					E-RNTI								OPTIONAL,
	newSecondary-E-RNTI				E-RNTI								OPTIONAL,
	serving-HSDSCH-CellInformation	Serving-HSDSCH-CellInformation-r9,
	e-dch-ReconfigurationInfo			E-DCH-ReconfigurationInfo-r7,
	dtx-drx-TimingInfo					DTX-DRX-TimingInfo-r7				OPTIONAL,
	dtx-drx-Info						DTX-DRX-Info-r7					OPTIONAL,
	hs-scch-LessInfo					HS-SCCH-LessInfo-r7				OPTIONAL,
	mimoParameters						MIMO-Parameters-r9					OPTIONAL,
	dl-SecondaryCellInfoFDD			DL-SecondaryCellInfoFDD-r10		OPTIONAL,
	additionalDLSecCellInfoListFDD	AdditionalDLSecCellInfoListFDD	OPTIONAL,
	ul-SecondaryCellInfoFDD			UL-SecondaryCellInfoFDD			OPTIONAL,
	e-dch-ReconfigurationInfo-SecULFrequency
								E-DCH-ReconfigurationInfo-SecULFrequency	OPTIONAL
}

TargetCellPreconfigInfo-vb50ext ::=	SEQUENCE {
	ulOLTDInfoFDD							UL-OLTD-InfoFDD				OPTIONAL
}

TargetCellPreconfigInfo-r11 ::=	SEQUENCE {
	activationTimeOffset				ActivationTimeOffset				OPTIONAL,
	new-H-RNTI							H-RNTI,
	newPrimary-E-RNTI					E-RNTI								OPTIONAL,
	newSecondary-E-RNTI				E-RNTI								OPTIONAL,
	serving-HSDSCH-CellInformation	Serving-HSDSCH-CellInformation-r11,
	e-dch-ReconfigurationInfo			E-DCH-ReconfigurationInfo-r11,
	dtx-drx-TimingInfo					DTX-DRX-TimingInfo-r7				OPTIONAL,
	dtx-drx-Info						DTX-DRX-Info-r7					OPTIONAL,
	hs-scch-LessInfo					HS-SCCH-LessInfo-r7				OPTIONAL,
	mimoParameters						MIMO-Parameters-r9					OPTIONAL,
	mimo4x4Parameters					MIMO4x4-Parameters					OPTIONAL,
	dl-SecondaryCellInfoFDD			DL-SecondaryCellInfoFDD-r11		OPTIONAL,
	additionalDLSecCellInfoListFDD	AdditionalDLSecCellInfoListFDD-r11	OPTIONAL,
	additionalDLSecCellInfoListFDD2	AdditionalDLSecCellInfoListFDD2	OPTIONAL,
	ul-SecondaryCellInfoFDD			UL-SecondaryCellInfoFDD			OPTIONAL,
	e-dch-ReconfigurationInfo-SecULFrequency
								E-DCH-ReconfigurationInfo-SecULFrequency	OPTIONAL,
	ul-CLTD-InfoFDD					UL-CLTD-InfoFDD					OPTIONAL,
	f-tpich-ReconfigurationInfo		F-TPICH-ReconfigurationInfo		OPTIONAL,
	uL-OLTD-InfoFDD					UL-OLTD-InfoFDD					OPTIONAL,
	ul-16QAM-Config					UL-16QAM-Config					OPTIONAL,
	ul-64QAM-Config					UL-64QAM-Config					OPTIONAL,
	ul-MIMO-Info						UL-MIMO-InfoFDD					OPTIONAL
}

TargetCellPreconfigInfo-r12 ::=	SEQUENCE {
	activationTimeOffset				ActivationTimeOffset				OPTIONAL,
	new-H-RNTI							H-RNTI,
	newPrimary-E-RNTI					E-RNTI								OPTIONAL,
	newSecondary-E-RNTI				E-RNTI								OPTIONAL,
	serving-HSDSCH-CellInformation	Serving-HSDSCH-CellInformation-r12,
	e-dch-ReconfigurationInfo			E-DCH-ReconfigurationInfo-r11,
	dtx-drx-TimingInfo					DTX-DRX-TimingInfo-r7				OPTIONAL,
	dtx-drx-Info						DTX-DRX-Info-r12					OPTIONAL,
	hs-scch-LessInfo					HS-SCCH-LessInfo-r7				OPTIONAL,
	mimoParameters						MIMO-Parameters-r9					OPTIONAL,
	mimo4x4Parameters					MIMO4x4-Parameters					OPTIONAL,
	dl-SecondaryCellInfoFDD			DL-SecondaryCellInfoFDD-r11		OPTIONAL,
	additionalDLSecCellInfoListFDD	AdditionalDLSecCellInfoListFDD-r11	OPTIONAL,
	additionalDLSecCellInfoListFDD2	AdditionalDLSecCellInfoListFDD2	OPTIONAL,
	ul-SecondaryCellInfoFDD			UL-SecondaryCellInfoFDD-r12		OPTIONAL,
	e-dch-ReconfigurationInfo-SecULFrequency
								E-DCH-ReconfigurationInfo-SecULFrequency	OPTIONAL,
	ul-CLTD-InfoFDD					UL-CLTD-InfoFDD					OPTIONAL,
	f-tpich-ReconfigurationInfo		F-TPICH-ReconfigurationInfo		OPTIONAL,
	uL-OLTD-InfoFDD					UL-OLTD-InfoFDD					OPTIONAL,
	ul-16QAM-Config					UL-16QAM-Config					OPTIONAL,
	ul-64QAM-Config					UL-64QAM-Config					OPTIONAL,
	ul-MIMO-Info						UL-MIMO-InfoFDD					OPTIONAL,
	dPCCH2InfoFDD						DPCCH2InfoFDD						OPTIONAL
}

TargetCellPreconfigInfo-r13 ::=	SEQUENCE {
	activationTimeOffset				ActivationTimeOffset					OPTIONAL,
	new-H-RNTI							H-RNTI,
	newPrimary-E-RNTI					E-RNTI									OPTIONAL,
	newSecondary-E-RNTI				E-RNTI									OPTIONAL,
	serving-HSDSCH-CellInformation	Serving-HSDSCH-CellInformation-r12,
	e-dch-ReconfigurationInfo			E-DCH-ReconfigurationInfo-r11,
	dtx-drx-TimingInfo					DTX-DRX-TimingInfo-r7					OPTIONAL,
	dtx-drx-Info						DTX-DRX-Info-r12						OPTIONAL,
	hs-scch-LessInfo					HS-SCCH-LessInfo-r7					OPTIONAL,
	mimoParameters						MIMO-Parameters-r9						OPTIONAL,
	mimo4x4Parameters					MIMO4x4-Parameters						OPTIONAL,
	dl-SecondaryCellInfoFDD			DL-SecondaryCellInfoFDD-r11			OPTIONAL,
	additionalDLSecCellInfoListFDD	AdditionalDLSecCellInfoListFDD-r11	OPTIONAL,
	additionalDLSecCellInfoListFDD2	AdditionalDLSecCellInfoListFDD2		OPTIONAL,
	ul-SecondaryCellInfoFDD			UL-SecondaryCellInfoFDD-r13			OPTIONAL,
	e-dch-ReconfigurationInfo-SecULFrequency
								E-DCH-ReconfigurationInfo-SecULFrequency	OPTIONAL,
	ul-CLTD-InfoFDD					UL-CLTD-InfoFDD						OPTIONAL,
	f-tpich-ReconfigurationInfo		F-TPICH-ReconfigurationInfo			OPTIONAL,
	uL-OLTD-InfoFDD					UL-OLTD-InfoFDD						OPTIONAL,
	ul-16QAM-Config					UL-16QAM-Config						OPTIONAL,
	ul-64QAM-Config					UL-64QAM-Config						OPTIONAL,
	ul-MIMO-Info						UL-MIMO-InfoFDD						OPTIONAL,
	dPCCH2InfoFDD						DPCCH2InfoFDD							OPTIONAL
}


TDD-FPACH-CCode16-r4 ::=			ENUMERATED {
										cc16-1, cc16-2, cc16-3, cc16-4,
										cc16-5, cc16-6, cc16-7, cc16-8,
										cc16-9, cc16-10, cc16-11, cc16-12,
										cc16-13, cc16-14, cc16-15, cc16-16 }

TDD-UL-Interference ::=			INTEGER (-110..-52)

TDD-PICH-CCode ::=					ENUMERATED {
										cc16-1, cc16-2, cc16-3, cc16-4,
										cc16-5, cc16-6, cc16-7, cc16-8,
										cc16-9, cc16-10, cc16-11, cc16-12,
										cc16-13, cc16-14, cc16-15, cc16-16 }

TDD768-PICH-CCode ::=				ENUMERATED {
										cc32-1, cc32-2, cc32-3, cc32-4,
										cc32-5, cc32-6, cc32-7, cc32-8,
										cc32-9, cc32-10, cc32-11, cc32-12,
										cc32-13, cc32-14, cc32-15, cc32-16,
										cc32-17, cc32-18, cc32-19, cc32-20,
										cc32-21, cc32-22, cc32-23, cc32-24,
										cc32-25, cc32-26, cc32-27, cc32-28,
										cc32-29, cc32-30, cc32-31, cc32-32 }

TDD-MBSFNInformation ::=			SEQUENCE (SIZE (1..maxTS)) OF
										TDD-MBSFNTSlotInfo

TDD-MBSFNTSlotInfo ::=			SEQUENCE {
	timeSlotNumber						TimeslotNumber,
	cellParametersID					CellParametersID
}

TDD-PRACH-CCode8 ::=				ENUMERATED {
										cc8-1, cc8-2, cc8-3, cc8-4,
										cc8-5, cc8-6, cc8-7, cc8-8 }

TDD-PRACH-CCode16 ::=				ENUMERATED {
										cc16-1, cc16-2, cc16-3, cc16-4,
										cc16-5, cc16-6, cc16-7, cc16-8,
										cc16-9, cc16-10, cc16-11, cc16-12,
										cc16-13, cc16-14, cc16-15, cc16-16 }

TDD-PRACH-CCode-LCR-r4 ::=		ENUMERATED {
										cc4-1, cc4-2, cc4-3, cc4-4,
										cc8-1, cc8-2, cc8-3, cc8-4,
										cc8-5, cc8-6, cc8-7, cc8-8,
										cc16-1, cc16-2, cc16-3, cc16-4,
										cc16-5, cc16-6, cc16-7, cc16-8,
										cc16-9, cc16-10, cc16-11, cc16-12,
										cc16-13, cc16-14, cc16-15, cc16-16 }

TDD-PRACH-CCodeList ::= 			CHOICE {
	sf8									SEQUENCE (SIZE (1..8)) OF
											TDD-PRACH-CCode8,
-- Channelisation codes cc16-9, cc16-10, cc16-11, cc16-12, cc16-13, cc16-14,
-- cc16-15 and cc16-16 shall not be used
	sf16								SEQUENCE (SIZE (1..8)) OF
											TDD-PRACH-CCode16
}

TDD768-PRACH-CCode16 ::=				ENUMERATED {
										cc16-1, cc16-2, cc16-3, cc16-4,
										cc16-5, cc16-6, cc16-7, cc16-8,
										cc16-9, cc16-10, cc16-11, cc16-12,
										cc16-13, cc16-14, cc16-15, cc16-16 }

TDD768-PRACH-CCode32 ::=				ENUMERATED {
										cc32-1, cc32-2, cc32-3, cc32-4,
										cc32-5, cc32-6, cc32-7, cc32-8,
										cc32-9, cc32-10, cc32-11, cc32-12,
										cc32-13, cc32-14, cc32-15, cc32-16 }

TDD768-PRACH-CCodeList ::= 			CHOICE {
	sf32								SEQUENCE (SIZE (1..16)) OF
											TDD768-PRACH-CCode32,
-- Channelisation codes cc32-17, cc32-18, cc32-19, cc32-20, cc32-21, cc32-22,
-- cc32-23, cc32-24, cc32-25, cc32-26, cc32-27, cc32-28, cc32-29, cc32-30, cc32-31
-- and cc32-32 shall not be used
	sf16								SEQUENCE (SIZE (1..16)) OF
											TDD768-PRACH-CCode16
}

TFC-ControlDuration ::=				ENUMERATED {
										tfc-cd1, tfc-cd2, tfc-cd4, tfc-cd8,
										tfc-cd16, tfc-cd24, tfc-cd32,
										tfc-cd48, tfc-cd64, tfc-cd128,
										tfc-cd192, tfc-cd256, tfc-cd512 }

TFCI-Coding ::=						ENUMERATED {
										tfci-bits-4, tfci-bits-8,
										tfci-bits-16, tfci-bits-32 }

TGCFN ::=							INTEGER (0..255)

-- In TGD, value 270 represents "undefined" in the tabular description.
TGD ::=								INTEGER (15..270)

TGL ::=								INTEGER (1..14)

TGMP ::=							ENUMERATED {
										tdd-Measurement, fdd-Measurement,
										gsm-CarrierRSSIMeasurement,
										gsm-initialBSICIdentification, gsmBSICReconfirmation,
										multi-carrier }

TGMP-r8 ::=							ENUMERATED {
										tdd-Measurement, fdd-Measurement,
										gsm-CarrierRSSIMeasurement,
										gsm-initialBSICIdentification, gsmBSICReconfirmation,
										multi-carrier, e-UTRA, spare }

TGP-Sequence ::=					SEQUENCE {
	tgpsi								TGPSI,
	tgps-Status							CHOICE {
		activate							SEQUENCE {
			tgcfn								TGCFN
		},
		deactivate							NULL
	},
	tgps-ConfigurationParams			TGPS-ConfigurationParams			OPTIONAL
}

TGP-Sequence-r8 ::=					SEQUENCE {
	tgpsi								TGPSI,
	tgps-Status							CHOICE {
		activate							SEQUENCE {
			tgcfn								TGCFN
		},
		deactivate							NULL
	},
	tgps-ConfigurationParams			TGPS-ConfigurationParams-r8			OPTIONAL
}

TGP-Sequence-r10 ::=					SEQUENCE {
	tgpsi								TGPSI,
	tgps-Status							CHOICE {
		activate							SEQUENCE {
			tgcfn								TGCFN
		},
		deactivate							NULL
	},
	tgps-ConfigurationParams			TGPS-ConfigurationParams-r10			OPTIONAL
}

TGPS-Reconfiguration-CFN ::=		INTEGER (0..255)

TGP-SequenceList ::=				SEQUENCE (SIZE (1..maxTGPS)) OF
										TGP-Sequence

TGP-SequenceList-r8 ::=				SEQUENCE (SIZE (1..maxTGPS)) OF
										TGP-Sequence-r8

TGP-SequenceList-r10 ::=			SEQUENCE (SIZE (1..maxTGPS)) OF
										TGP-Sequence-r10

TGP-SequenceShort ::=				SEQUENCE {
	tgpsi								TGPSI,
	tgps-Status							CHOICE {
		activate							SEQUENCE {
			tgcfn								TGCFN
		},
		deactivate							NULL
	}
}

TGP-SequenceShort-r10 ::=				SEQUENCE {
	tgpsi								TGPSI,
	tgps-Status							CHOICE {
		activate							SEQUENCE {
			tgcfn								TGCFN
		},
		deactivate							NULL
	},
	freqSpecificCompressedMode			ENUMERATED { true }					OPTIONAL
}

TGPL ::=							INTEGER (1..144)

-- TABULAR: In TGPRC, value 0 represents "infinity" in the tabular description.
TGPRC ::=							INTEGER (0..511)

TGPS-ConfigurationParams ::=		SEQUENCE {
	tgmp								TGMP,
	tgprc								TGPRC,
	tgsn								TGSN,
	tgl1								TGL,
	tgl2								TGL									OPTIONAL,
	tgd									TGD,
	tgpl1								TGPL,
	-- dummy is not used in this version of the specification, it should
	-- not be sent and if received it shall be ignored.
	dummy							TGPL								OPTIONAL,
	rpp									RPP,
	itp									ITP,
	-- TABULAR: Compressed mode method is nested inside UL-DL-Mode
	ul-DL-Mode							UL-DL-Mode,
	dl-FrameType						DL-FrameType,
	deltaSIR1							DeltaSIR,
	deltaSIRAfter1						DeltaSIR,
	deltaSIR2							DeltaSIR							OPTIONAL,
	deltaSIRAfter2						DeltaSIR							OPTIONAL,
	nidentifyAbort						NidentifyAbort						OPTIONAL,
	treconfirmAbort						TreconfirmAbort						OPTIONAL
}

TGPS-ConfigurationParams-r8 ::=		SEQUENCE {
	tgmp								TGMP-r8,
	tgprc								TGPRC,
	tgsn								TGSN,
	tgl1								TGL,
	tgl2								TGL									OPTIONAL,
	tgd									TGD,
	tgpl1								TGPL,
	rpp									RPP,
	itp									ITP,
	-- TABULAR: Compressed mode method is nested inside UL-DL-Mode
	ul-DL-Mode							UL-DL-Mode,
	dl-FrameType						DL-FrameType,
	deltaSIR1							DeltaSIR,
	deltaSIRAfter1						DeltaSIR,
	deltaSIR2							DeltaSIR							OPTIONAL,
	deltaSIRAfter2						DeltaSIR							OPTIONAL,
	nidentifyAbort						NidentifyAbort						OPTIONAL,
	treconfirmAbort						TreconfirmAbort						OPTIONAL
}

TGPS-ConfigurationParams-r10 ::=		SEQUENCE {
	tgmp								TGMP-r8,
	freqSpecificCompressedMode			ENUMERATED { true }					OPTIONAL,
	tgprc								TGPRC,
	tgsn								TGSN,
	tgl1								TGL,
	tgl2								TGL									OPTIONAL,
	tgd									TGD,
	tgpl1								TGPL,
	rpp									RPP,
	itp									ITP,
	-- TABULAR: Compressed mode method is nested inside UL-DL-Mode
	ul-DL-Mode							UL-DL-Mode,
	dl-FrameType						DL-FrameType,
	deltaSIR1							DeltaSIR,
	deltaSIRAfter1						DeltaSIR,
	deltaSIR2							DeltaSIR							OPTIONAL,
	deltaSIRAfter2						DeltaSIR							OPTIONAL,
	nidentifyAbort						NidentifyAbort						OPTIONAL,
	treconfirmAbort						TreconfirmAbort						OPTIONAL
}

TGPSI ::=							INTEGER (1..maxTGPS)

TGSN ::=							INTEGER (0..14)

TimeInfo ::=						SEQUENCE {
	activationTime						ActivationTime						OPTIONAL,
	durationTimeInfo					DurationTimeInfo					OPTIONAL
}

TimeSlotLCR-ext ::=					ENUMERATED {
										ts7, spare3, spare2, spare1 }

TimeslotList ::=					SEQUENCE (SIZE (1..maxTS)) OF
										TimeslotNumber

TimeslotList-r4 ::=					CHOICE {
-- the choice for 7.68 Mcps TDD is as for 3.84 Mcps TDD  --
	tdd384								SEQUENCE (SIZE (1..maxTS)) OF
											TimeslotNumber,
	tdd128								SEQUENCE (SIZE (1..maxTS-LCR)) OF
											TimeslotNumber-LCR-r4
}

-- If TimeslotNumber is included for a 1.28Mcps TDD description, it shall take values from 0..6
TimeslotNumber ::=						INTEGER (0..14)

TimeslotNumber-LCR-r4 ::=				INTEGER (0..6)

TimeslotNumber-PRACH-LCR-r4 ::=		INTEGER (1..6)

TimeslotSync2 ::=				INTEGER (0..6)

DTX-DRX-TimingInfo-r7 ::=			SEQUENCE {
	timing								CHOICE {
		continue							NULL,
		newTiming							NewTiming
	}
}

-- Actual value TimingOffset = IE value * 256
TimingOffset ::=					INTEGER (0..149)

TimingMaintainedSynchInd ::=		ENUMERATED { false }

TPC-CombinationIndex ::=			INTEGER (0..5)

TPC-CommandTargetRate ::=			INTEGER (0..10)

-- Actual value TPC-StepSizeFDD = IE value + 1
TPC-StepSizeFDD ::=					INTEGER (0..1)

TPC-StepSizeTDD ::=					INTEGER (1..3)

TransportBlockSizeIndex ::=			INTEGER (1..32)

-- Actual value TreconfirmAbort = IE value * 0.5 seconds
TreconfirmAbort ::=	INTEGER (1..20)

TwoMsHarqConfiguration ::=				SEQUENCE {
	harqProcessAllocation				BIT STRING (SIZE (8))				OPTIONAL
}

TX-DiversityMode ::=				ENUMERATED {
										noDiversity,
										sttd,
										closedLoopMode1,
		-- dummy is not used in this version of the specification, it should
		-- not be sent and if received it should be ignored.
										dummy }

UARFCN ::=						INTEGER (0..16383)

UCSM-Info ::=						SEQUENCE {
	minimumSpreadingFactor				MinimumSpreadingFactor,
	nf-Max								NF-Max,
	channelReqParamsForUCSM				ChannelReqParamsForUCSM
}

UE-DPCCH-Burst ::=					ENUMERATED {
										sub-frames-1,
										sub-frames-2,
										sub-frames-5,
										spare1 }

UE-DPCCHPowerResetAfterDTXOnSecUplink ::=	SEQUENCE {
	filterCoefficient					INTEGER (0..5),
    -- Actual value range powerOffset = (-4..10) * 2
	powerOffset							INTEGER (-8..20),
	inactivityThresholdForResetPower	ENUMERATED {
										ms10, ms20, ms30, ms40,
										ms50, ms60, ms80, ms120}			OPTIONAL
}

UE-DRX-Cycle ::=					ENUMERATED {
										sub-frames-4,
										sub-frames-5,
										sub-frames-8,
										sub-frames-10,
										sub-frames-16,
										sub-frames-20,
										spare2,
										spare1 }

UE-DRX-Cycle2 ::=					ENUMERATED {
										sub-frames-4,
										sub-frames-5,
										sub-frames-8,
										sub-frames-10,
										sub-frames-16,
										sub-frames-20,
										sub-frames-32,
										sub-frames-40,
										sub-frames-64,
										sub-frames-80,
										spare6,
										spare5,
										spare4,
										spare3,
										spare2,
										spare1 }

UE-DTX-Cycle1-10ms ::=				ENUMERATED {
										sub-frames-1,
										sub-frames-5,
										sub-frames-10,
										sub-frames-20 }

UE-DTX-Cycle1-2ms ::=				ENUMERATED {
										sub-frames-1,
										sub-frames-4,
										sub-frames-5,
										sub-frames-8,
										sub-frames-10,
										sub-frames-16,
										sub-frames-20,
										spare1 }

UE-DTX-Cycle2-10ms ::=				ENUMERATED {
										sub-frames-5,
										sub-frames-10,
										sub-frames-20,
										sub-frames-40,
										sub-frames-80,
										sub-frames-160,
										spare2,
										spare1 }

UE-DTX-Cycle2-2ms ::=				ENUMERATED {
										sub-frames-4,
										sub-frames-5,
										sub-frames-8,
										sub-frames-10,
										sub-frames-16,
										sub-frames-20,
										sub-frames-32,
										sub-frames-40,
										sub-frames-64,
										sub-frames-80,
										sub-frames-128,
										sub-frames-160,
										spare4,
										spare3,
										spare2,
										spare1 }

UE-DTX-Cycle2-2ms-Secondary ::=		ENUMERATED {
										sub-frames-4,
										sub-frames-5,
										sub-frames-8,
										sub-frames-10,
										sub-frames-16,
										sub-frames-20,
										sub-frames-32,
										sub-frames-40,
										sub-frames-64,
										sub-frames-80,
										sub-frames-128,
										sub-frames-160,
										sub-frames-256,
										sub-frames-320,
										sub-frames-512,
										sub-frames-640,
										sub-frames-1024,
										sub-frames-1280,
										spare14,
										spare13,
										spare12,
										spare11,
										spare10,
										spare9,
										spare8,
										spare7,
										spare6,
										spare5,
										spare4,
										spare3,
										spare2,
										spare1 }

UE-DTX-Cycle2InactivityThreshold ::=	ENUMERATED {
											e-dch-tti-1,
											e-dch-tti-4,
											e-dch-tti-8,
											e-dch-tti-16,
											e-dch-tti-32,
											e-dch-tti-64,
											e-dch-tti-128,
											e-dch-tti-256,
											spare8,
											spare7,
											spare6,
											spare5,
											spare4,
											spare3,
											spare2,
											spare1 }

UE-DTX-long-preamble-length ::=			ENUMERATED {
											slots-4,
											slots-15 }

UE-DTX-DRX-Offset ::=					INTEGER (0..159)

UE-GrantMonitoring-InactivityThreshold ::=	ENUMERATED {
												e-dch-tti-0,
												e-dch-tti-1,
												e-dch-tti-2,
												e-dch-tti-4,
												e-dch-tti-8,
												e-dch-tti-16,
												e-dch-tti-32,
												e-dch-tti-64,
												e-dch-tti-128,
												e-dch-tti-256,
												spare6,
												spare5,
												spare4,
												spare3,
												spare2,
												spare1 }

UL-16QAM-Config ::=		SEQUENCE {
	ul-16QAM-Settings					UL-16QAM-Settings					OPTIONAL,
	e-TFCI-TableIndex					E-TFCI-TableIndex					OPTIONAL,
	mac-es-e-resetIndicator				ENUMERATED { true }					OPTIONAL
}

UL-16QAM-Settings ::=				SEQUENCE {
	beta-Ed-Gain-E-AGCH-Table-Selection	INTEGER (0..1)
}

UL-64QAM-Config ::=		SEQUENCE {
	ul-64QAM-Settings					UL-64QAM-Settings					OPTIONAL,
	mac-is-i-resetIndicator				ENUMERATED { true }					OPTIONAL
}

UL-64QAM-Settings ::=				SEQUENCE {
	beta-Ed-Gain-E-AGCH-Table-Selection	INTEGER (0..1)
}

UL-CCTrCH ::=						SEQUENCE {
	tfcs-ID								TFCS-IdentityPlain					DEFAULT 1,
	ul-TargetSIR						UL-TargetSIR,
	timeInfo							TimeInfo,
	commonTimeslotInfo					CommonTimeslotInfo					OPTIONAL,
	ul-CCTrCH-TimeslotsCodes			UplinkTimeslotsCodes				OPTIONAL
}

UL-CCTrCH-r4 ::=					SEQUENCE {
	tfcs-ID								TFCS-IdentityPlain					DEFAULT 1,
	-- The IE ul-TargetSIR corresponds to PRX-DPCHdes for 1.28Mcps TDD
	-- Actual value PRX-DPCHdes = (value of IE "ul-TargetSIR" - 120)
	ul-TargetSIR						UL-TargetSIR,
	timeInfo							TimeInfo,
	commonTimeslotInfo					CommonTimeslotInfo					OPTIONAL,
	tddOption							CHOICE {
		tdd384								SEQUENCE {
			ul-CCTrCH-TimeslotsCodes			UplinkTimeslotsCodes		OPTIONAL
		},
		tdd128								SEQUENCE {
			ul-CCTrCH-TimeslotsCodes			UplinkTimeslotsCodes-LCR-r4	OPTIONAL
		}
	}
}

UL-CCTrCH-r7 ::=					SEQUENCE {
	tfcs-ID								TFCS-IdentityPlain					DEFAULT 1,
	-- The IE ul-TargetSIR corresponds to PRX-DPCHdes for 1.28Mcps TDD
	-- Actual value PRX-DPCHdes = (value of IE "ul-TargetSIR" - 120)
	ul-TargetSIR						UL-TargetSIR,
	timeInfo							TimeInfo,
	commonTimeslotInfo					CommonTimeslotInfo					OPTIONAL,
	tddOption							CHOICE {
		tdd384								SEQUENCE {
			ul-CCTrCH-TimeslotsCodes			UplinkTimeslotsCodes		OPTIONAL
		},
		tdd768								SEQUENCE {
			ul-CCTrCH-TimeslotsCodes			UplinkTimeslotsCodes-VHCR	OPTIONAL
		},
		tdd128								SEQUENCE {
			ul-CCTrCH-TimeslotsCodes			UplinkTimeslotsCodes-LCR-r7	OPTIONAL
		}
	}
}

UL-CCTrCHList ::=					SEQUENCE (SIZE (1..maxCCTrCH)) OF
										UL-CCTrCH

UL-CCTrCHList-r4 ::=				SEQUENCE (SIZE (1..maxCCTrCH)) OF
										UL-CCTrCH-r4

UL-CCTrCHList-r7 ::=				SEQUENCE (SIZE (1..maxCCTrCH)) OF
										UL-CCTrCH-r7

UL-CCTrCHListToRemove ::=			SEQUENCE (SIZE (1..maxCCTrCH)) OF
										TFCS-IdentityPlain

UL-CCTrChTPCList ::=				SEQUENCE (SIZE (0..maxCCTrCH)) OF
											TFCS-Identity

UL-ChannelRequirement ::=			CHOICE {
	ul-DPCH-Info						UL-DPCH-Info,
	-- dummy is not used in this version of the specification, it should
	-- not be sent and if received the UE behaviour is not specified.
	dummy								CPCH-SetInfo
}

UL-ChannelRequirement-r4 ::=		CHOICE {
	ul-DPCH-Info						UL-DPCH-Info-r4,
	-- dummy is not used in this version of the specification, it should
	-- not be sent and if received the UE behaviour is not specified.
	dummy								CPCH-SetInfo
}

UL-ChannelRequirement-r5 ::=		CHOICE {
	ul-DPCH-Info						UL-DPCH-Info-r5,
	-- dummy is not used in this version of the specification, it should
	-- not be sent and if received the UE behaviour is not specified.
	dummy								CPCH-SetInfo
}

-- Note: the reference to CPCH in the element name below is incorrect. The name is not
-- changed to keep it aligned with R99.
UL-ChannelRequirementWithCPCH-SetID ::=	CHOICE {
	ul-DPCH-Info						UL-DPCH-Info,
	-- dummy1 and dummy 2 are not used in this version of the specification, they should
	-- not be sent and if received the UE behaviour is not specified.
	dummy1								CPCH-SetInfo,
	dummy2								CPCH-SetID
}

-- Note: the reference to CPCH in the element name below is incorrect. The name is not
-- changed to keep it aligned with R99.
UL-ChannelRequirementWithCPCH-SetID-r4 ::=	CHOICE {
	ul-DPCH-Info						UL-DPCH-Info-r4,
	-- dummy1 and dummy2 are not used in this version of the specification, they
	-- should not be sent and if received the UE behaviour is not specified.
	dummy1								CPCH-SetInfo,
	dummy2								CPCH-SetID
}

-- Note: the reference to CPCH in the element name below is incorrect. The name is not
-- changed to keep it aligned with R99.
UL-ChannelRequirementWithCPCH-SetID-r5 ::=	CHOICE {
	ul-DPCH-Info						UL-DPCH-Info-r5,
	-- dummy1 and dummy2 are not used in this version of the specification, they should
	-- not be sent and if received the UE behaviour is not specified.
	dummy1								CPCH-SetInfo,
	dummy2								CPCH-SetID
}


UL-CLTD-InfoFDD ::=	SEQUENCE {
	configurationInfo					CHOICE {
		continue							NULL,
		newConfiguration					SEQUENCE {
			s-dpcch-Info					S-DPCCH-Information,
			initial-CLTD-ActivationState	ENUMERATED { first-state, second-state } OPTIONAL,
			primaryCPICH-Info				PrimaryCPICH-Info		OPTIONAL
		}
	}
}

UL-CompressedModeMethod ::=			ENUMERATED {
										sf-2,
										higherLayerScheduling }

UL-DL-Mode ::=						CHOICE {
	ul									UL-CompressedModeMethod,
	dl									DL-CompressedModeMethod,
	ul-and-dl								SEQUENCE {
		ul									UL-CompressedModeMethod,
		dl									DL-CompressedModeMethod
	}}

UL-DPCCH-SlotFormat ::=				ENUMERATED {
										slf0, slf1, slf2 }

UL-DPCH-CodeInfoForCommonEDCH ::=	SEQUENCE {
	ul-DPCCHscramblingCodeType			ScramblingCodeType,
	ul-DPCCHscramblingCode				UL-ScramblingCode					OPTIONAL
}

UL-DPCH-Info ::=					SEQUENCE {
	ul-DPCH-PowerControlInfo			UL-DPCH-PowerControlInfo			OPTIONAL,
	modeSpecificInfo					CHOICE {
		fdd									SEQUENCE {
			scramblingCodeType					ScramblingCodeType,
			scramblingCode						UL-ScramblingCode,
			numberOfDPDCH						NumberOfDPDCH				DEFAULT 1,
			spreadingFactor						SpreadingFactor,
			tfci-Existence						BOOLEAN,
			-- numberOfFBI-Bits is conditional based on history
			numberOfFBI-Bits					NumberOfFBI-Bits			OPTIONAL,
			puncturingLimit						PuncturingLimit
		},
		tdd									SEQUENCE {
			ul-TimingAdvance					UL-TimingAdvanceControl		OPTIONAL,
			ul-CCTrCHList						UL-CCTrCHList				OPTIONAL,
			ul-CCTrCHListToRemove				UL-CCTrCHListToRemove		OPTIONAL
		}
	}
}

UL-DPCH-Info-r4 ::=					SEQUENCE {
	ul-DPCH-PowerControlInfo			UL-DPCH-PowerControlInfo-r4			OPTIONAL,
	modeSpecificInfo					CHOICE {
		fdd									SEQUENCE {
			scramblingCodeType					ScramblingCodeType,
			scramblingCode						UL-ScramblingCode,
			numberOfDPDCH						NumberOfDPDCH				DEFAULT 1,
			spreadingFactor						SpreadingFactor,
			tfci-Existence						BOOLEAN,
			-- numberOfFBI-Bits is conditional based on history
			numberOfFBI-Bits					NumberOfFBI-Bits			OPTIONAL,
			puncturingLimit						PuncturingLimit
		},
		tdd									SEQUENCE {
			ul-TimingAdvance					UL-TimingAdvanceControl-r4	OPTIONAL,
			ul-CCTrCHList						UL-CCTrCHList-r4			OPTIONAL,
			ul-CCTrCHListToRemove				UL-CCTrCHListToRemove		OPTIONAL
		}
	}
}

UL-DPCH-Info-r5 ::=					SEQUENCE {
	ul-DPCH-PowerControlInfo			UL-DPCH-PowerControlInfo-r5			OPTIONAL,
	modeSpecificInfo					CHOICE {
		fdd									SEQUENCE {
			scramblingCodeType					ScramblingCodeType,
			scramblingCode						UL-ScramblingCode,
			numberOfDPDCH						NumberOfDPDCH				DEFAULT 1,
			spreadingFactor						SpreadingFactor,
			tfci-Existence						BOOLEAN,
			-- numberOfFBI-Bits is conditional based on history
			numberOfFBI-Bits					NumberOfFBI-Bits			OPTIONAL,
			puncturingLimit						PuncturingLimit
		},
		tdd									SEQUENCE {
			ul-TimingAdvance					UL-TimingAdvanceControl-r4	OPTIONAL,
			ul-CCTrCHList						UL-CCTrCHList-r4			OPTIONAL,
			ul-CCTrCHListToRemove				UL-CCTrCHListToRemove		OPTIONAL
		}
	}
}

UL-DPCH-Info-r6 ::=					SEQUENCE {
	ul-DPCH-PowerControlInfo			UL-DPCH-PowerControlInfo-r6			OPTIONAL,
	modeSpecificInfo					CHOICE {
		fdd									SEQUENCE {
			scramblingCodeType					ScramblingCodeType,
			scramblingCode						UL-ScramblingCode,
			dpdchPresence						CHOICE {
				present								SEQUENCE {
					numberOfDPDCH						NumberOfDPDCH				DEFAULT 1,
					spreadingFactor						SpreadingFactor,
					tfci-Existence						BOOLEAN,
					-- numberOfFBI-Bits is conditional based on history
					numberOfFBI-Bits					NumberOfFBI-Bits			OPTIONAL,
					puncturingLimit						PuncturingLimit
				},
				notPresent							SEQUENCE {
					tfci-Existence						BOOLEAN,
					-- numberOfFBI-Bits is conditional based on history
					numberOfFBI-Bits					NumberOfFBI-Bits			OPTIONAL
				}
			}
		},
		tdd									SEQUENCE {
			ul-TimingAdvance					UL-TimingAdvanceControl-r4	OPTIONAL,
			ul-CCTrCHList						UL-CCTrCHList-r4			OPTIONAL,
			ul-CCTrCHListToRemove				UL-CCTrCHListToRemove		OPTIONAL
		}
	}
}

UL-DPCH-Info-r7 ::=					SEQUENCE {
	ul-DPCH-PowerControlInfo			UL-DPCH-PowerControlInfo-r7			OPTIONAL,
	modeSpecificInfo					CHOICE {
		fdd									SEQUENCE {
			scramblingCodeType					ScramblingCodeType,
			scramblingCode						UL-ScramblingCode,
			dpdchPresence						CHOICE {
				present								SEQUENCE {
					numberOfDPDCH						NumberOfDPDCH				DEFAULT 1,
					spreadingFactor						SpreadingFactor,
					tfci-Existence						BOOLEAN,
					-- numberOfFBI-Bits is conditional based on history
					numberOfFBI-Bits					NumberOfFBI-Bits			OPTIONAL,
					numberOfTPC-Bits					NumberOfTPC-Bits			OPTIONAL,
					puncturingLimit						PuncturingLimit
						},
				notPresent							SEQUENCE {
					tfci-Existence						BOOLEAN,
					-- numberOfFBI-Bits is conditional based on history
					numberOfFBI-Bits					NumberOfFBI-Bits			OPTIONAL,
					numberOfTPC-Bits					NumberOfTPC-Bits			OPTIONAL
				}
			}
		},
		tdd									SEQUENCE {
			ul-TimingAdvance					UL-TimingAdvanceControl-r7	OPTIONAL,
			ul-CCTrCHList						UL-CCTrCHList-r7			OPTIONAL,
			ul-CCTrCHListToRemove				UL-CCTrCHListToRemove		OPTIONAL
		}
	}
}

UL-DPCH-Info-r11 ::=					SEQUENCE {
	ul-DPCH-PowerControlInfo			UL-DPCH-PowerControlInfo-r11			OPTIONAL,
	modeSpecificInfo					CHOICE {
		fdd									SEQUENCE {
			scramblingCodeType					ScramblingCodeType,
			scramblingCode						UL-ScramblingCode,
			dpdchPresence						CHOICE {
				present								SEQUENCE {
					numberOfDPDCH						NumberOfDPDCH				DEFAULT 1,
					spreadingFactor						SpreadingFactor,
					tfci-Existence						BOOLEAN,
					-- numberOfFBI-Bits is conditional based on history
					numberOfFBI-Bits					NumberOfFBI-Bits			OPTIONAL,
					numberOfTPC-Bits					NumberOfTPC-Bits			OPTIONAL,
					puncturingLimit						PuncturingLimit
						},
				notPresent							SEQUENCE {
					tfci-Existence						BOOLEAN,
					-- numberOfFBI-Bits is conditional based on history
					numberOfFBI-Bits					NumberOfFBI-Bits			OPTIONAL,
					numberOfTPC-Bits					NumberOfTPC-Bits			OPTIONAL
				}
			}
		},
		tdd									SEQUENCE {
			ul-TimingAdvance					UL-TimingAdvanceControl-r7	OPTIONAL,
			ul-CCTrCHList						UL-CCTrCHList-r7			OPTIONAL,
			ul-CCTrCHListToRemove				UL-CCTrCHListToRemove		OPTIONAL
		}
	}
}

UL-DPCH-InfoPostFDD ::=				SEQUENCE {
	ul-DPCH-PowerControlInfo			UL-DPCH-PowerControlInfoPostFDD,
			scramblingCodeType					ScramblingCodeType,
			reducedScramblingCodeNumber			ReducedScramblingCodeNumber,
			spreadingFactor						SpreadingFactor

}

UL-DPCH-InfoPostTDD ::=				SEQUENCE {
	ul-DPCH-PowerControlInfo			UL-DPCH-PowerControlInfoPostTDD,
	ul-TimingAdvance					UL-TimingAdvanceControl					OPTIONAL,
	ul-CCTrCH-TimeslotsCodes			UplinkTimeslotsCodes
}

UL-DPCH-InfoPostTDD-LCR-r4 ::=		SEQUENCE {
	ul-DPCH-PowerControlInfo			UL-DPCH-PowerControlInfoPostTDD-LCR-r4,
	ul-TimingAdvance					UL-TimingAdvanceControl-LCR-r4				OPTIONAL,
	ul-CCTrCH-TimeslotsCodes			UplinkTimeslotsCodes-LCR-r4
}

UL-DPCH-InfoPredef ::=				SEQUENCE {
	ul-DPCH-PowerControlInfo			UL-DPCH-PowerControlInfoPredef,
	modeSpecificInfo					CHOICE {
		fdd									SEQUENCE {
			tfci-Existence						BOOLEAN,
			puncturingLimit						PuncturingLimit
		},
		tdd									SEQUENCE {
			commonTimeslotInfo					CommonTimeslotInfo
		}
	}
}

UL-DPCH-InfoPredef-v770ext ::=		SEQUENCE {
	modeSpecificInfo					CHOICE {
		fdd									SEQUENCE {
			numberOfTPC-Bits					NumberOfTPC-Bits				OPTIONAL
		},
		tdd									NULL	}
}

UL-DPCH-PowerControlInfo ::=		CHOICE {
	fdd									SEQUENCE {
		dpcch-PowerOffset					DPCCH-PowerOffset,
		pc-Preamble							PC-Preamble,
		sRB-delay							SRB-delay,
		-- TABULAR: TPC step size nested inside PowerControlAlgorithm
		powerControlAlgorithm				PowerControlAlgorithm
	},
	tdd									SEQUENCE {
		ul-TargetSIR						UL-TargetSIR				OPTIONAL,
		ul-OL-PC-Signalling					CHOICE {
			broadcast-UL-OL-PC-info				NULL,
			individuallySignalled				SEQUENCE {
				individualTS-InterferenceList		IndividualTS-InterferenceList,
				dpch-ConstantValue					ConstantValueTdd,
				primaryCCPCH-TX-Power				PrimaryCCPCH-TX-Power
			}
		}																OPTIONAL
	}
}

UL-DPCH-PowerControlInfo-r4 ::=		CHOICE {
	fdd									SEQUENCE {
		dpcch-PowerOffset					DPCCH-PowerOffset,
		pc-Preamble							PC-Preamble,
		sRB-delay							SRB-delay,
		-- TABULAR: TPC step size nested inside PowerControlAlgorithm
		powerControlAlgorithm				PowerControlAlgorithm
	},
	tdd									SEQUENCE {
		-- The IE ul-TargetSIR corresponds to PRX-DPCHdes for 1.28Mcps TDD
		-- Actual value PRX-DPCHdes = (value of IE "ul-TargetSIR" - 120)
		ul-TargetSIR						UL-TargetSIR				OPTIONAL,
		ul-OL-PC-Signalling					CHOICE {
			broadcast-UL-OL-PC-info				NULL,
			individuallySignalled				SEQUENCE {
				tddOption							CHOICE {
					tdd384								SEQUENCE {
						individualTS-InterferenceList		IndividualTS-InterferenceList,
						dpch-ConstantValue					ConstantValue
					},
					tdd128								SEQUENCE {
						tpc-StepSize						TPC-StepSizeTDD
					}
				},
				primaryCCPCH-TX-Power				PrimaryCCPCH-TX-Power
			}
		}
	}
}

UL-DPCH-PowerControlInfo-r5 ::=		CHOICE {
	fdd									SEQUENCE {
		dpcch-PowerOffset					DPCCH-PowerOffset,
		pc-Preamble							PC-Preamble,
		sRB-delay							SRB-delay,
		-- TABULAR: TPC step size nested inside PowerControlAlgorithm
		powerControlAlgorithm				PowerControlAlgorithm,
		deltaACK							DeltaACK	OPTIONAL,
		deltaNACK							DeltaNACK	OPTIONAL,
		ack-NACK-repetition-factor			ACK-NACK-repetitionFactor	OPTIONAL
	},
	tdd									SEQUENCE {
		-- The IE ul-TargetSIR corresponds to PRX-DPCHdes for 1.28Mcps TDD
		-- Actual value PRX-DPCHdes = (value of IE "ul-TargetSIR" - 120)
		ul-TargetSIR						UL-TargetSIR				OPTIONAL,
		ul-OL-PC-Signalling					CHOICE {
			broadcast-UL-OL-PC-info				NULL,
			individuallySignalled				SEQUENCE {
				tddOption							CHOICE {
					tdd384								SEQUENCE {
						individualTS-InterferenceList		IndividualTS-InterferenceList,
						dpch-ConstantValue					ConstantValue
					},
					tdd128								SEQUENCE {
						tpc-StepSize						TPC-StepSizeTDD
					}
				},
				primaryCCPCH-TX-Power				PrimaryCCPCH-TX-Power
			}
		}
	}
}

UL-DPCH-PowerControlInfo-r6 ::=		CHOICE {
	fdd									SEQUENCE {
		dpcch-PowerOffset					DPCCH-PowerOffset,
		pc-Preamble							PC-Preamble,
		sRB-delay							SRB-delay,
		-- TABULAR: TPC step size nested inside PowerControlAlgorithm
		powerControlAlgorithm				PowerControlAlgorithm,
		deltaACK							DeltaACK	OPTIONAL,
		deltaNACK							DeltaNACK	OPTIONAL,
		ack-NACK-repetition-factor			ACK-NACK-repetitionFactor	OPTIONAL,
		harq-Preamble-Mode					HARQ-Preamble-Mode
	},
	tdd									SEQUENCE {
		-- The IE ul-TargetSIR corresponds to PRX-DPCHdes for 1.28Mcps TDD
		-- Actual value PRX-DPCHdes = (value of IE "ul-TargetSIR" - 120)
		ul-TargetSIR						UL-TargetSIR				OPTIONAL,
		ul-OL-PC-Signalling					CHOICE {
			broadcast-UL-OL-PC-info				NULL,
			individuallySignalled				SEQUENCE {
				tddOption							CHOICE {
					tdd384								SEQUENCE {
						individualTS-InterferenceList		IndividualTS-InterferenceList,
						dpch-ConstantValue					ConstantValue
					},
					tdd128								SEQUENCE {
						beaconPLEst							BEACON-PL-Est		OPTIONAL,
						tpc-StepSize						TPC-StepSizeTDD
					}
				},
				primaryCCPCH-TX-Power				PrimaryCCPCH-TX-Power
			}
		}
	}
}

UL-DPCH-PowerControlInfo-r7 ::=		CHOICE {
	fdd									SEQUENCE {
		dpcch-PowerOffset					DPCCH-PowerOffset,
		pc-Preamble							PC-Preamble,
		sRB-delay							SRB-delay,
		-- TABULAR: TPC step size nested inside PowerControlAlgorithm
		powerControlAlgorithm				PowerControlAlgorithm,
		deltaACK							DeltaACK	OPTIONAL,
		deltaNACK							DeltaNACK	OPTIONAL,
		ack-NACK-repetition-factor			ACK-NACK-repetitionFactor	OPTIONAL,
		harq-Preamble-Mode					HARQ-Preamble-Mode
	},
	tdd									SEQUENCE {
		-- The IE ul-TargetSIR corresponds to PRX-DPCHdes for 1.28Mcps TDD
		-- Actual value PRX-DPCHdes = (value of IE "ul-TargetSIR" - 120)
		ul-TargetSIR						UL-TargetSIR				OPTIONAL,
		ul-OL-PC-Signalling					CHOICE {
			broadcast-UL-OL-PC-info				NULL,
			individuallySignalled				SEQUENCE {
				tddOption							CHOICE {
					tdd384								SEQUENCE {
						individualTS-InterferenceList		IndividualTS-InterferenceList,
						dpch-ConstantValue					ConstantValue
					},
					tdd768								SEQUENCE {
						individualTS-InterferenceList		IndividualTS-InterferenceList,
						dpch-ConstantValue					ConstantValue
					},
					tdd128								SEQUENCE {
						beaconPLEst							BEACON-PL-Est		OPTIONAL,
						tpc-StepSize						TPC-StepSizeTDD
					}
				},
				primaryCCPCH-TX-Power				PrimaryCCPCH-TX-Power
			}
		}
	}
}

UL-DPCH-PowerControlInfo-r11 ::=		CHOICE {
	fdd									SEQUENCE {
		dpcch-PowerOffset					DPCCH-PowerOffset,
		pc-Preamble							PC-Preamble,
		sRB-delay							SRB-delay,
		-- TABULAR: TPC step size nested inside PowerControlAlgorithm
		powerControlAlgorithm				PowerControlAlgorithm,
		deltaACK							DeltaACK-r11	OPTIONAL,
		deltaNACK							DeltaNACK-r11	OPTIONAL,
		ack-NACK-repetition-factor			ACK-NACK-repetitionFactor	OPTIONAL,
		ack-NACK-repetition-factor-assisting	ACK-NACK-repetitionFactor	OPTIONAL,
		harq-Preamble-Mode					HARQ-Preamble-Mode
	},
	tdd									SEQUENCE {
		-- The IE ul-TargetSIR corresponds to PRX-DPCHdes for 1.28Mcps TDD
		-- Actual value PRX-DPCHdes = (value of IE "ul-TargetSIR" - 120)
		ul-TargetSIR						UL-TargetSIR				OPTIONAL,
		ul-OL-PC-Signalling					CHOICE {
			broadcast-UL-OL-PC-info				NULL,
			individuallySignalled				SEQUENCE {
				tddOption							CHOICE {
					tdd384								SEQUENCE {
						individualTS-InterferenceList		IndividualTS-InterferenceList,
						dpch-ConstantValue					ConstantValue
					},
					tdd768								SEQUENCE {
						individualTS-InterferenceList		IndividualTS-InterferenceList,
						dpch-ConstantValue					ConstantValue
					},
					tdd128								SEQUENCE {
						beaconPLEst							BEACON-PL-Est		OPTIONAL,
						tpc-StepSize						TPC-StepSizeTDD
					}
				},
				primaryCCPCH-TX-Power				PrimaryCCPCH-TX-Power
			}
		}
	}
}

UL-DPCHpowerControlInfoConcurrentTTI ::=	SEQUENCE {
	deltaACK									DeltaACK					OPTIONAL,
	deltaNACK									DeltaNACK					OPTIONAL,
	ack-NACK-repetition-factor					ACK-NACK-repetitionFactor	OPTIONAL
}

UL-DPCHpowerControlInfoForCommonEDCH ::=	SEQUENCE {
	-- TABULAR: TPC step size nested inside PowerControlAlgorithm
	powerControlAlgorithm						PowerControlAlgorithm,
	deltaACK									DeltaACK					OPTIONAL,
	deltaNACK									DeltaNACK					OPTIONAL,
	ack-NACK-repetition-factor					ACK-NACK-repetitionFactor	OPTIONAL
}

UL-DPCH-PowerControlInfoPostFDD ::=	SEQUENCE {
	-- DPCCH-PowerOffset2 has a smaller range to save bits
	dpcch-PowerOffset					DPCCH-PowerOffset2,
	pc-Preamble							PC-Preamble,
	sRB-delay							SRB-delay
}

UL-DPCH-PowerControlInfoPostTDD ::=	SEQUENCE {
	ul-TargetSIR						UL-TargetSIR,
	ul-TimeslotInterference				TDD-UL-Interference
}

UL-DPCH-PowerControlInfoPostTDD-LCR-r4 ::=	SEQUENCE {
	-- The IE ul-TargetSIR corresponds to PRX-DPCHdes for 1.28Mcps TDD
	-- Actual value PRX-DPCHdes = (value of IE "ul-TargetSIR" - 120)
	ul-TargetSIR						UL-TargetSIR
}

UL-DPCH-PowerControlInfoPredef ::=		CHOICE {
	fdd									SEQUENCE {
		-- TABULAR: TPC step size nested inside PowerControlAlgorithm
		powerControlAlgorithm				PowerControlAlgorithm
	},
	tdd									SEQUENCE {
		-- dpch-ConstantValue shall be ignored if in 1.28Mcps TDD mode.
		dpch-ConstantValue					ConstantValueTdd
	}
}


UL-EDCH-Information-ext ::=			CHOICE {
	fdd									NULL,
	tdd									SEQUENCE {
		non-ScheduledTransGrantInfo			Non-ScheduledTransGrantInfoTDD-ext		OPTIONAL
	}
}

UL-EDCH-Information-r6 ::=			SEQUENCE {
	mac-es-e-resetIndicator				ENUMERATED { true }						OPTIONAL,
	e-DPCCH-Info						E-DPCCH-Info							OPTIONAL,
	e-DPDCH-Info						E-DPDCH-Info							OPTIONAL,
	schedulingTransmConfiguration		E-DPDCH-SchedulingTransmConfiguration	OPTIONAL
}

UL-EDCH-Information-r7 ::=			SEQUENCE {
	mac-es-e-resetIndicator				ENUMERATED { true }						OPTIONAL,
	modeSpecificInfo					CHOICE {
		fdd									SEQUENCE {
			e-DPCCH-Info						E-DPCCH-Info-r7					OPTIONAL,
			e-DPDCH-Info						E-DPDCH-Info-r7					OPTIONAL,
			schedulingTransmConfiguration		E-DPDCH-SchedulingTransmConfiguration	OPTIONAL,
			ul-16QAM-Settings					UL-16QAM-Settings				OPTIONAL
		},
		tdd									SEQUENCE {
			e-RUCCH-Info						E-RUCCH-Info					OPTIONAL,
			e-PUCH-Info							E-PUCH-Info						OPTIONAL,
			non-ScheduledTransGrantInfo			Non-ScheduledTransGrantInfoTDD	OPTIONAL
		}
	}
}

UL-EDCH-Information-r8 ::=			SEQUENCE {
	mac-es-e-resetIndicator				ENUMERATED { true }						OPTIONAL,
	modeSpecificInfo					CHOICE {
		fdd									SEQUENCE {
			e-DPCCH-Info						E-DPCCH-Info-r7					OPTIONAL,
			e-DPDCH-Info						E-DPDCH-Info-r8					OPTIONAL,
			schedulingTransmConfiguration		E-DPDCH-SchedulingTransmConfiguration	OPTIONAL,
			ul-16QAM-Settings					UL-16QAM-Settings				OPTIONAL
		},
		tdd									SEQUENCE {
			e-RUCCH-Info						E-RUCCH-Info					OPTIONAL,
			e-PUCH-Info							E-PUCH-Info						OPTIONAL,
			non-ScheduledTransGrantInfo			Non-ScheduledTransGrantInfoTDD	OPTIONAL
		}
	}
}

UL-EDCH-Information-r9 ::=			SEQUENCE {
	mac-es-e-resetIndicator				ENUMERATED { true }								OPTIONAL,
	modeSpecificInfo					CHOICE {
		fdd									SEQUENCE {
			e-DPCCH-Info						E-DPCCH-Info-r7							OPTIONAL,
			e-DPDCH-Info						E-DPDCH-Info-r8							OPTIONAL,
			schedulingTransmConfiguration		E-DPDCH-SchedulingTransmConfiguration	OPTIONAL,
			ul-16QAM-Settings					UL-16QAM-Settings						OPTIONAL
		},
		tdd									SEQUENCE {
			e-RUCCH-Info						E-RUCCH-Info							OPTIONAL,
			e-PUCH-Info							E-PUCH-Info								OPTIONAL,
			non-ScheduledTransGrantInfo			Non-ScheduledTransGrantInfoTDD-r9		OPTIONAL
		}
	}
}

UL-EDCH-Information-r11 ::=			SEQUENCE {
	mac-es-e-resetIndicator				ENUMERATED { true }								OPTIONAL,
	modeSpecificInfo					CHOICE {
		fdd									SEQUENCE {
			e-DPCCH-Info						E-DPCCH-Info-r7							OPTIONAL,
			e-DPDCH-Info						E-DPDCH-Info-r8							OPTIONAL,
			ul-MIMO-Info						UL-MIMO-InfoFDD							OPTIONAL,
			schedulingTransmConfiguration		E-DPDCH-SchedulingTransmConfiguration	OPTIONAL,
			ul-16QAM-Settings					UL-16QAM-Settings						OPTIONAL,
			ul-64QAM-Settings					UL-64QAM-Settings						OPTIONAL
		},
		tdd									SEQUENCE {
			e-RUCCH-Info						E-RUCCH-Info							OPTIONAL,
			e-PUCH-Info							E-PUCH-Info								OPTIONAL,
			non-ScheduledTransGrantInfo			Non-ScheduledTransGrantInfoTDD-r9		OPTIONAL
		}
	}
}

UL-MIMO-InfoFDD ::= SEQUENCE {
	configurationInfo		CHOICE {
		continue					NULL,
		newConfiguration			SEQUENCE {
			s-e-dpcch-power-offset			INTEGER(0..17),
			rank2-minimum-E-TFCI			E-DCH-MinimumSet-E-TFCI,
			inter-stream-compensation		INTEGER(0..15)					OPTIONAL
		}
	}
}

UL-MulticarrierEDCH-InfolistItem-TDD128 ::=			SEQUENCE {
	uarfcn				UARFCN,
	prxdes-base			INTEGER (-112..-50),
	e-PUCH-info			E-PUCH-Info-MulticarrierEDCH-TDD128	OPTIONAL,
	e-AGCH-info			E-AGCH-Information-TDD128			OPTIONAL,
	e-HICH-info			E-HICH-Information-TDD128			OPTIONAL
}

UL-MulticarrierEDCH-Infolist-TDD128 ::= 	SEQUENCE (SIZE (1..maxTDD128Carrier-1)) OF
										UL-MulticarrierEDCH-InfolistItem-TDD128

UL-MulticarrierEDCH-Deletelist-TDD128 ::= 	SEQUENCE (SIZE (1..maxTDD128Carrier-1)) OF
										UARFCN

UL-MulticarrierEDCHInfo-TDD128 ::=			SEQUENCE {
	configuration-info				CHOICE {
		continue							NULL,
		newConfiguration					UL-MulticarrierEDCH-NewConfigurationInfo-TDD128
	}
}

UL-MulticarrierEDCH-NewConfigurationInfo-TDD128 ::=			SEQUENCE {
	tsn-Length						ENUMERATED { tsn-14bits }				OPTIONAL,
	ul-MulticarrierEDCH-Infolist	UL-MulticarrierEDCH-Infolist-TDD128		OPTIONAL,
	ul-MulticarrierEDCH-Deletelist	UL-MulticarrierEDCH-Deletelist-TDD128	OPTIONAL
}

UL-Interference ::=					INTEGER (-110..-70)

UL-ScramblingCode ::=				INTEGER (0..16777215)


UL-SynchronisationParameters-r4 ::=	SEQUENCE {
	stepSize							INTEGER (1..8),
	frequency							INTEGER (1..8)
}

-- Actual value UL-TargetSIR = (IE value * 0.5) - 11
UL-TargetSIR ::=					INTEGER (0..62)

UL-TimingAdvance ::=				INTEGER (0..63)

UL-TimingAdvanceControl ::=			CHOICE {
	disabled							NULL,
	enabled								SEQUENCE {
		ul-TimingAdvance					UL-TimingAdvance				OPTIONAL,
		activationTime						ActivationTime					OPTIONAL
	}
}

UL-TimingAdvanceControl-r4 ::=		CHOICE {
	disabled							NULL,
	enabled								SEQUENCE {
		tddOption							CHOICE {
			tdd384								SEQUENCE {
				ul-TimingAdvance					UL-TimingAdvance				OPTIONAL,
				activationTime						ActivationTime					OPTIONAL
			},
			tdd128								SEQUENCE {
				ul-SynchronisationParameters		UL-SynchronisationParameters-r4	OPTIONAL,
				synchronisationParameters			SynchronisationParameters-r4	OPTIONAL
			}
		}
	}
}

UL-TimingAdvanceControl-r7 ::=		CHOICE {
	disabled							NULL,
	enabled								SEQUENCE {
		tddOption							CHOICE {
			tdd384								SEQUENCE {
				ul-TimingAdvance					UL-TimingAdvance				OPTIONAL,
				ext-UL-TimingAdvance				EXT-UL-TimingAdvance			OPTIONAL,
				activationTime						ActivationTime					OPTIONAL
			},
			tdd768								SEQUENCE {
				ext-UL-TimingAdvance				EXT-UL-TimingAdvance			OPTIONAL,
				activationTime						ActivationTime					OPTIONAL
			},
			tdd128								SEQUENCE {
				ul-SynchronisationParameters		UL-SynchronisationParameters-r4	OPTIONAL,
				synchronisationParameters			SynchronisationParameters-r4	OPTIONAL
			}
		}
	}
}

UL-TimingAdvanceControl-LCR-r4 ::=	CHOICE {
	disabled							NULL,
	enabled								SEQUENCE {
		ul-SynchronisationParameters		UL-SynchronisationParameters-r4	OPTIONAL,
		synchronisationParameters			SynchronisationParameters-r4	OPTIONAL
	}
}

UL-TransModeSwitchingParam ::=		SEQUENCE {
	k				INTEGER (1..32),
	l				INTEGER (1..32),
	m				INTEGER (1..32)
}

UL-TS-ChannelisationCode ::=		ENUMERATED {
										cc1-1, cc2-1, cc2-2,
										cc4-1, cc4-2, cc4-3, cc4-4,
										cc8-1, cc8-2, cc8-3, cc8-4,
										cc8-5, cc8-6, cc8-7, cc8-8,
										cc16-1, cc16-2, cc16-3, cc16-4,
										cc16-5, cc16-6, cc16-7, cc16-8,
										cc16-9, cc16-10, cc16-11, cc16-12,
										cc16-13, cc16-14, cc16-15, cc16-16 }

UL-TS-ChannelisationCodeList ::= 	SEQUENCE (SIZE (1..2)) OF
										UL-TS-ChannelisationCode

UL-TS-ChannelisationCodeList-r7 ::= 	SEQUENCE (SIZE (1..2)) OF
											SEQUENCE {
		ul-TS-Channelisation-Code				UL-TS-ChannelisationCode,
		plcch-info								PLCCH-Info		OPTIONAL
}

UL-TS-ChannelisationCode-VHCR ::=		ENUMERATED {
										cc1-1, cc2-1, cc2-2,
										cc4-1, cc4-2, cc4-3, cc4-4,
										cc8-1, cc8-2, cc8-3, cc8-4,
										cc8-5, cc8-6, cc8-7, cc8-8,
										cc16-1, cc16-2, cc16-3, cc16-4,
										cc16-5, cc16-6, cc16-7, cc16-8,
										cc16-9, cc16-10, cc16-11, cc16-12,
										cc16-13, cc16-14, cc16-15, cc16-16,
										cc32-1, cc32-2, cc32-3, cc32-4,
										cc32-5, cc32-6, cc32-7, cc32-8,
										cc32-9, cc32-10, cc32-11, cc32-12,
										cc32-13, cc32-14, cc32-15, cc32-16,
										cc32-17, cc32-18, cc32-19, cc32-20,
										cc32-21, cc32-22, cc32-23, cc32-24,
										cc32-25, cc32-26, cc32-27, cc32-28,
										cc32-29, cc32-30, cc32-31, cc32-32 }

UL-TS-ChannelisationCodeList-VHCR ::=	SEQUENCE (SIZE (1..2)) OF
											UL-TS-ChannelisationCode-VHCR

Uplink-DPCCH-Slot-Format-Information ::=	ENUMERATED {
												slot-format-1,
										-- dummy is not used in this version of
										-- specification, it should not be sent and if
										-- received it should be ignored.
												dummy,
												slot-format-4,
												spare1 }

UplinkAdditionalTimeslots ::=		SEQUENCE {
	parameters							CHOICE {
		sameAsLast							SEQUENCE {
			timeslotNumber						TimeslotNumber
		},
		newParameters						SEQUENCE {
			individualTimeslotInfo						IndividualTimeslotInfo,
			ul-TS-ChannelisationCodeList				UL-TS-ChannelisationCodeList
		}
	}
}

UplinkAdditionalTimeslots-LCR-r4 ::=	SEQUENCE {
	parameters							CHOICE {
		sameAsLast							SEQUENCE {
			timeslotNumber						TimeslotNumber
		},
		newParameters						SEQUENCE {
			individualTimeslotInfo						IndividualTimeslotInfo-LCR-r4,
			ul-TS-ChannelisationCodeList				UL-TS-ChannelisationCodeList
		}
	}
}

UplinkAdditionalTimeslots-LCR-r7 ::=	SEQUENCE {
	parameters							CHOICE {
		sameAsLast							SEQUENCE {
			timeslotNumber						TimeslotNumber
			-- plcch-info assigned as previously defined slot
		},
		newParameters						SEQUENCE {
			individualTimeslotInfo				IndividualTimeslotInfo-LCR-r4,
			ul-TS-ChannelisationCodeList		UL-TS-ChannelisationCodeList-r7
		}
	}
}

UplinkAdditionalTimeslots-VHCR ::=	SEQUENCE {
	parameters							CHOICE {
		sameAsLast							SEQUENCE {
			timeslotNumber						TimeslotNumber
		},
		newParameters						SEQUENCE {
			individualTimeslotInfo				IndividualTimeslotInfo-VHCR,
			ul-TS-ChannelisationCodeList		UL-TS-ChannelisationCodeList
		}
	}
}

UplinkTimeslotsCodes ::=			SEQUENCE {
	dynamicSFusage						BOOLEAN,
	firstIndividualTimeslotInfo			IndividualTimeslotInfo,
	ul-TS-ChannelisationCodeList		UL-TS-ChannelisationCodeList,
	moreTimeslots						CHOICE {
		noMore								NULL,
		additionalTimeslots					CHOICE {
			consecutive							SEQUENCE {
				numAdditionalTimeslots				INTEGER (1..maxTS-1)
			},
			timeslotList						SEQUENCE (SIZE (1..maxTS-1)) OF
													UplinkAdditionalTimeslots
		}
	}
}

UplinkTimeslotsCodes-VHCR ::=		SEQUENCE {
	dynamicSFusage						BOOLEAN,
	firstIndividualTimeslotInfo			IndividualTimeslotInfo-VHCR,
	ul-TS-ChannelisationCodeList		UL-TS-ChannelisationCodeList-VHCR,
	moreTimeslots						CHOICE {
		noMore								NULL,
		additionalTimeslots					CHOICE {
			consecutive							SEQUENCE {
				numAdditionalTimeslots				INTEGER (1..maxTS-1)
			},
			timeslotList						SEQUENCE (SIZE (1..maxTS-1)) OF
													UplinkAdditionalTimeslots-VHCR
		}
	}
}

UplinkTimeslotsCodes-LCR-r4 ::=		SEQUENCE {
	dynamicSFusage						BOOLEAN,
	firstIndividualTimeslotInfo			IndividualTimeslotInfo-LCR-r4,
	ul-TS-ChannelisationCodeList		UL-TS-ChannelisationCodeList,
	moreTimeslots						CHOICE {
		noMore								NULL,
		additionalTimeslots					CHOICE {
			consecutive							SEQUENCE {
				numAdditionalTimeslots				INTEGER (1..maxTS-LCR-1)
			},
			timeslotList						SEQUENCE (SIZE (1..maxTS-LCR-1)) OF
													UplinkAdditionalTimeslots-LCR-r4
		}
	}
}

UplinkTimeslotsCodes-LCR-r7 ::=		SEQUENCE {
	dynamicSFusage						BOOLEAN,
	firstIndividualTimeslotInfo			IndividualTimeslotInfo-LCR-r4,
	ul-TS-ChannelisationCodeList		UL-TS-ChannelisationCodeList-r7,
	moreTimeslots						CHOICE {
		noMore								NULL,
		additionalTimeslots					CHOICE {
			consecutive							SEQUENCE {
			-- the choice of 'consecutive' is not needed because there is only 1 option.
				numAdditionalTimeslots				INTEGER (1..maxTS-LCR-1)
			},
			timeslotList						SEQUENCE (SIZE (1..maxTS-LCR-1)) OF
													UplinkAdditionalTimeslots-LCR-r7
		}
	}
}

UpPCHposition-LCR ::=				INTEGER (0..127)

Wi-LCR ::=							INTEGER (1..4)

-- ***************************************************
--
--     MEASUREMENT INFORMATION ELEMENTS (10.3.7)
--
-- ***************************************************

AcquisitionSatInfo ::=				SEQUENCE {
	satID								SatID,
	-- Actual value dopplerOthOrder = IE value * 2.5
	doppler0thOrder						INTEGER (-2048..2047),
	extraDopplerInfo					ExtraDopplerInfo					OPTIONAL,
	codePhase							INTEGER (0..1022),
	integerCodePhase					INTEGER (0..19),
	gps-BitNumber						INTEGER (0..3),
	codePhaseSearchWindow				CodePhaseSearchWindow,
	azimuthAndElevation					AzimuthAndElevation					OPTIONAL
}

AcquisitionSatInfo-va40ext ::=		SEQUENCE {
	azimuthAndElevation					AzimuthAndElevation-va40ext			OPTIONAL
}

AcquisitionSatInfo-r10 ::=			SEQUENCE {
	satID								SatID,
	-- Actual value dopplerOthOrder = IE value * 2.5
	doppler0thOrder						INTEGER (-2048..2047),
	extraDopplerInfo					ExtraDopplerInfo					OPTIONAL,
	codePhase							INTEGER (0..1022),
	integerCodePhase					INTEGER (0..19),
	gps-BitNumber						INTEGER (0..3),
	codePhaseSearchWindow				CodePhaseSearchWindow,
	azimuthAndElevation					AzimuthAndElevation-r10				OPTIONAL
}
AcquisitionSatInfo-vc50ext ::=		SEQUENCE {
	extraDopplerInfoExtension			ExtraDopplerInfoExtension			OPTIONAL
}

AcquisitionSatInfo-r12 ::=			SEQUENCE {
	satID								SatID,
	-- Actual value dopplerOthOrder = IE value * 2.5
	doppler0thOrder						INTEGER (-2048..2047),
	extraDopplerInfo					ExtraDopplerInfo					OPTIONAL,
-- If the extraDopplerInfoExtension is present, the extraDopplerInfo should not be present
	extraDopplerInfoExtension			ExtraDopplerInfoExtension			OPTIONAL,
	codePhase							INTEGER (0..1022),
	integerCodePhase					INTEGER (0..19),
	gps-BitNumber						INTEGER (0..3),
	codePhaseSearchWindow				CodePhaseSearchWindow,
	azimuthAndElevation					AzimuthAndElevation-r10				OPTIONAL
}

AcquisitionSatInfoList ::=			SEQUENCE (SIZE (1..maxSat)) OF
										AcquisitionSatInfo

AcquisitionSatInfoList-va40ext ::=	SEQUENCE (SIZE (1..maxSat)) OF
										AcquisitionSatInfo-va40ext

AcquisitionSatInfoList-r10 ::=		SEQUENCE (SIZE (1..maxSat)) OF
										AcquisitionSatInfo-r10

AcquisitionSatInfoList-vc50ext ::=	SEQUENCE (SIZE (1..maxSat)) OF
										AcquisitionSatInfo-vc50ext

AcquisitionSatInfoList-r12 ::=		SEQUENCE (SIZE (1..maxSat)) OF
										AcquisitionSatInfo-r12

AdditionalMeasurementID-List ::=	SEQUENCE (SIZE (1..maxAdditionalMeas)) OF
										MeasurementIdentity

AdditionalMeasurementID-List-r9 ::=	SEQUENCE (SIZE (1..maxAdditionalMeas)) OF
												MeasurementIdentity-r9

AlmanacSatInfo ::=					SEQUENCE {
	dataID								INTEGER (0..3),
	satID								SatID,
	e									BIT STRING (SIZE (16)),
	t-oa								BIT STRING (SIZE (8)),
	deltaI								BIT STRING (SIZE (16)),
	omegaDot							BIT STRING (SIZE (16)),
	satHealth							BIT STRING (SIZE (8)),
	a-Sqrt								BIT STRING (SIZE (24)),
	omega0								BIT STRING (SIZE (24)),
	m0									BIT STRING (SIZE (24)),
	omega								BIT STRING (SIZE (24)),
	af0									BIT STRING (SIZE (11)),
	af1									BIT STRING (SIZE (11))
}

AlmanacSatInfoList ::=				SEQUENCE (SIZE (1..maxSat)) OF
										AlmanacSatInfo

ALM-BDSKeplerianSet	::=			SEQUENCE {
	sat-info-BDSkpList					GANSS-SAT-Info-Almanac-BDSkpList
}

ALM-ECEFsbasAlmanacSet ::=			SEQUENCE {
	sat-info-SBASecefList				GANSS-SAT-Info-Almanac-SBASecefList
}

ALM-GlonassAlmanacSet ::=			SEQUENCE {
	sat-info-GLOkpList					GANSS-SAT-Info-Almanac-GLOkpList
}

ALM-keplerianParameters ::=			SEQUENCE {
	-- time of week by 600s steps
	t-oa								INTEGER (0..1023),
	iod-a								INTEGER (0..15),
	sat-info-kpList						GANSS-SAT-Info-Almanac-KpList
}

ALM-MidiAlmanacSet ::=				SEQUENCE {
	-- time of week by 4096s steps
	t-oa								INTEGER (0..147),
	sat-info-MIDIkpList					GANSS-SAT-Info-Almanac-MIDIkpList
}

ALM-NAVKeplerianSet ::=				SEQUENCE {
	-- time of week by 4096s steps
	t-oa								INTEGER (0..147),
	sat-info-NAVkpList					GANSS-SAT-Info-Almanac-NAVkpList
}

ALM-ReducedKeplerianSet ::=			SEQUENCE {
	-- time of week by 4096s steps
	t-oa								INTEGER (0..147),
	sat-info-REDkpList					GANSS-SAT-Info-Almanac-REDkpList
}

AuxInfoGANSS-ID1 ::=				SEQUENCE (SIZE (1..maxGANSSSat)) OF AuxInfoGANSS-ID1-element

AuxInfoGANSS-ID1-element ::=		SEQUENCE {
	svID								INTEGER(0..63),
	signalsAvailable					BIT STRING (SIZE(8))
}

AuxInfoGANSS-ID3 ::=				SEQUENCE (SIZE (1.. maxGANSSSat)) OF AuxInfoGANSS-ID3-element

AuxInfoGANSS-ID3-element ::=		SEQUENCE {
	svID								INTEGER (0..63),
	signalsAvailable					BIT STRING (SIZE (8)),
	channelNumber						INTEGER (-7..13)
}

AverageRLC-BufferPayload ::=		ENUMERATED {
										pla0, pla4, pla8, pla16, pla32,
										pla64, pla128, pla256, pla512,
										pla1024, pla2k, pla4k, pla8k, pla16k,
										pla32k, pla64k, pla128k, pla256k,
										pla512k, pla1024k, spare12, spare11,
										spare10, spare9, spare8, spare7, spare6,
										spare5, spare4, spare3, spare2, spare1 }

AzimuthAndElevation ::=				SEQUENCE {
	-- Actual value azimuth = IE value * 11.25 + IE value of azimuthLSB * 0.703125 degrees
	azimuth								INTEGER (0..31),
	-- Actual value elevation = IE value * 11.25 + IE value of elevationLSB * 0.703125 degrees
	elevation							INTEGER (0..7)
}

AzimuthAndElevation-va40ext ::=		SEQUENCE {
	azimuthLSB							INTEGER (0..15),
	elevationLSB						INTEGER (0..15)
}

AzimuthAndElevation-r10 ::=	SEQUENCE {
	-- Actual value azimuth = IE value * 11.25 + IE value of azimuthLSB * 0.703125 degrees
	azimuth								INTEGER (0..31),
	-- Actual value elevation = IE value * 11.25 + IE value of elevationLSB * 0.703125 degrees
	elevation							INTEGER (0..7),
	azimuthLSB							INTEGER (0..15),
	elevationLSB						INTEGER (0..15)
}

BadSatList ::=						SEQUENCE (SIZE (1..maxSat)) OF
										INTEGER (0..63)

Frequency-Band ::=					ENUMERATED {
										dcs1800BandUsed, pcs1900BandUsed }

BCCH-ARFCN ::=						INTEGER (0..1023)

BDSclockModel ::=			SEQUENCE {
	bdsAODC				BIT STRING (SIZE (5)),
	bdsToc				BIT STRING (SIZE (17)),
	bdsa0				BIT STRING (SIZE (24)),
	bdsa1				BIT STRING (SIZE (22)),
	bdsa2				BIT STRING (SIZE (11)),
	bdsTgd1				BIT STRING (SIZE (10))
}

BDS-IGPInfoList ::= SEQUENCE (SIZE (1..maxIGPInfo)) OF SEQUENCE {
	bds-IGPNumber				INTEGER (1..320),
	bds-VerticalDelay			BIT STRING (SIZE (9)),
	bds-GIVEI					BIT STRING (SIZE (4))
}

DBDS-InfoList ::= SEQUENCE (SIZE (1..maxSgnType)) OF DBDS-Info

DBDS-Info ::= SEQUENCE {
	bds-SignalID			GANSS-Signal-Id		OPTIONAL,
	dbds-SignalInfoList		DBDS-SignalInfoList
}

DBDS-SignalInfoList ::= SEQUENCE (SIZE (1..maxGANSSSat)) OF
									DBDS-SignalInfo

DBDS-SignalInfo ::= SEQUENCE {
	svID 				INTEGER(0..63),
	bds-UDREI			INTEGER (0..15),
	bds-RURAI			INTEGER (0..15),
	bds-ECC-DeltaT		BIT STRING (SIZE (13))
}

BLER-MeasurementResults ::=			SEQUENCE {
	transportChannelIdentity			TransportChannelIdentity,
	dl-TransportChannelBLER				DL-TransportChannelBLER				OPTIONAL
}

BLER-MeasurementResultsList ::=		SEQUENCE (SIZE (1..maxTrCH)) OF
										BLER-MeasurementResults

BLER-TransChIdList ::=				SEQUENCE (SIZE (1..maxTrCH)) OF
										TransportChannelIdentity

BSIC-VerificationRequired ::=		ENUMERATED {
										required, notRequired }

BSICReported ::=					CHOICE {
	-- Value maxCellMeas is not allowed for verifiedBSIC
	verifiedBSIC						INTEGER (0..maxCellMeas),
	nonVerifiedBSIC						BCCH-ARFCN
}

BurstModeParameters ::=				SEQUENCE {
	burstStart							INTEGER (0..15),
	burstLength							INTEGER (10..25),
	burstFreq							INTEGER (1..16)
}

CellDCH-ReportCriteria ::=			CHOICE {
	intraFreqReportingCriteria			IntraFreqReportingCriteria,
	periodicalReportingCriteria			PeriodicalReportingCriteria
}

CellDCH-ReportCriteria-LCR-r4 ::=	CHOICE {
	intraFreqReportingCriteria			IntraFreqReportingCriteria-LCR-r4,
	periodicalReportingCriteria			PeriodicalReportingCriteria
}

CellDCHMeasOccasionPattern-LCR ::=		SEQUENCE {
	patternIdentifier					INTEGER(0..maxMeasOccasionPattern-1),
	statusFlag							ENUMERATED	{
											activate, deactivate},
	measurementPurpose					BIT STRING (SIZE (5))				OPTIONAL,
	measurementOccasionPatternParameter	MeasurementOccasionPatternParameter	OPTIONAL
}
CellDCHMeasOccasionInfo-TDD128-r9::=	SEQUENCE {
	cellDCHMeasOccasionSequenceList 			SEQUENCE (SIZE (1..maxMeasOccasionPattern)) OF
										CellDCHMeasOccasionPattern-LCR
}

-- Actual value CellIndividualOffset = IE value * 0.5
CellIndividualOffset ::=			INTEGER (-20..20)


CellInfo ::=						SEQUENCE {
	cellIndividualOffset				CellIndividualOffset			 	DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	}
}

CellInfo-r4 ::=						SEQUENCE {
	cellIndividualOffset				CellIndividualOffset			 	DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN
		},
		tdd									SEQUENCE {
			primaryCCPCH-Info					PrimaryCCPCH-Info-r4,
			primaryCCPCH-TX-Power				PrimaryCCPCH-TX-Power		OPTIONAL,
			timeslotInfoList					TimeslotInfoList-r4			OPTIONAL,
			readSFN-Indicator					BOOLEAN

		}
	}
}

CellInfo-LCR-r8-ext ::=						SEQUENCE {
	cellSelectionReselectionInfo		CellSelectReselectInfoMC-RSCP	OPTIONAL
}

CellInfo-r9 ::=						SEQUENCE {
	cellIndividualOffset				CellIndividualOffset			 	DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN
		},
		tdd									SEQUENCE {
			primaryCCPCH-Info					PrimaryCCPCH-Info-r4,
			primaryCCPCH-TX-Power				PrimaryCCPCH-TX-Power		OPTIONAL,
			timeslotInfoList					TimeslotInfoList-r4			OPTIONAL,
			readSFN-Indicator					BOOLEAN
		}
	},
	-- For 1.28 Mcps TDD, cellSelectionReselectionInfo is optional present when sent
	-- in Measurement Control.For FDD, this IE is not needed.
	cellSelectionReselectionInfo		CellSelectReselectInfoMC-RSCP		OPTIONAL
}

CellInfoListToBeExcluded::=		SEQUENCE (SIZE (1..maxExcludedDetectedSetCells )) OF
										PrimaryCPICH-Info

CellInfoSI-RSCP ::=					SEQUENCE {
	cellIndividualOffset				CellIndividualOffset		 		DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-RSCP		OPTIONAL
}

CellInfoSI-RSCP-LCR-r4 ::=			SEQUENCE {
	cellIndividualOffset				CellIndividualOffset		 		DEFAULT 0,
	referenceTimeDifferenceToCell		ReferenceTimeDifferenceToCell		OPTIONAL,
	primaryCCPCH-Info					PrimaryCCPCH-Info-LCR-r4,
	primaryCCPCH-TX-Power				PrimaryCCPCH-TX-Power				OPTIONAL,
	timeslotInfoList					TimeslotInfoList-LCR-r4				OPTIONAL,
	readSFN-Indicator					BOOLEAN,
	cellSelectionReselectionInfo		CellSelectReselectInfoSIB-11-12-RSCP		OPTIONAL
}

CellInfoSI-ECN0 ::=					SEQUENCE {
	cellIndividualOffset				CellIndividualOffset		 		DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-ECN0	OPTIONAL
}

CellInfoSI-ECN0-LCR-r4 ::=			SEQUENCE {
	cellIndividualOffset				CellIndividualOffset		 		DEFAULT 0,
	referenceTimeDifferenceToCell		ReferenceTimeDifferenceToCell		OPTIONAL,
	primaryCCPCH-Info					PrimaryCCPCH-Info-LCR-r4,
	primaryCCPCH-TX-Power				PrimaryCCPCH-TX-Power				OPTIONAL,
	timeslotInfoList					TimeslotInfoList-LCR-r4				OPTIONAL,
	readSFN-Indicator					BOOLEAN,
	cellSelectionReselectionInfo		CellSelectReselectInfoSIB-11-12-ECN0	OPTIONAL
}

CellInfoSI-HCS-RSCP ::=				SEQUENCE {
	cellIndividualOffset				CellIndividualOffset		 		DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-HCS-RSCP	OPTIONAL
}

CellInfoSI-HCS-RSCP-LCR-r4 ::=		SEQUENCE {
	cellIndividualOffset				CellIndividualOffset		 		DEFAULT 0,
	referenceTimeDifferenceToCell		ReferenceTimeDifferenceToCell		OPTIONAL,
	primaryCCPCH-Info					PrimaryCCPCH-Info-LCR-r4,
	primaryCCPCH-TX-Power				PrimaryCCPCH-TX-Power				OPTIONAL,
	timeslotInfoList					TimeslotInfoList-LCR-r4				OPTIONAL,
	readSFN-Indicator					BOOLEAN,
	cellSelectionReselectionInfo		CellSelectReselectInfoSIB-11-12-HCS-RSCP	OPTIONAL
}

CellInfoSI-HCS-ECN0 ::=				SEQUENCE {
	cellIndividualOffset				CellIndividualOffset		 		DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-HCS-ECN0	OPTIONAL
}

CellInfoSI-HCS-ECN0-LCR-r4 ::=		SEQUENCE {
	cellIndividualOffset				CellIndividualOffset		 		DEFAULT 0,
	referenceTimeDifferenceToCell		ReferenceTimeDifferenceToCell		OPTIONAL,
	primaryCCPCH-Info					PrimaryCCPCH-Info-LCR-r4,
	primaryCCPCH-TX-Power				PrimaryCCPCH-TX-Power				OPTIONAL,
	timeslotInfoList					TimeslotInfoList-LCR-r4				OPTIONAL,
	readSFN-Indicator					BOOLEAN,
	cellSelectionReselectionInfo		CellSelectReselectInfoSIB-11-12-HCS-ECN0	OPTIONAL
}

CellMeasuredResults ::=				SEQUENCE {
	cellIdentity						CellIdentity						OPTIONAL,
	-- dummy is not used in this version of the specification, it should
	-- not be sent and if received it should be ignored.
	dummy			SFN-SFN-ObsTimeDifference			OPTIONAL,
	cellSynchronisationInfo			CellSynchronisationInfo			OPTIONAL,
	modeSpecificInfo					CHOICE {
		fdd									SEQUENCE {
			primaryCPICH-Info					PrimaryCPICH-Info,
			cpich-Ec-N0							CPICH-Ec-N0					OPTIONAL,
			cpich-RSCP							CPICH-RSCP					OPTIONAL,
			pathloss							Pathloss					OPTIONAL
		},
		tdd									SEQUENCE {
			cellParametersID					CellParametersID,
			proposedTGSN						TGSN						OPTIONAL,
			primaryCCPCH-RSCP					PrimaryCCPCH-RSCP			OPTIONAL,
			pathloss							Pathloss					OPTIONAL,
			timeslotISCP-List					TimeslotISCP-List			OPTIONAL
		}
	}
}

-- The IE is created in order to add missing DeltaRSCPPerCell IE from Rel-5.
CellMeasuredResults-r9 ::=				SEQUENCE {
	cellIdentity						CellIdentity						OPTIONAL,
	cellSynchronisationInfo			CellSynchronisationInfo			OPTIONAL,
	modeSpecificInfo					CHOICE {
		fdd									SEQUENCE {
			primaryCPICH-Info					PrimaryCPICH-Info,
			cpich-Ec-N0							CPICH-Ec-N0					OPTIONAL,
			cpich-RSCP							CPICH-RSCP					OPTIONAL,
			deltaRSCPPerCell					DeltaRSCPPerCell			OPTIONAL,
			pathloss							Pathloss					OPTIONAL
		},
		tdd									SEQUENCE {
			cellParametersID					CellParametersID,
			proposedTGSN						TGSN						OPTIONAL,
			primaryCCPCH-RSCP					PrimaryCCPCH-RSCP			OPTIONAL,
			pathloss							Pathloss					OPTIONAL,
			timeslotISCP-List					TimeslotISCP-List			OPTIONAL
		}
	}
}

CellMeasuredResults-v920ext ::= SEQUENCE {
	csgIdentity							CSG-Identity						OPTIONAL,
	csgMemberIndication					ENUMERATED { member }				OPTIONAL
}

CellMeasuredResults-vc50ext ::= SEQUENCE {
	csg-MemberPLMNList					CSG-MemberPLMNList					OPTIONAL
}

CellMeasurementEventResults ::=		CHOICE {
	fdd									SEQUENCE (SIZE (1..maxCellMeas)) OF
											PrimaryCPICH-Info,
	tdd									SEQUENCE (SIZE (1..maxCellMeas)) OF
											PrimaryCCPCH-Info
}

CellMeasurementEventResultsOnSecUlFreq ::=	CHOICE {
	fdd									SEQUENCE (SIZE (1.. maxCellMeasOnSecULFreq)) OF
											PrimaryCPICH-Info,
	spare								NULL
}

CellMeasurementEventResults-LCR-r4 ::=	SEQUENCE (SIZE (1..maxCellMeas)) OF
											PrimaryCCPCH-Info-LCR-r4

CellReportingQuantities ::=			SEQUENCE {
	-- dummy is not used in this version of the specification
	-- and if received it should be ignored.
	dummy					SFN-SFN-OTD-Type,
	cellIdentity-reportingIndicator						BOOLEAN,
	cellSynchronisationInfoReportingIndicator			BOOLEAN,
	modeSpecificInfo					CHOICE {
		fdd									SEQUENCE {
			cpich-Ec-N0-reportingIndicator							BOOLEAN,
			cpich-RSCP-reportingIndicator							BOOLEAN,
			pathloss-reportingIndicator							BOOLEAN
		},
		tdd									SEQUENCE {
			timeslotISCP-reportingIndicator						BOOLEAN,
			proposedTGSN-ReportingRequired						BOOLEAN,
			primaryCCPCH-RSCP-reportingIndicator					BOOLEAN,
			pathloss-reportingIndicator							BOOLEAN
		}
	}
}

CellSelectReselectInfoMC-RSCP ::=	SEQUENCE {
	q-OffsetS-N						Q-OffsetS-N						DEFAULT 0,
	maxAllowedUL-TX-Power				MaxAllowedUL-TX-Power				OPTIONAL,
	hcs-NeighbouringCellInformation-RSCP
										HCS-NeighbouringCellInformation-RSCP	OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12 ::=	SEQUENCE {
	q-Offset1S-N						Q-OffsetS-N							DEFAULT 0,
	q-Offset2S-N						Q-OffsetS-N							OPTIONAL,
	maxAllowedUL-TX-Power				MaxAllowedUL-TX-Power				OPTIONAL,
	hcs-NeighbouringCellInformation-RSCP
										HCS-NeighbouringCellInformation-RSCP	OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-RSCP ::=	SEQUENCE {
	q-OffsetS-N						Q-OffsetS-N						DEFAULT 0,
	maxAllowedUL-TX-Power				MaxAllowedUL-TX-Power				OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-ECN0 ::=	SEQUENCE {
	q-Offset1S-N						Q-OffsetS-N						DEFAULT 0,
	q-Offset2S-N						Q-OffsetS-N						DEFAULT 0,
	maxAllowedUL-TX-Power				MaxAllowedUL-TX-Power				OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-HCS-RSCP ::=	SEQUENCE {
	q-OffsetS-N						Q-OffsetS-N						DEFAULT 0,
	maxAllowedUL-TX-Power				MaxAllowedUL-TX-Power				OPTIONAL,
	hcs-NeighbouringCellInformation-RSCP
										HCS-NeighbouringCellInformation-RSCP	OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-HCS-ECN0 ::=	SEQUENCE {
	q-Offset1S-N						Q-OffsetS-N						DEFAULT 0,
	q-Offset2S-N						Q-OffsetS-N						DEFAULT 0,
	maxAllowedUL-TX-Power				MaxAllowedUL-TX-Power				OPTIONAL,
	hcs-NeighbouringCellInformation-ECN0
										HCS-NeighbouringCellInformation-ECN0	OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfo-v590ext ::= SEQUENCE {
	deltaQrxlevmin					DeltaQrxlevmin					OPTIONAL,
	deltaQhcs						DeltaRSCP						OPTIONAL
}

CellSelectReselectInfoPCHFACH-v5b0ext ::= SEQUENCE {
	q-Hyst-l-S-PCH				Q-Hyst-S-Fine						OPTIONAL,
	q-Hyst-l-S-FACH				Q-Hyst-S-Fine						OPTIONAL,
	q-Hyst-2-S-PCH				Q-Hyst-S-Fine						OPTIONAL,
	q-Hyst-2-S-FACH				Q-Hyst-S-Fine						OPTIONAL,
	t-Reselection-S-PCH			T-Reselection-S						OPTIONAL,
	t-Reselection-S-FACH		T-Reselection-S-Fine				OPTIONAL
}

CellSelectReselectInfoTreselectionScaling-v5c0ext ::= SEQUENCE {
	-- For speed detection, the same HCS parameters are utilised
	non-HCS-t-CR-Max							T-CRMax									OPTIONAL,
	speedDependentScalingFactor					SpeedDependentScalingFactor				OPTIONAL,
	interFrequencyTreselectionScalingFactor		TreselectionScalingFactor				OPTIONAL,
	interRATTreselectionScalingFactor			TreselectionScalingFactor				OPTIONAL
}

CellsForInterFreqMeasList ::=		SEQUENCE (SIZE  (1..maxCellMeas)) OF
										InterFreqCellID

CellsForInterFreqMeasList-r12 ::=		SEQUENCE (SIZE  (1..maxCellMeas-ext)) OF
										InterFreqCellID-r12

CellsForInterRATMeasList ::=			SEQUENCE (SIZE  (1..maxCellMeas)) OF
										InterRATCellID

CellsForIntraFreqMeasList ::=		SEQUENCE (SIZE  (1..maxCellMeas)) OF
										IntraFreqCellID

CellsForIntraFreqMeasListOnSecULFreq ::=	SEQUENCE (SIZE  (1..maxCellMeasOnSecULFreq)) OF
												IntraFreqCellIDOnSecULFreq

CellSynchronisationInfo ::=			SEQUENCE {
	modeSpecificInfo					CHOICE {
		fdd									SEQUENCE {
			countC-SFN-Frame-difference			CountC-SFN-Frame-difference		OPTIONAL,
			tm									INTEGER(0..38399)
		},
		tdd									SEQUENCE {
			countC-SFN-Frame-difference			CountC-SFN-Frame-difference		OPTIONAL
		}
	}
}

CellToReport ::=					SEQUENCE {
	bsicReported						BSICReported
}

CellToReportList ::=				SEQUENCE (SIZE (1..maxCellMeas)) OF
										CellToReport

CNAVclockModel ::=					SEQUENCE {
	cnavToc								BIT STRING (SIZE (11)),
	cnavTop								BIT STRING (SIZE (11)),
	cnavURA0							BIT STRING (SIZE (5)),
	cnavURA1							BIT STRING (SIZE (3)),
	cnavURA2							BIT STRING (SIZE (3)),
	cnavAf2								BIT STRING (SIZE (10)),
	cnavAf1								BIT STRING (SIZE (20)),
	cnavAf0								BIT STRING (SIZE (26)),
	cnavTgd								BIT STRING (SIZE (13)),
	cnavISCl1cp							BIT STRING (SIZE (13))				OPTIONAL,
	cnavISCl1cd							BIT STRING (SIZE (13))				OPTIONAL,
	cnavISCl1ca							BIT STRING (SIZE (13))				OPTIONAL,
	cnavISCl2c							BIT STRING (SIZE (13))				OPTIONAL,
	cnavISCl5i5							BIT STRING (SIZE (13))				OPTIONAL,
	cnavISCl5q5							BIT STRING (SIZE (13))				OPTIONAL
}

CodePhaseSearchWindow ::=			ENUMERATED {
										w1023, w1, w2, w3, w4, w6, w8,
										w12, w16, w24, w32, w48, w64,
										w96, w128, w192 }

CountC-SFN-Frame-difference ::= SEQUENCE {
	-- Actual value countC-SFN-High = IE value * 256
	countC-SFN-High					INTEGER(0..15),
	off								INTEGER(0..255)
}

-- SPARE: CPICH-Ec-No, Max = 49
-- Values above Max are spare
CPICH-Ec-N0 ::=						INTEGER (0..63)

-- SPARE: CPICH- RSCP, Max = 91
-- Values above Max are spare
CPICH-RSCP ::=						INTEGER (0..127)

CPICH-Ec-N0-RSCP ::=	SEQUENCE {
	cpich-Ec-N0						CPICH-Ec-N0,
	cpich-RSCP						CPICH-RSCP
}

CSG-MemberPLMNList ::=	SEQUENCE(SIZE (1..6)) OF
										PLMN-Identity

CSGCellInfo ::=			SEQUENCE {
	modeSpecificInfo					CHOICE {
		fdd									SEQUENCE {
			startPSC							PrimaryCPICH-Info,
			numberOfPSCs						INTEGER (1..512)
		},
		tdd								NULL
	}
}

CSGCellInfoList ::=		SEQUENCE (SIZE (1..maxMeasCSGRange)) OF
										CSGCellInfo

CSGInterFreqCellInfo ::=			SEQUENCE {
	frequencyInfo						FrequencyInfo,
	cSGInterFreqCellInfoListperFreq		CSGCellInfoList
}

CSGInterFreqCellInfoList ::=		SEQUENCE (SIZE (1..maxFreq)) OF
										CSGInterFreqCellInfo

CSGIntraFreqCellInfoList ::=			CSGCellInfoList

CSGProximityDetection ::=			SEQUENCE {
	uTRACSGProximityDetec					ENUMERATED { enable }			OPTIONAL,
	e-UTRACSGProximityDetec					ENUMERATED { enable }			OPTIONAL
}

CSGProximityIndication ::=				SEQUENCE {
	cSGproximityInd						ENUMERATED {entering, leaving },
	radioAccessTechnology				CHOICE {
		uTRA								SEQUENCE {
			cSGFrequencyInfoUTRA					FrequencyInfo
		},
		e-UTRA								SEQUENCE {
			cSGFrequencyInfoEUTRA					EARFCN
		}
	}
}

CSGProximityIndication-vb50ext ::=				SEQUENCE {
	cSGFrequencyInfoEUTRA					EARFCNExtension						OPTIONAL
}

DataBitAssistance ::=				SEQUENCE {
	ganss-signal-id						GANSS-Signal-Id,
	data-bits							BIT STRING (SIZE (1..1024))
}

DataBitAssistanceList ::=			SEQUENCE (SIZE (1..maxGANSSSat)) OF
										DataBitAssistanceSat

DataBitAssistanceSat ::= 			SEQUENCE {
	satID								INTEGER(0..63),
	dataBitAssistanceSgnList			DataBitAssistanceSgnList
}

DataBitAssistanceSgnList ::= 		SEQUENCE (SIZE (1..maxSgnType)) OF
										DataBitAssistance

DeltaPRC ::=						INTEGER (-127..127)

--Actual value DeltaQrxlevmin = IE value * 2
DeltaQrxlevmin ::= INTEGER (-2..-1)

DeltaRSCP ::= INTEGER (-5..-1)

DeltaRSCPPerCell ::= SEQUENCE {
	deltaRSCP						DeltaRSCP	OPTIONAL
}

-- Actual value DeltaRRC = IE value * 0.032
DeltaRRC ::=						INTEGER (-7..7)

DeltaUT1 ::=						SEQUENCE {
	b1									BIT STRING (SIZE (11)),
	b2									BIT STRING (SIZE (10))
}

DGANSSInfo ::=						SEQUENCE {
	ganssSignalId						GANSS-Signal-Id						OPTIONAL,
	ganssStatusHealth					GANSS-Status-Health,
	dgansssignalInformationList			DGANSSSignalInformationList			OPTIONAL
}

DGANSSInfo-r9 ::=						SEQUENCE {
	ganssSignalId						GANSS-Signal-Id						OPTIONAL,
	ganssStatusHealth					GANSS-Status-Health,
	dgansssignalInformationList			DGANSSSignalInformationList-r9		OPTIONAL
}

DGANSSInfo-v920ext ::=				SEQUENCE {
	dgansssignalInformationList			DGANSSSignalInformationList-v920ext	OPTIONAL
}

DGANSSInfoList ::=					SEQUENCE (SIZE (1..maxSgnType)) OF
										DGANSSInfo

DGANSSInfoList-r9 ::=					SEQUENCE (SIZE (1..maxSgnType)) OF
										DGANSSInfo-r9

DGANSSInfoList-v920ext ::=			SEQUENCE (SIZE (1..maxSgnType)) OF
										DGANSSInfo-v920ext

DGANSSSignalInformation ::=			SEQUENCE {
	satId								INTEGER (0..63),
	iode-dganss							BIT STRING (SIZE (10)),
	udre								UDRE,
	ganss-prc							INTEGER (-2047..2047),		-- scale factor 0.32
	ganss-rrc							INTEGER (-127..127)			-- scale factor 0.032
}

DGANSSSignalInformation-r9 ::=			SEQUENCE {
	satId								INTEGER (0..63),
	iode-dganss							BIT STRING (SIZE (10)),
	udre								UDRE,
	ganss-prc							INTEGER (-2047..2047),		-- scale factor 0.32
	ganss-rrc							INTEGER (-127..127),		-- scale factor 0.032
	udreGrowthRate						UDREGrowthRate 						OPTIONAL,
	udreValidityTime					UDREValidityTime					OPTIONAL
}

DGANSSSignalInformation-v920ext ::=	SEQUENCE	{
	udreGrowthRate						UDREGrowthRate 			OPTIONAL,
	udreValidityTime					UDREValidityTime		OPTIONAL
}

DGANSSSignalInformationList ::=		SEQUENCE (SIZE (1..maxGANSSSat)) OF
										DGANSSSignalInformation

DGANSSSignalInformationList-r9 ::=		SEQUENCE (SIZE (1..maxGANSSSat)) OF
										DGANSSSignalInformation-r9

DGANSSSignalInformationList-v920ext ::= SEQUENCE (SIZE (1..maxGANSSSat)) OF
											DGANSSSignalInformation-v920ext

DGANSS-Sig-Id-Req ::=				BIT STRING (SIZE (8))

DGPS-CorrectionSatInfo ::=			SEQUENCE {
	satID								SatID,
	iode								IODE,
	udre								UDRE,
	prc									PRC,
	rrc									RRC,
-- dummy1 and dummy2 are not used in this version of the specification and should be ignored.
	dummy1							DeltaPRC,
	dummy2							DeltaRRC,
	-- dummy3 and dummy4 are not used in this version of the specification. They should not
	-- be sent and if received they should be ignored.
	dummy3							DeltaPRC			OPTIONAL,
	dummy4							DeltaRRC			OPTIONAL
}

DGPS-CorrectionSatInfo-r9 ::=			SEQUENCE {
	satID								SatID,
	iode								IODE,
	udre								UDRE,
	prc									PRC,
	rrc									RRC,
	udreGrowthRate						UDREGrowthRate 						OPTIONAL,
	udreValidityTime					UDREValidityTime					OPTIONAL
}

DGPS-CorrectionSatInfo-v920ext ::=	SEQUENCE {
	udreGrowthRate						UDREGrowthRate 			OPTIONAL,
	udreValidityTime					UDREValidityTime		OPTIONAL
}

DGPS-CorrectionSatInfoList ::=		SEQUENCE (SIZE (1..maxSat)) OF
										DGPS-CorrectionSatInfo

DGPS-CorrectionSatInfoList-r9 ::=		SEQUENCE (SIZE (1..maxSat)) OF
										DGPS-CorrectionSatInfo-r9

DGPS-CorrectionSatInfoList-v920ext ::=	SEQUENCE (SIZE (1..maxSat)) OF
											DGPS-CorrectionSatInfo-v920ext

DiffCorrectionStatus ::=			ENUMERATED {
										udre-1-0, udre-0-75, udre-0-5, udre-0-3,
										udre-0-2, udre-0-1, noData, invalidData }

DL-TransportChannelBLER ::=			INTEGER (0..63)

DopplerUncertainty ::=				ENUMERATED {
										hz12-5, hz25, hz50, hz100, hz200,
										spare3, spare2, spare1 }

DopplerUncertaintyExt ::=			ENUMERATED {
										hz300, hz400, hz500, hz600, noInformation,
										spare3, spare2, spare1 }

EllipsoidPoint ::=					SEQUENCE {
	latitudeSign		ENUMERATED { north, south },
	latitude			INTEGER (0..8388607),
	longitude			INTEGER (-8388608..8388607)
}


EllipsoidPointAltitude ::=			SEQUENCE {
	latitudeSign		ENUMERATED { north, south },
	latitude			INTEGER (0..8388607),
	longitude			INTEGER (-8388608..8388607),
	altitudeDirection	ENUMERATED {height, depth},
	altitude			INTEGER (0..32767)
}


EllipsoidPointAltitudeEllipsoide ::=	SEQUENCE {
	latitudeSign			ENUMERATED { north, south },
	latitude				INTEGER (0..8388607),
	longitude				INTEGER (-8388608..8388607),
	altitudeDirection		ENUMERATED {height, depth},
	altitude				INTEGER (0..32767),
	uncertaintySemiMajor	INTEGER (0..127),
	uncertaintySemiMinor	INTEGER (0..127),
	-- Actual value orientationMajorAxis = IE value * 2
	orientationMajorAxis	INTEGER (0..89),
	uncertaintyAltitude		INTEGER (0..127),
	confidence				INTEGER (0..100)
}


EllipsoidPointUncertCircle ::=		SEQUENCE {
	latitudeSign			ENUMERATED { north, south },
	latitude				INTEGER (0..8388607),
	longitude				INTEGER (-8388608..8388607),
	uncertaintyCode			INTEGER (0..127)
}


EllipsoidPointUncertEllipse ::=		SEQUENCE {
	latitudeSign			ENUMERATED { north, south },
	latitude				INTEGER (0..8388607),
	longitude				INTEGER (-8388608..8388607),
	uncertaintySemiMajor	INTEGER (0..127),
	uncertaintySemiMinor	INTEGER (0..127),
	-- Actual value orientationMajorAxis = IE value * 2
	orientationMajorAxis	INTEGER (0..89),
	confidence				INTEGER (0..100)
}


EnvironmentCharacterisation ::=		ENUMERATED {
										possibleHeavyMultipathNLOS,
										lightMultipathLOS,
										notDefined,
										spare }

EUTRA-CSGMemberPLMNList ::=	SEQUENCE(SIZE (1..5)) OF
										PLMN-Identity

Eutra-EventResult ::=				SEQUENCE {
	earfcn								EARFCN,
	reportedCells						SEQUENCE (SIZE (1..maxReportedEUTRACellPerFreq)) OF
											EUTRA-PhysicalCellIdentity
}

EUTRA-EventResult-vb50ext ::=		SEQUENCE {
	earfcn								EARFCNExtension							OPTIONAL
}

EUTRA-EventResult-vc50ext ::=		SEQUENCE {
	earfcn								EARFCNExtension2,
	reportedCells						SEQUENCE (SIZE (1..maxReportedEUTRACellPerFreq)) OF
											EUTRA-PhysicalCellIdentity
}

Eutra-EventResultList ::=			SEQUENCE (SIZE (1..maxReportedEUTRAFreqs)) OF
										Eutra-EventResult

EUTRA-EventResultList-vb50ext ::=	SEQUENCE (SIZE (1..maxReportedEUTRAFreqs)) OF
										EUTRA-EventResult-vb50ext

EUTRA-EventResultList-vc50ext ::=	SEQUENCE (SIZE (1..maxReportedEUTRAFreqs-ext)) OF
										EUTRA-EventResult-vc50ext

EUTRA-EventResults ::=				SEQUENCE {
	eventID								EventIDInterRAT,
	eutra-EventResultsList				Eutra-EventResultList
}

EUTRA-EventResults-vb50ext ::=		SEQUENCE {
	eutra-EventResultsList				EUTRA-EventResultList-vb50ext
}

EUTRA-EventResults-vc50ext ::=		SEQUENCE {
	eutra-EventResultsList				EUTRA-EventResultList-vc50ext
}

EUTRA-EventResultsForCELLFACH ::= 				SEQUENCE {
	eutraFrequencyIndicator						BIT STRING (SIZE (maxNumEUTRAFreqs-FACH))
}

EUTRA-EventResultsForCELLFACH-vc50ext ::= 			SEQUENCE {
	eutraFrequencyIndicator						BIT STRING (SIZE (maxNumEUTRAFreqs-FACH))
}

EUTRA-FrequencyAndPriorityInfo ::=	SEQUENCE {
	earfcn								EARFCN,
	measurementBandwidth				EUTRA-MeasurementBandwidth				OPTIONAL,
	priority							INTEGER (0..maxPrio-1),
	-- Actual value = IE value * 2
	qRxLevMinEUTRA						INTEGER (-70..-22),
	-- Actual value = IE value * 2
	threshXhigh							INTEGER (0..31),
	-- Actual value = IE value * 2
	threshXlow							INTEGER (0..31),
	eutra-exclude-ListedCellList			EUTRA-Exclude-listedCellPerFreqList		OPTIONAL,
	eutraDetection						BOOLEAN
}

EUTRA-FrequencyAndPriorityInfo-v920ext ::=	SEQUENCE {
	qqualMinEUTRA						INTEGER (-34..-3)						OPTIONAL,
	threshXhigh2						INTEGER (0..31)							OPTIONAL,
	threshXlow2							INTEGER (0..31)							OPTIONAL
}

EUTRA-FrequencyAndPriorityInfo-vb50ext ::=	SEQUENCE {
	qqualMinEUTRA-WB					INTEGER (-34..-3)							OPTIONAL
}

EUTRA-FrequencyAndPriorityInfo-vc50ext ::=	SEQUENCE {
	qqualMinRSRQ-OnAllSymbols				INTEGER (-34..-3)						OPTIONAL,
	reducedMeasurementPerformance		ENUMERATED {true}							OPTIONAL
}

EUTRA-FrequencyAndPriorityInfo-vd20ext ::=	SEQUENCE {
	subpriority							ENUMERATED {oDot2,oDot4,oDot6,oDot8}		OPTIONAL
}

EUTRA-FrequencyAndPriorityInfoExtension-vb50ext ::=	SEQUENCE {
	earfcn								EARFCNExtension,
	measurementBandwidth				EUTRA-MeasurementBandwidth				OPTIONAL,
	priority							INTEGER (0..maxPrio-1),
	-- Actual value = IE value * 2
	qRxLevMinEUTRA						INTEGER (-70..-22),
	-- Actual value = IE value * 2
	threshXhigh							INTEGER (0..31),
	-- Actual value = IE value * 2
	threshXlow							INTEGER (0..31),
	qqualMinEUTRA						INTEGER (-34..-3)						OPTIONAL,
	threshXhigh2						INTEGER (0..31)							OPTIONAL,
	threshXlow2							INTEGER (0..31)							OPTIONAL,
	eutra-exclude-listedCellList			EUTRA-Exclude-listedCellPerFreqList		OPTIONAL,
	eutraDetection						BOOLEAN
}

EUTRA-FrequencyAndPriorityInfoExtension-vb80ext ::=	SEQUENCE {
	qqualMinEUTRA-WB					INTEGER (-34..-3)						OPTIONAL
}

EUTRA-FrequencyAndPriorityInfoExtension-vc50ext ::=	SEQUENCE {
	qqualMinRSRQ-OnAllSymbols				INTEGER (-34..-3)						OPTIONAL,
	reducedMeasurementPerformance		ENUMERATED {true}							OPTIONAL
}

EUTRA-FrequencyAndPriorityInfoExtension-vd20ext ::=	SEQUENCE {
	subpriority							ENUMERATED {oDot2,oDot4,oDot6,oDot8}		OPTIONAL
}

EUTRA-FrequencyAndPriorityInfoExtensionList ::=	SEQUENCE (SIZE (1..maxNumEUTRAFreqs)) OF
											EUTRA-FrequencyAndPriorityInfoExtension-vb50ext

EUTRA-FrequencyAndPriorityInfoExtensionList-vb80ext ::=	SEQUENCE  (SIZE (1..maxNumEUTRAFreqs)) OF
											EUTRA-FrequencyAndPriorityInfoExtension-vb80ext

EUTRA-FrequencyAndPriorityInfoExtensionList-vc50ext ::=	SEQUENCE  (SIZE (1..maxNumEUTRAFreqs)) OF
											EUTRA-FrequencyAndPriorityInfoExtension-vc50ext

EUTRA-FrequencyAndPriorityInfoExtensionList-vd20ext ::=	SEQUENCE  (SIZE (1..maxNumEUTRAFreqs)) OF
											EUTRA-FrequencyAndPriorityInfoExtension-vd20ext

EUTRA-FrequencyAndPriorityInfoList ::=	SEQUENCE (SIZE (1..maxNumEUTRAFreqs)) OF
											EUTRA-FrequencyAndPriorityInfo

EUTRA-FrequencyAndPriorityInfoList-v920ext ::=	SEQUENCE (SIZE (1..maxNumEUTRAFreqs)) OF
											EUTRA-FrequencyAndPriorityInfo-v920ext

EUTRA-FrequencyAndPriorityInfoList-vb50ext ::=	SEQUENCE  (SIZE (1..maxNumEUTRAFreqs)) OF
											EUTRA-FrequencyAndPriorityInfo-vb50ext

EUTRA-FrequencyAndPriorityInfoList-vc50ext ::=	SEQUENCE  (SIZE (1..maxNumEUTRAFreqs)) OF
											EUTRA-FrequencyAndPriorityInfo-vc50ext

EUTRA-FrequencyAndPriorityInfoList-vd20ext ::=	SEQUENCE  (SIZE (1..maxNumEUTRAFreqs)) OF
											EUTRA-FrequencyAndPriorityInfo-vd20ext

EUTRA-FrequencyList ::=				SEQUENCE {
	eutraFrequencyRemoval				EUTRA-FrequencyRemoval,
	eutraNewFrequencies					EUTRA-FrequencyInfoList					OPTIONAL
}

EUTRA-FrequencyList-r9 ::=			SEQUENCE {
	eutraFrequencyRemoval				EUTRA-FrequencyRemoval,
	eutraNewFrequencies					EUTRA-FrequencyInfoList					OPTIONAL,
	eutraSIAcquisition					EUTRA-SIAcquisition						OPTIONAL
}

EUTRA-FrequencyList-r11 ::=			SEQUENCE {
	eutraFrequencyRemoval				EUTRA-FrequencyRemoval-r11,
	eutraNewFrequencies					EUTRA-FrequencyInfoList-r11				OPTIONAL,
	eutraSIAcquisition					EUTRA-SIAcquisition-r11					OPTIONAL
}

EUTRA-FrequencyList-r12 ::=			SEQUENCE {
	eutraFrequencyRemoval				EUTRA-FrequencyRemoval-r11,
	eutraNewFrequencies				EUTRA-FrequencyInfoList-r12				OPTIONAL,
	eutraSIAcquisition					EUTRA-SIAcquisition-r11					OPTIONAL,
	rsrqMeasOnAllSymbols				BOOLEAN										OPTIONAL
}

EUTRA-SIAcquisition ::=				SEQUENCE {
	earfcn								EARFCN,
	physicalCellIdentity				EUTRA-PhysicalCellIdentity
}

EUTRA-SIAcquisition-r11 ::=				SEQUENCE {
-- If the IE earfcn is set to a value of 65535, then the EARFCN
--	value for that instance shall be read from the IE earfcnExt.
	earfcn								EARFCN,
	earfcnExt							EARFCNExtension					OPTIONAL,
	physicalCellIdentity				EUTRA-PhysicalCellIdentity
}

EUTRA-MeasuredCells ::=				SEQUENCE {
	physicalCellIdentity				EUTRA-PhysicalCellIdentity,
	rSRP								INTEGER (0..97)		OPTIONAL,
	rSRQ								INTEGER (0..33)		OPTIONAL
}

Eutra-MeasuredResult ::=			SEQUENCE {
	earfcn								EARFCN,
	measuredEUTRACells					SEQUENCE (SIZE (1..maxReportedEUTRACellPerFreq)) OF
											EUTRA-MeasuredCells
}

EUTRA-MeasuredResult-vb50ext ::=		SEQUENCE {
	earfcn								EARFCNExtension							OPTIONAL
}

Eutra-MeasuredResultList ::=		SEQUENCE (SIZE (1..maxReportedEUTRAFreqs)) OF
										Eutra-MeasuredResult

EUTRA-MeasuredResultList-vb50ext ::=	SEQUENCE (SIZE (1..maxReportedEUTRAFreqs)) OF
										EUTRA-MeasuredResult-vb50ext

EUTRA-MeasuredResults ::=			SEQUENCE {
	eutraMeasuredResultList				Eutra-MeasuredResultList
}

EUTRA-MeasuredResults-vb50ext ::=	SEQUENCE {
	eutraMeasuredResultList				EUTRA-MeasuredResultList-vb50ext
}

EUTRA-MeasuredCells-v920ext ::=		SEQUENCE {
	eutraSIacquisitionResults			EUTRA-SIacquisitionResults
}

EUTRA-MeasuredCells-vc50ext ::=		SEQUENCE {
	physicalCellIdentity				EUTRA-PhysicalCellIdentity	OPTIONAL,
	rSRP								INTEGER (0..97)				OPTIONAL,
	rSRQ								INTEGER (0..33)				OPTIONAL,
	eutraSIacquisitionResults			EUTRA-SIacquisitionResults-vc50ext,
	rsrqExtension						INTEGER (-30..46)		OPTIONAL
}

Eutra-MeasuredResult-v920ext ::=	SEQUENCE {
	measuredEUTRACells-v920ext			SEQUENCE (SIZE (1..maxReportedEUTRACellPerFreq)) OF
											EUTRA-MeasuredCells-v920ext
}

Eutra-MeasuredResult-vc50ext ::=	SEQUENCE {
	earfcn								EARFCNExtension2			OPTIONAL,
	measuredEUTRACells-vc50ext			SEQUENCE (SIZE (1..maxReportedEUTRACellPerFreq)) OF
											EUTRA-MeasuredCells-vc50ext
}

Eutra-MeasuredResultList-v920ext ::=	SEQUENCE (SIZE (1..maxReportedEUTRAFreqs)) OF
											Eutra-MeasuredResult-v920ext

Eutra-MeasuredResultList-vc50ext ::=	SEQUENCE (SIZE (1..maxReportedEUTRAFreqs)) OF
											Eutra-MeasuredResult-vc50ext

EUTRA-MeasuredResults-v920ext ::=	SEQUENCE {
	eutraMeasuredResultList-v920ext		Eutra-MeasuredResultList-v920ext
}

EUTRA-MeasuredResults-vc50ext ::=	SEQUENCE {
	eutraMeasuredResultList-vc50ext		Eutra-MeasuredResultList-vc50ext
}

EUTRA-SIacquisitionResults ::= 		SEQUENCE {
	cgiInfo								SEQUENCE {
		plmn-Identity 						PLMN-Identity,
		cellIdentity 						BIT STRING (SIZE (28)),
		trackingAreaCode 					BIT STRING (SIZE (16))
	},
	csgIdentity							CSG-Identity						OPTIONAL,
	csgMemberIndication					ENUMERATED { member }				OPTIONAL
}

EUTRA-SIacquisitionResults-vc50ext ::= 		SEQUENCE {
	cgiInfo								CGI-Info							OPTIONAL,
	csgIdentity							CSG-Identity						OPTIONAL,
	csgMemberIndication					ENUMERATED { member }				OPTIONAL,
	csgMemberPLMN 						EUTRA-CSGMemberPLMNList				OPTIONAL,
	primaryPLMNSuitable					ENUMERATED { true }					OPTIONAL
}

CGI-Info ::=						SEQUENCE {
		plmn-Identity 						PLMN-Identity,
		cellIdentity 						BIT STRING (SIZE (28)),
		trackingAreaCode 					BIT STRING (SIZE (16))
}

EUTRA-FrequencyRemoval ::=			CHOICE {
		removeAllFrequencies			NULL,
		removeSomeFrequencies			SEQUENCE (SIZE (1..maxNumEUTRAFreqs)) OF
											EARFCN,
		removeNoFrequencies				NULL
}

EUTRA-FrequencyRemoval-r11 ::=			CHOICE {
		removeAllFrequencies			NULL,
		removeSomeFrequencies			FrequenciesToRemove,
		removeNoFrequencies				NULL
}

EUTRA-FrequencyInfoList ::=			SEQUENCE (SIZE (1..maxNumEUTRAFreqs)) OF
										EUTRA-FrequencyInfo

EUTRA-FrequencyInfoList-r11 ::=			SEQUENCE (SIZE (1..maxNumEUTRAFreqs)) OF
										EUTRA-FrequencyInfo-r11

EUTRA-FrequencyInfoList-r12 ::=			SEQUENCE (SIZE (1..maxNumEUTRAFreqs)) OF
										EUTRA-FrequencyInfo-r12

EUTRA-FrequencyInfo ::=				SEQUENCE {
	earfcn								EARFCN,
	measurementBandwidth				EUTRA-MeasurementBandwidth				OPTIONAL,
	eutra-exclude-listedCellList			EUTRA-Exclude-listedCellPerFreqList		OPTIONAL
}

EUTRA-FrequencyInfo-r11 ::=	SEQUENCE {
-- If the IE earfcn is set to a value of 65535, then the EARFCN
-- value for that instance shall be read from the IE earfcnExt.
	earfcn								EARFCN,
	earfcnExt							EARFCNExtension							OPTIONAL,
	measurementBandwidth				EUTRA-MeasurementBandwidth				OPTIONAL,
	eutra-exclude-listedCellList			EUTRA-Exclude-listedCellPerFreqList		OPTIONAL,
	widebandRSRQMeasurements			ENUMERATED {true}						OPTIONAL
}

EUTRA-FrequencyInfo-r12 ::=	SEQUENCE {
	earfcn								EARFCNExtension2,
	reducedMeasurementPerformance		ENUMERATED {true}						OPTIONAL,
	measurementBandwidth				EUTRA-MeasurementBandwidth				OPTIONAL,
	eutra-exclude-listedCellList			EUTRA-Exclude-listedCellPerFreqList		OPTIONAL,
	widebandRSRQMeasurements			ENUMERATED {true}						OPTIONAL
}

EUTRA-FrequencyRACHReportingInfo ::= SEQUENCE {
	eutra-FrequencyListIndicator				BIT STRING (SIZE (maxNumEUTRAFreqs)),
	eutra-FrequencyRepQuantityRACH				ENUMERATED { rsrp, rsrq },
	eutra-FrequencyRACHReportingThreshold		INTEGER (0..97),
	rachReportingPriority				ENUMERATED { 	intraEUTRAInter, interIntraEUTRA,
														interEUTRAIntra, eUTRAIntraInter,
														eUTRAInterIntra, spare3,
														spare2, spare1		 }		OPTIONAL
}

EUTRA-FrequencyRACHReportingInfo-vc50ext ::= SEQUENCE {
    eutra-FrequencyListIndicator               BIT STRING (SIZE (maxNumEUTRAFreqs)),
	eutra-FrequencyRACHReportingThresholdExtension		INTEGER (-30..-1)		OPTIONAL
}

EUTRA-MeasurementBandwidth ::=		ENUMERATED { mbw6, mbw15, mbw25, mbw50, mbw75, mbw100 }

EUTRA-MeasurementForCELLFACH ::=			SEQUENCE {
	eutraFrequenciesForMeasurement			SEQUENCE (SIZE (1..maxNumEUTRAFreqs-FACH)) OF
												EARFCNRange,
	reportCriteria							ENUMERATED { event-triggeredreporting,																						periodicalReporting },
	measurementQuantity						ENUMERATED { rsrp, rsrq },
	reportingThreshold						INTEGER (0..97)
}

EUTRA-MeasurementForCELLFACH-r12 ::=		SEQUENCE {
	eutraFrequenciesForMeasurement			SEQUENCE (SIZE (1..maxNumEUTRAFreqs-FACH-ext)) OF
												EARFCNRange,
	reportCriteria							ENUMERATED { event-triggeredreporting,																						periodicalReporting },
	measurementQuantity						ENUMERATED { rsrp, rsrq },
	reportingThreshold						INTEGER (-30..97)
}
FrequenciesToRemove ::= SEQUENCE (SIZE (1..maxNumEUTRAFreqs)) OF
											EARFCNRange

Event1a ::=							SEQUENCE {
	triggeringCondition					TriggeringCondition2,
	reportingRange						ReportingRange,
	forbiddenAffectCellList				ForbiddenAffectCellList					OPTIONAL,
	w									W,
	reportDeactivationThreshold			ReportDeactivationThreshold,
	reportingAmount						ReportingAmount,
	reportingInterval					ReportingInterval
}

Event1a-r4 ::=						SEQUENCE {
	triggeringCondition					TriggeringCondition2,
	reportingRange						ReportingRange,
	forbiddenAffectCellList				ForbiddenAffectCellList-r4				OPTIONAL,
	w									W,
	reportDeactivationThreshold			ReportDeactivationThreshold,
	reportingAmount						ReportingAmount,
	reportingInterval					ReportingInterval
}

Event1a-OnSecUlFreq-r9 ::=						SEQUENCE {
	triggeringCondition					TriggeringCondition2,
	reportingRange						ReportingRange,
	forbiddenAffectCellListOnSecULFreq	ForbiddenAffectCellListOnSecULFreq		OPTIONAL,
	w									W,
	reportDeactivationThreshold			ReportDeactivationThreshold,
	reportingAmount						ReportingAmount,
	reportingInterval					ReportingInterval
}

Event1a-LCR-r4 ::=					SEQUENCE {
	triggeringCondition					TriggeringCondition2,
	reportingRange						ReportingRange,
	forbiddenAffectCellList				ForbiddenAffectCellList-LCR-r4			OPTIONAL,
	w									W,
	reportDeactivationThreshold			ReportDeactivationThreshold,
	reportingAmount						ReportingAmount,
	reportingInterval					ReportingInterval
}

Event1b ::=							SEQUENCE {
	triggeringCondition					TriggeringCondition1,
	reportingRange						ReportingRange,
	forbiddenAffectCellList				ForbiddenAffectCellList					OPTIONAL,
	w									W
}

Event1b-r4 ::=						SEQUENCE {
	triggeringCondition					TriggeringCondition1,
	reportingRange						ReportingRange,
	forbiddenAffectCellList				ForbiddenAffectCellList-r4				OPTIONAL,
	w									W
}

Event1b-r7 ::=						SEQUENCE {
	triggeringCondition					TriggeringCondition1,
	reportingRange						ReportingRange,
	forbiddenAffectCellList				ForbiddenAffectCellList-r4				OPTIONAL,
	w									W,
	periodicReportingInfo-1b			PeriodicReportingInfo-1b				OPTIONAL
}

Event1b-OnSecUlFreq-r9 ::=						SEQUENCE {
	triggeringCondition					TriggeringCondition1,
	reportingRange						ReportingRange,
	forbiddenAffectCellListOnSecULFreq	ForbiddenAffectCellListOnSecULFreq		OPTIONAL,
	w									W,
	periodicReportingInfo-1b			PeriodicReportingInfo-1b				OPTIONAL
}

Event1b-LCR-r4 ::=					SEQUENCE {
	triggeringCondition					TriggeringCondition1,
	reportingRange						ReportingRange,
	forbiddenAffectCellList				ForbiddenAffectCellList-LCR-r4			OPTIONAL,
	w									W
}

Event1c ::=							SEQUENCE {
	replacementActivationThreshold		ReplacementActivationThreshold,
	reportingAmount						ReportingAmount,
	reportingInterval					ReportingInterval
}

Event1d ::=							SEQUENCE {
	triggeringCondition					TriggeringCondition2	OPTIONAL,
	useCIO								BOOLEAN					OPTIONAL
}

Event1e ::=						SEQUENCE {
	triggeringCondition					TriggeringCondition2,
	thresholdUsedFrequency				ThresholdUsedFrequency
}

Event1e-r6 ::=					SEQUENCE {
	triggeringCondition					TriggeringCondition2,
	thresholdUsedFrequency				ThresholdUsedFrequency-r6
}

Event1f ::=						SEQUENCE {
	triggeringCondition					TriggeringCondition1,
	thresholdUsedFrequency				ThresholdUsedFrequency
}

Event1f-r6 ::=					SEQUENCE {
	triggeringCondition					TriggeringCondition1,
	thresholdUsedFrequency				ThresholdUsedFrequency-r6
}

Event1j-r6 ::=					SEQUENCE {
	replacementActivationThreshold		ReplacementActivationThreshold,
	reportingAmount						ReportingAmount,
	reportingInterval					ReportingInterval
}

Event2a ::=							SEQUENCE {
	-- dummy is not used in this version of the specification and should be ignored
	dummy								Threshold,
	usedFreqW							W,
	hysteresis							HysteresisInterFreq,
	timeToTrigger						TimeToTrigger,
	reportingCellStatus					ReportingCellStatus					OPTIONAL,
	nonUsedFreqParameterList			NonUsedFreqParameterList			OPTIONAL
}

Event2a-r6 ::=						SEQUENCE {
	usedFreqW							W,
	hysteresis							HysteresisInterFreq,
	timeToTrigger						TimeToTrigger,
	reportingCellStatus					ReportingCellStatus					OPTIONAL,
	nonUsedFreqParameterList			NonUsedFreqWList-r6					OPTIONAL
}

Event2a-r10 ::=					SEQUENCE {
	usedFreqW							W,
	hysteresis							HysteresisInterFreq,
	timeToTrigger						TimeToTrigger,
	reportingCellStatus					ReportingCellStatus-r10				OPTIONAL,
	nonUsedFreqParameterList			NonUsedFreq2aParameterList-r10		OPTIONAL
}

Event2a-r11 ::=					SEQUENCE {
	usedFreqW							W,
	hysteresis							HysteresisInterFreq,
	timeToTrigger						TimeToTrigger,
	reportingCellStatus					ReportingCellStatus-r10				OPTIONAL,
	nonUsedFreqParameterList			NonUsedFreq2aParameterList-r11		OPTIONAL
}

Event2b ::=							SEQUENCE {
	usedFreqThreshold					Threshold,
	usedFreqW							W,
	hysteresis							HysteresisInterFreq,
	timeToTrigger						TimeToTrigger,
	reportingCellStatus					ReportingCellStatus					OPTIONAL,
	nonUsedFreqParameterList			NonUsedFreqParameterList			OPTIONAL
}

Event2b-r6 ::=						SEQUENCE {
	usedFreqThreshold					Threshold-r6,
	usedFreqW							W,
	hysteresis							HysteresisInterFreq,
	timeToTrigger						TimeToTrigger,
	reportingCellStatus					ReportingCellStatus					OPTIONAL,
	nonUsedFreqParameterList			NonUsedFreqParameterList-r6			OPTIONAL
}

Event2b-r10 ::=					SEQUENCE {
	usedFreqThreshold					Threshold-r6,
	usedFreqW							W,
	hysteresis							HysteresisInterFreq,
	timeToTrigger						TimeToTrigger,
	reportingCellStatus					ReportingCellStatus-r10				OPTIONAL,
	nonUsedFreqParameterList			NonUsedFreqParameterList-r10		OPTIONAL
}

Event2b-r11 ::=					SEQUENCE {
	usedFreqThreshold					Threshold-r6,
	usedFreqW							W,
	hysteresis							HysteresisInterFreq,
	timeToTrigger						TimeToTrigger,
	reportingCellStatus					ReportingCellStatus-r10				OPTIONAL,
	nonUsedFreqParameterList			NonUsedFreqParameterList-r11		OPTIONAL
}

Event2c ::=							SEQUENCE {
	hysteresis							HysteresisInterFreq,
	timeToTrigger						TimeToTrigger,
	reportingCellStatus					ReportingCellStatus					OPTIONAL,
	nonUsedFreqParameterList			NonUsedFreqParameterList			OPTIONAL
}

Event2c-r6 ::=						SEQUENCE {
	hysteresis							HysteresisInterFreq,
	timeToTrigger						TimeToTrigger,
	reportingCellStatus					ReportingCellStatus					OPTIONAL,
	nonUsedFreqParameterList			NonUsedFreqParameterList-r6			OPTIONAL
}

Event2c-r10 ::=					SEQUENCE {
	hysteresis							HysteresisInterFreq,
	timeToTrigger						TimeToTrigger,
	reportingCellStatus					ReportingCellStatus-r10				OPTIONAL,
	nonUsedFreqParameterList			NonUsedFreqParameterList-r10		OPTIONAL
}

Event2c-r11 ::=					SEQUENCE {
	hysteresis							HysteresisInterFreq,
	timeToTrigger						TimeToTrigger,
	reportingCellStatus					ReportingCellStatus-r10				OPTIONAL,
	nonUsedFreqParameterList			NonUsedFreqParameterList-r11		OPTIONAL
}

Event2d ::=							SEQUENCE {
	usedFreqThreshold					Threshold,
	usedFreqW							W,
	hysteresis							HysteresisInterFreq,
	timeToTrigger						TimeToTrigger,
	reportingCellStatus					ReportingCellStatus					OPTIONAL
}

Event2d-r6 ::=						SEQUENCE {
	usedFreqThreshold					Threshold-r6,
	usedFreqW							W,
	hysteresis							HysteresisInterFreq,
	timeToTrigger						TimeToTrigger,
	reportingCellStatus					ReportingCellStatus					OPTIONAL
}

Event2d-r10 ::=					SEQUENCE {
	usedFreqThreshold					Threshold-r6,
	usedFreqW							W,
	hysteresis							HysteresisInterFreq,
	timeToTrigger						TimeToTrigger,
	reportingCellStatus					ReportingCellStatus-r10				OPTIONAL
}

Event2e ::=							SEQUENCE {
	hysteresis							HysteresisInterFreq,
	timeToTrigger						TimeToTrigger,
	reportingCellStatus					ReportingCellStatus					OPTIONAL,
	nonUsedFreqParameterList			NonUsedFreqParameterList			OPTIONAL
}

Event2e-r6 ::=						SEQUENCE {
	hysteresis							HysteresisInterFreq,
	timeToTrigger						TimeToTrigger,
	reportingCellStatus					ReportingCellStatus					OPTIONAL,
	nonUsedFreqParameterList			NonUsedFreqParameterList-r6			OPTIONAL
}

Event2e-r10 ::=					SEQUENCE {
	hysteresis							HysteresisInterFreq,
	timeToTrigger						TimeToTrigger,
	reportingCellStatus					ReportingCellStatus-r10				OPTIONAL,
	nonUsedFreqParameterList			NonUsedFreqParameterList-r10		OPTIONAL
}

Event2e-r11 ::=					SEQUENCE {
	hysteresis							HysteresisInterFreq,
	timeToTrigger						TimeToTrigger,
	reportingCellStatus					ReportingCellStatus-r10				OPTIONAL,
	nonUsedFreqParameterList			NonUsedFreqParameterList-r11		OPTIONAL
}

Event2f ::=							SEQUENCE {
	usedFreqThreshold					Threshold,
	usedFreqW							W,
	hysteresis							HysteresisInterFreq,
	timeToTrigger						TimeToTrigger,
	reportingCellStatus					ReportingCellStatus					OPTIONAL
}

Event2f-r6 ::=						SEQUENCE {
	usedFreqThreshold					Threshold-r6,
	usedFreqW							W,
	hysteresis							HysteresisInterFreq,
	timeToTrigger						TimeToTrigger,
	reportingCellStatus					ReportingCellStatus					OPTIONAL
}

Event2f-r10 ::=					SEQUENCE {
	usedFreqThreshold					Threshold-r6,
	usedFreqW							W,
	hysteresis							HysteresisInterFreq,
	timeToTrigger						TimeToTrigger,
	reportingCellStatus					ReportingCellStatus-r10				OPTIONAL
}


Event2g ::=					SEQUENCE {
	hysteresis							HysteresisInterFreq,
	timeToTrigger						TimeToTrigger,
	reportingCellStatus					ReportingCellStatus-r10				OPTIONAL,
	useCIO								ENUMERATED {true}					OPTIONAL
}

Event3a ::=							SEQUENCE {
	thresholdOwnSystem					Threshold,
	w									W,
	thresholdOtherSystem				Threshold,
	hysteresis							Hysteresis,
	timeToTrigger						TimeToTrigger,
	reportingCellStatus					ReportingCellStatus					OPTIONAL
}

Event3b ::=							SEQUENCE {
	thresholdOtherSystem				Threshold,
	hysteresis							Hysteresis,
	timeToTrigger						TimeToTrigger,
	reportingCellStatus					ReportingCellStatus					OPTIONAL

}

Event3c ::=							SEQUENCE {
	thresholdOtherSystem				Threshold,
	hysteresis							Hysteresis,
	timeToTrigger						TimeToTrigger,
	reportingCellStatus					ReportingCellStatus					OPTIONAL
}

Event3d ::=							SEQUENCE {
	hysteresis							Hysteresis,
	timeToTrigger						TimeToTrigger,
	reportingCellStatus					ReportingCellStatus					OPTIONAL
}

Event3a-r12 ::=							SEQUENCE {
	thresholdOwnSystem					Threshold,
	w									W,
	thresholdOtherSystem				Threshold-r12,
	hysteresis							Hysteresis,
	timeToTrigger						TimeToTrigger,
	reportingCellStatus					ReportingCellStatus					OPTIONAL
}

Event3b-r12 ::=							SEQUENCE {
	thresholdOtherSystem				Threshold-r12,
	hysteresis							Hysteresis,
	timeToTrigger						TimeToTrigger,
	reportingCellStatus					ReportingCellStatus					OPTIONAL

}

Event3c-r12 ::=							SEQUENCE {
	thresholdOtherSystem				Threshold-r12,
	hysteresis							Hysteresis,
	timeToTrigger						TimeToTrigger,
	reportingCellStatus					ReportingCellStatus					OPTIONAL
}

EventIDInterFreq ::=				ENUMERATED {
										e2a, e2b, e2c, e2d, e2e, e2f, e2g, spare1 }

EventIDInterRAT ::=					ENUMERATED {
										e3a, e3b, e3c, e3d }

EventIDIntraFreq ::=				ENUMERATED {
										e1a, e1b, e1c, e1d, e1e,
										e1f, e1g, e1h, e1i, e1j,
										spare6, spare5, spare4, spare3, spare2,
										spare1 }

EventResults ::=					CHOICE {
	intraFreqEventResults				IntraFreqEventResults,
	interFreqEventResults				InterFreqEventResults,
	interRATEventResults				InterRATEventResults,
	trafficVolumeEventResults			TrafficVolumeEventResults,
	qualityEventResults					QualityEventResults,
	ue-InternalEventResults				UE-InternalEventResults,
	ue-positioning-MeasurementEventResults	UE-Positioning-MeasurementEventResults,
	spare								NULL
}

EventResults-v770ext ::=			CHOICE {
	ue-positioning-MeasurementEventResults	UE-Positioning-MeasurementEventResults-v770ext
}

EventResults-v860ext ::=			CHOICE {
	ue-positioning-MeasurementEventResults	UE-Positioning-MeasurementEventResults-v860ext
}

EventResults-va40ext ::=			CHOICE {
	interFreqEventResults				InterFreqEventResults-va40ext
}

EventResultsOnSecUlFreq ::= SEQUENCE {
	intraFreqEventResults						IntraFreqEventResultsOnSecUlFreq
}

ExtraDoppler ::=					SEQUENCE {
	-- Doppler 1st order term, -0.2..+0.1 m/s2
	-- ( = -42..+21 with 1/210 m/s2 resolution)
	dopplerFirstOrder					INTEGER (-42.. 21),
	dopplerUncertainty					ENUMERATED { dopU40, dopU20, dopU10, dopU5, dopU2-5,
											spare3, spare2, spare1 }
}

ExtraDopplerExtension ::=			SEQUENCE {
	-- Doppler 1st order term, -0.2..+0.1 m/s2
	-- ( = -42..+21 with 1/210 m/s2 resolution)
	dopplerFirstOrder					INTEGER (-42.. 21),
	dopplerUncertaintyExt				ENUMERATED { dopU60, dopU80, dopU100, dopU120,
 												noInformation, spare3, spare2, spare1 }
}


ExtraDopplerInfo ::=				SEQUENCE {
	-- Actual value doppler1stOrder = IE value * 0.023
	doppler1stOrder						INTEGER (-42..21),
	dopplerUncertainty					DopplerUncertainty
}

ExtraDopplerInfoExtension ::=		SEQUENCE {
	-- Actual value doppler1stOrder = IE value * 0.023
	doppler1stOrder						INTEGER (-42..21),
	dopplerUncertaintyExt				DopplerUncertaintyExt
}

FACH-MeasurementOccasionInfo ::=	SEQUENCE {
	fACH-meas-occasion-coeff			INTEGER (1..12)						OPTIONAL,
	inter-freq-FDD-meas-ind				BOOLEAN,
	-- inter-freq-TDD-meas-ind is for 3.84Mcps TDD and 7.68 Mcps TDD. For 1.28Mcps TDD, the IE in
	-- FACH-MeasurementOccasionInfo-LCR-r4-ext is used.
	inter-freq-TDD-meas-ind				BOOLEAN,
	inter-RAT-meas-ind					SEQUENCE (SIZE (1..maxOtherRAT)) OF
											RAT-Type						OPTIONAL
}

FACH-MeasurementOccasionInfo-LCR-r4-ext ::=	SEQUENCE {
	inter-freq-TDD128-meas-ind					BOOLEAN
}

FilterCoefficient ::=				ENUMERATED {
										fc0, fc1, fc2, fc3, fc4, fc5,
										fc6, fc7, fc8, fc9, fc11, fc13,
										fc15, fc17, fc19, spare1 }

FilteredUEPowerHeadroomReportInfo ::=	SEQUENCE {
	timeToTrigger						TimeToTrigger,
	hysteresis1						Hysteresis							OPTIONAL,
	hysteresis2						Hysteresis							OPTIONAL,
	uePowerHeadroomThreshold1			UE-PowerHeadroomThreshold			OPTIONAL,
	uePowerHeadroomThreshold2			UE-PowerHeadroomThreshold			OPTIONAL,
	filterCoefficient					FilterCoefficient					OPTIONAL
}

-- Actual value FineSFN-SFN = IE value * 0.0625
FineSFN-SFN ::=						INTEGER (0..15)

ForbiddenAffectCell ::=				CHOICE {
	fdd									PrimaryCPICH-Info,
	tdd									PrimaryCCPCH-Info
}

ForbiddenAffectCell-r4 ::=			CHOICE {
	fdd									PrimaryCPICH-Info,
	tdd									PrimaryCCPCH-Info-r4
}

ForbiddenAffectCell-LCR-r4 ::=		SEQUENCE {
	tdd									PrimaryCCPCH-Info-LCR-r4
}

ForbiddenAffectCellList ::=			SEQUENCE (SIZE (1..maxCellMeas)) OF
										ForbiddenAffectCell

ForbiddenAffectCellList-r4 ::=			SEQUENCE (SIZE (1..maxCellMeas)) OF
										ForbiddenAffectCell-r4

ForbiddenAffectCellList-LCR-r4 ::=	SEQUENCE (SIZE (1..maxCellMeas)) OF
										ForbiddenAffectCell-LCR-r4

ForbiddenAffectCellListOnSecULFreq ::=	SEQUENCE (SIZE (1.. maxCellMeasOnSecULFreq)) OF
											ForbiddenAffectCellOnSecULFreq

ForbiddenAffectCellOnSecULFreq ::=	SEQUENCE {
	primaryCPICH						PrimaryCPICH-Info
}

FreqQualityEstimateQuantity-FDD ::= ENUMERATED {
										cpich-Ec-N0,
										cpich-RSCP }

FreqQualityEstimateQuantity-TDD ::= ENUMERATED {
										primaryCCPCH-RSCP }

GanssDataBits ::=					SEQUENCE {
	ganssTod							INTEGER (0..86399),
	dataBitAssistance					ReqDataBitAssistance
}

GANSSDecipheringKeys ::=			SEQUENCE {
	currentDecipheringKey				BIT STRING (SIZE (56)),
	nextDecipheringKey					BIT STRING (SIZE (56))
}

GANSSGenericData ::=				SEQUENCE {
	ganssId								INTEGER (0..7)									OPTIONAL,
	ganssTimeModelsList					GANSSTimeModelsList								OPTIONAL,
	uePositioningDGANSSCorrections		UE-Positioning-DGANSSCorrections				OPTIONAL,
	uePositioningGANSSNavigationModel	UE-Positioning-GANSS-NavigationModel			OPTIONAL,
	uePositioningGANSSRealTimeIntegrity		UE-Positioning-GANSS-RealTimeIntegrity		OPTIONAL,
	uePositioningGANSSDataBitAssistance		UE-Positioning-GANSS-Data-Bit-Assistance	OPTIONAL,
	uePositioningGANSSReferenceMeasurementInfo
										UE-Positioning-GANSS-ReferenceMeasurementInfo	OPTIONAL,
	uePositioningGANSSAlmanac			UE-Positioning-GANSS-Almanac					OPTIONAL,
	uePositioningGANSSUTCModel			UE-Positioning-GANSS-UTCModel					OPTIONAL
}

GANSSGenericData-v860ext ::=		SEQUENCE {
	uePositiningGANSSsbasID				UE-Positioning-GANSS-SBAS-ID					OPTIONAL,
	uePositioningGANSSAddNavigationModels
										UE-Positioning-GANSS-AddNavigationModels		OPTIONAL,
	uePositioningGANSSAlmanac			UE-Positioning-GANSS-Almanac-v860ext			OPTIONAL,
	uePositioningGANSSAddUTCModels		UE-Positioning-GANSS-AddUTCModels				OPTIONAL,
	uePositioningGANSSAuxiliaryInfo		UE-Positioning-GANSS-AuxiliaryInfo				OPTIONAL
}

GANSSGenericData-r8 ::=				SEQUENCE {
	ganssId								INTEGER (0..7)									OPTIONAL,
	uePositiningGANSSsbasID				UE-Positioning-GANSS-SBAS-ID					OPTIONAL,
	ganssTimeModelsList					GANSSTimeModelsList								OPTIONAL,
	uePositioningDGANSSCorrections		UE-Positioning-DGANSSCorrections				OPTIONAL,
	uePositioningGANSSNavigationModel	UE-Positioning-GANSS-NavigationModel			OPTIONAL,
	uePositioningGANSSAddNavigationModels
										UE-Positioning-GANSS-AddNavigationModels		OPTIONAL,
	uePositioningGANSSRealTimeIntegrity	UE-Positioning-GANSS-RealTimeIntegrity			OPTIONAL,
	uePositioningGANSSDataBitAssistance	UE-Positioning-GANSS-Data-Bit-Assistance		OPTIONAL,
	uePositioningGANSSReferenceMeasurementInfo
										UE-Positioning-GANSS-ReferenceMeasurementInfo	OPTIONAL,
	uePositioningGANSSAlmanac			UE-Positioning-GANSS-Almanac-r8					OPTIONAL,
	uePositioningGANSSUTCModel			UE-Positioning-GANSS-UTCModel					OPTIONAL,
	uePositioningGANSSAddUTCModels		UE-Positioning-GANSS-AddUTCModels				OPTIONAL,
	uePositioningGANSSAuxiliaryInfo		UE-Positioning-GANSS-AuxiliaryInfo				OPTIONAL
}

GANSSGenericData-r9 ::=				SEQUENCE {
	ganssId								INTEGER (0..7)									OPTIONAL,
	uePositiningGANSSsbasID				UE-Positioning-GANSS-SBAS-ID					OPTIONAL,
	ganssTimeModelsList					GANSSTimeModelsList								OPTIONAL,
	uePositioningDGANSSCorrections		UE-Positioning-DGANSSCorrections-r9				OPTIONAL,
	uePositioningGANSSNavigationModel	UE-Positioning-GANSS-NavigationModel			OPTIONAL,
	uePositioningGANSSAddNavigationModels
										UE-Positioning-GANSS-AddNavigationModels		OPTIONAL,
	uePositioningGANSSRealTimeIntegrity	UE-Positioning-GANSS-RealTimeIntegrity			OPTIONAL,
	uePositioningGANSSDataBitAssistance	UE-Positioning-GANSS-Data-Bit-Assistance		OPTIONAL,
	uePositioningGANSSReferenceMeasurementInfo
										UE-Positioning-GANSS-ReferenceMeasurementInfo	OPTIONAL,
	uePositioningGANSSAlmanac			UE-Positioning-GANSS-Almanac-r8					OPTIONAL,
	uePositioningGANSSUTCModel			UE-Positioning-GANSS-UTCModel					OPTIONAL,
	uePositioningGANSSAddUTCModels		UE-Positioning-GANSS-AddUTCModels				OPTIONAL,
	uePositioningGANSSAuxiliaryInfo		UE-Positioning-GANSS-AuxiliaryInfo				OPTIONAL
}

GANSSGenericData-v920ext ::=		SEQUENCE {
	uePositioningDGANSSCorrections		UE-Positioning-DGANSSCorrections-v920ext		OPTIONAL
}

GANSSGenericData-va40ext ::=		SEQUENCE {
	ganssTimeModelsList					GANSSTimeModelsList-va40ext						OPTIONAL,
	uePositioningGANSSReferenceMeasurementInfo
										UE-Positioning-GANSS-ReferenceMeasurementInfo-va40ext
																						OPTIONAL,
	uePositioningGANSSAlmanac			UE-Positioning-GANSS-Almanac-va40ext			OPTIONAL
}

GANSSGenericData-vc50ext ::=		SEQUENCE {
	uePositioningDBDSCorrections			UE-Positioning-DBDSCorrections				OPTIONAL,
	uePositioningBDSIonoGridModel			UE-Positioning-BDS-IonoGridModel			OPTIONAL,
	ue-positioning-GANSS-AddNavigationModels
											UE-Positioning-GANSS-AddNavigationModels-vc50ext
																						OPTIONAL, 	uePositioningGANSSReferenceMeasurementInfo
											UE-Positioning-GANSS-ReferenceMeasurementInfo-vc50ext
																						OPTIONAL,
	ue-Positioning-GANSS-Almanac			UE-Positioning-GANSS-Almanac-vc50ext		OPTIONAL,
	ue-Positioning-GANSS-AddUTCModels		UE-Positioning-GANSS-AddUTCModels-vc50ext	OPTIONAL
}

GANSSGenericData-r10 ::=			SEQUENCE {
	ganssId								INTEGER (0..7)									OPTIONAL,
	uePositiningGANSSsbasID				UE-Positioning-GANSS-SBAS-ID					OPTIONAL,
	ganssTimeModelsList					GANSSTimeModelsList-r10							OPTIONAL,
	uePositioningDGANSSCorrections		UE-Positioning-DGANSSCorrections-r9				OPTIONAL,
	uePositioningGANSSNavigationModel	UE-Positioning-GANSS-NavigationModel			OPTIONAL,
	uePositioningGANSSAddNavigationModels
										UE-Positioning-GANSS-AddNavigationModels		OPTIONAL,
	uePositioningGANSSRealTimeIntegrity	UE-Positioning-GANSS-RealTimeIntegrity			OPTIONAL,
	uePositioningGANSSDataBitAssistance	UE-Positioning-GANSS-Data-Bit-Assistance		OPTIONAL,
	uePositioningGANSSReferenceMeasurementInfo
										UE-Positioning-GANSS-ReferenceMeasurementInfo-r10
																						OPTIONAL,
	uePositioningGANSSAlmanac			UE-Positioning-GANSS-Almanac-r10				OPTIONAL,
	uePositioningGANSSUTCModel			UE-Positioning-GANSS-UTCModel					OPTIONAL,
	uePositioningGANSSAddUTCModels		UE-Positioning-GANSS-AddUTCModels				OPTIONAL,
	uePositioningGANSSAuxiliaryInfo		UE-Positioning-GANSS-AuxiliaryInfo				OPTIONAL
}

GANSSGenericData-r12 ::=			SEQUENCE {
	ganssId									INTEGER (0..7)								OPTIONAL,
	uePositiningGANSSsbasID					UE-Positioning-GANSS-SBAS-ID				OPTIONAL,
	ganssTimeModelsList						GANSSTimeModelsList-r10						OPTIONAL,
	uePositioningDGANSSCorrections			UE-Positioning-DGANSSCorrections-r9			OPTIONAL,
	uePositioningDBDSCorrections			UE-Positioning-DBDSCorrections				OPTIONAL,
	uePositioningBDSIonoGridModel			UE-Positioning-BDS-IonoGridModel			OPTIONAL,
	uePositioningGANSSNavigationModel		UE-Positioning-GANSS-NavigationModel		OPTIONAL,
	uePositioningGANSSAddNavigationModels	UE-Positioning-GANSS-AddNavigationModels-r12
																						OPTIONAL,
	uePositioningGANSSRealTimeIntegrity		UE-Positioning-GANSS-RealTimeIntegrity		OPTIONAL,
	uePositioningGANSSDataBitAssistance		UE-Positioning-GANSS-Data-Bit-Assistance	OPTIONAL,
	uePositioningGANSSReferenceMeasurementInfo
											UE-Positioning-GANSS-ReferenceMeasurementInfo-r12
																						OPTIONAL,
	uePositioningGANSSAlmanac				UE-Positioning-GANSS-Almanac-r12			OPTIONAL,
	uePositioningGANSSUTCModel				UE-Positioning-GANSS-UTCModel				OPTIONAL,
	uePositioningGANSSAddUTCModels			UE-Positioning-GANSS-AddUTCModels-r12		OPTIONAL,
	uePositioningGANSSAuxiliaryInfo			UE-Positioning-GANSS-AuxiliaryInfo			OPTIONAL
}

GANSSGenericDataList ::=			SEQUENCE (SIZE (1..maxGANSS)) OF
										GANSSGenericData

GANSSGenericDataList-v860ext ::=	SEQUENCE (SIZE (1..maxGANSS)) OF
										GANSSGenericData-v860ext

GANSSGenericDataList-r8 ::=			SEQUENCE (SIZE (1..maxGANSS)) OF
										GANSSGenericData-r8

GANSSGenericDataList-r9 ::=			SEQUENCE (SIZE (1..maxGANSS)) OF
										GANSSGenericData-r9

GANSSGenericDataList-v920ext ::=	SEQUENCE (SIZE (1..maxGANSS)) OF
										GANSSGenericData-v920ext

GANSSGenericDataList-va40ext ::=	SEQUENCE (SIZE (1..maxGANSS)) OF
										GANSSGenericData-va40ext

GANSSGenericDataList-vc50ext ::=	SEQUENCE (SIZE (1..maxGANSS)) OF
										GANSSGenericData-vc50ext

GANSSGenericDataList-r10 ::=		SEQUENCE (SIZE (1..maxGANSS)) OF
										GANSSGenericData-r10

GANSSGenericDataList-r12 ::=		SEQUENCE (SIZE (1..maxGANSS)) OF
										GANSSGenericData-r12

GANSSGenericMeasurementInfo ::=		SEQUENCE (SIZE (1..maxGANSS)) OF SEQUENCE {
	ganssId								INTEGER (0..7)						OPTIONAL,
	ganssMeasurementSignalList			GANSSMeasurementSignalList
}

GANSSGenericMeasurementInfo-v860ext ::= SEQUENCE (SIZE (1..maxGANSS)) OF SEQUENCE {
	ganssMeasurementSignalList			GANSSMeasurementSignalList-v860ext
}

GANSSMeasurementParameters ::=		SEQUENCE (SIZE (1..maxGANSSSat)) OF SEQUENCE {
	satId								INTEGER (0..63),
	cSurNzero							INTEGER (0..63),
	multipathIndicator					ENUMERATED { nm, low, medium, high },
	carrierQualityIndication			BIT STRING (SIZE (2))				OPTIONAL,
	ganssCodePhase						INTEGER (0..2097151),
	ganssIntegerCodePhase				INTEGER (0..63)						OPTIONAL,
	codePhaseRmsError					INTEGER (0..63),
	doppler								INTEGER (-32768..32767),
	adr									INTEGER (0..33554431)				OPTIONAL
}

GANSSMeasurementParameters-v860ext ::= SEQUENCE (SIZE (1..maxGANSSSat)) OF SEQUENCE {
	ganssIntegerCodePhaseExt			INTEGER (64..127)					OPTIONAL
}

GANSSMeasurementSignalList ::=		SEQUENCE (SIZE (1..maxSgnType)) OF SEQUENCE {
	ganssSignalId						GANSS-Signal-Id						OPTIONAL,
	ganssCodePhaseAmbiguity				INTEGER (0..31)						OPTIONAL,
	ganssMeasurementParameters			GANSSMeasurementParameters
}

GANSSMeasurementSignalList-v860ext ::= SEQUENCE (SIZE (1..maxSgnType)) OF SEQUENCE {
	ganssCodePhaseAmbiguityExt			INTEGER (32..127)					OPTIONAL,
	ganssMeasurementParameters			GANSSMeasurementParameters-v860ext
}

GanssNavigationModelAdditionalData ::= SEQUENCE {
	ganssWeek							INTEGER (0..4095),
	ganssToe							INTEGER (0..167),
	t-toeLimit							INTEGER (0..10),
	satellitesListRelatedDataList		SatellitesListRelatedDataList		OPTIONAL
}

GANSSReferenceTimeOnly ::=			SEQUENCE {
	gANSS-tod							INTEGER (0..3599999),
	gANSS-timeId						INTEGER (0..7)						OPTIONAL,
	gANSS-tod-uncertainty				INTEGER (0..127)					OPTIONAL
}

GanssReqGenericData ::=				SEQUENCE {
	ganssId								INTEGER (0..7)						OPTIONAL,
	ganssRealTimeIntegrity				BOOLEAN,
	ganssDifferentialCorrection			DGANSS-Sig-Id-Req					OPTIONAL,
	ganssAlmanac						BOOLEAN,
	ganssNavigationModel				BOOLEAN,
	ganssTimeModelGNSS-GNSS				BIT STRING (SIZE (8))				OPTIONAL,
	ganssReferenceMeasurementInfo		BOOLEAN,
	ganssDataBits						GanssDataBits						OPTIONAL,
	ganssUTCModel						BOOLEAN,
	ganssNavigationModelAdditionalData	GanssNavigationModelAdditionalData	OPTIONAL
}

GanssReqGenericData-v860ext ::=		SEQUENCE {
	sbasId								UE-Positioning-GANSS-SBAS-ID		OPTIONAL,
	ganssAddNavigationModel				ENUMERATED { true }					OPTIONAL,
	ganssAddUTCmodel					ENUMERATED { true }					OPTIONAL,
	ganssAuxInfo						ENUMERATED { true }					OPTIONAL,
	ganssAddADchoices					SEQUENCE {
		orbitModelID						INTEGER (0..7)					OPTIONAL,
		clockModelID						INTEGER (0..7)					OPTIONAL,
		utcModelID							INTEGER (0..7)					OPTIONAL,
		almanacModelID						INTEGER (0..7)					OPTIONAL
	}		OPTIONAL
}

GanssReqGenericData-vc50ext ::=		SEQUENCE {
	bdsIonoGridModelReq			ENUMERATED { true }		OPTIONAL,
	bdsCorrectionsReq			DGANSS-Sig-Id-Req		OPTIONAL
}

GanssRequestedGenericAssistanceDataList ::= SEQUENCE (SIZE (1..maxGANSS)) OF
										GanssReqGenericData

GanssRequestedGenericAssistanceDataList-v860ext ::= SEQUENCE (SIZE (1..maxGANSS)) OF
										GanssReqGenericData-v860ext

GanssRequestedGenericAssistanceDataList-vc50ext ::= SEQUENCE (SIZE (1..maxGANSS)) OF
										GanssReqGenericData-vc50ext

GANSSSatelliteInformation ::=		SEQUENCE {
	ganssSatId							INTEGER (0..63),
	dopplerZeroOrder					INTEGER (-2048..2047),			-- scale factor 0.5m/s
	extraDoppler						ExtraDoppler						OPTIONAL,
	codePhase							INTEGER (0..1023),
	integerCodePhase					INTEGER (0..127),
	codePhaseSearchWindow				BIT STRING (SIZE (5)),
	azimuthandElevation					AzimuthAndElevation					OPTIONAL
}

GANSSSatelliteInformation-va40ext ::= SEQUENCE {
	azimuthAndElevation					AzimuthAndElevation-va40ext			OPTIONAL
}

GANSSSatelliteInformation-r10 ::=	SEQUENCE {
	ganssSatId							INTEGER (0..63),
	dopplerZeroOrder					INTEGER (-2048..2047),			-- scale factor 0.5m/s
	extraDoppler						ExtraDoppler						OPTIONAL,
	codePhase							INTEGER (0..1023),
	integerCodePhase					INTEGER (0..127),
	codePhaseSearchWindow				BIT STRING (SIZE (5)),
	azimuthandElevation					AzimuthAndElevation-r10				OPTIONAL
}

GANSSSatelliteInformation-vc50ext ::= SEQUENCE {
	extraDopplerExtension				ExtraDopplerExtension				OPTIONAL
}

GANSSSatelliteInformation-r12 ::=	SEQUENCE {
	ganssSatId							INTEGER (0..63),
	dopplerZeroOrder					INTEGER (-2048..2047),			-- scale factor 0.5m/s
	extraDoppler						ExtraDoppler						OPTIONAL,
-- If the extraDopplerExtension is present, the extraDoppler should not be present
	extraDopplerExtension				ExtraDopplerExtension				OPTIONAL,
	codePhase							INTEGER (0..1023),
	integerCodePhase					INTEGER (0..127),
	codePhaseSearchWindow				BIT STRING (SIZE (5)),
	azimuthandElevation					AzimuthAndElevation-r10				OPTIONAL
}

GANSSSatelliteInformationList ::=	SEQUENCE (SIZE (1..maxGANSSSat)) OF
										GANSSSatelliteInformation

GANSSSatelliteInformationList-va40ext ::= SEQUENCE (SIZE (1..maxGANSSSat)) OF
										GANSSSatelliteInformation-va40ext

GANSSSatelliteInformationList-r10 ::=	SEQUENCE (SIZE (1..maxGANSSSat)) OF
										GANSSSatelliteInformation-r10

GANSSSatelliteInformationList-vc50ext ::= SEQUENCE (SIZE (1..maxGANSSSat)) OF
										GANSSSatelliteInformation-vc50ext

GANSSSatelliteInformationList-r12 ::=	SEQUENCE (SIZE (1..maxGANSSSat)) OF
										GANSSSatelliteInformation-r12

GANSSTimeModelsList ::=				SEQUENCE (SIZE (1..maxGANSS-1)) OF
										UE-Positioning-GANSS-TimeModel

GANSSTimeModelsList-va40ext ::=		SEQUENCE (SIZE (1.. maxGANSS-1)) OF
										UE-Positioning-GANSS-TimeModel-va40ext

GANSSTimeModelsList-r10 ::=			SEQUENCE (SIZE (1..maxGANSS-1)) OF
										UE-Positioning-GANSS-TimeModel-r10

GANSS-SAT-Info-Almanac-BDSkp ::=	SEQUENCE {
	svID					INTEGER(0..63),
	bdsAlmToa				BIT STRING (SIZE (8)),
	bdsAlmSqrtA				BIT STRING (SIZE (24)),
	bdsAlmE					BIT STRING (SIZE (17)),
	bdsAlmW					BIT STRING (SIZE (24)),
	bdsAlmM0				BIT STRING (SIZE (24)),
	bdsAlmOmega0			BIT STRING (SIZE (24)),
	bdsAlmOmegaDot			BIT STRING (SIZE (17)),
	bdsAlmDeltaI			BIT STRING (SIZE (16)),
	bdsAlmA0				BIT STRING (SIZE (11)),
	bdsAlmA1				BIT STRING (SIZE (11)),
	bdsSvHealth				BIT STRING (SIZE(9))	OPTIONAL
}

GANSS-SAT-Info-Almanac-GLOkp ::=	SEQUENCE {
	gloAlmNA							BIT STRING (SIZE (11)),
	gloAlmnA							BIT STRING (SIZE (5)),
	gloAlmHA							BIT STRING (SIZE (5)),
	gloAlmLambdaA						BIT STRING (SIZE (21)),
	gloAlmTlambdaA						BIT STRING (SIZE (21)),
	gloAlmDeltaIA						BIT STRING (SIZE (18)),
	gloAkmDeltaTA						BIT STRING (SIZE (22)),
	gloAlmDeltaTdotA					BIT STRING (SIZE (7)),
	gloAlmEpsilonA						BIT STRING (SIZE (15)),
	gloAlmOmegaA						BIT STRING (SIZE (16)),
	gloAlmTauA							BIT STRING (SIZE (10)),
	gloAlmCA							BIT STRING (SIZE (1)),
	gloAlmMA							BIT STRING (SIZE (2))				OPTIONAL
}

GANSS-SAT-Info-Almanac-Kp ::=		SEQUENCE {
	svId								INTEGER(0..63),
	ganss-alm-e							BIT STRING (SIZE (11)),
	ganss-delta-I-alm					BIT STRING (SIZE (11)),
	ganss-omegadot-alm					BIT STRING (SIZE (11)),
	ganss-svstatusINAV-alm				BIT STRING (SIZE (4)),
	ganss-svstatusFNAV-alm				BIT STRING (SIZE (2))				OPTIONAL,
	ganss-delta-a-sqrt-alm				BIT STRING (SIZE (13)),
	ganss-omegazero-alm					BIT STRING (SIZE (16)),
	ganss-m-zero-alm					BIT STRING (SIZE (16)),
	ganss-omega-alm						BIT STRING (SIZE (16)),
	ganss-af-zero-alm					BIT STRING (SIZE (16)),
	ganss-af-one-alm					BIT STRING (SIZE (13))
}

GANSS-SAT-Info-Almanac-MIDIkp ::=	SEQUENCE {
	svID								INTEGER(0..63),
	midiAlmE							BIT STRING (SIZE (11)),
	midiAlmDeltaI						BIT STRING (SIZE (11)),
	midiAlmOmegaDot						BIT STRING (SIZE (11)),
	midiAlmSqrtA						BIT STRING (SIZE (17)),
	midiAlmOmega0						BIT STRING (SIZE (16)),
	midiAlmOmega						BIT STRING (SIZE (16)),
	midiAlmMo							BIT STRING (SIZE (16)),
	midiAlmaf0							BIT STRING (SIZE (11)),
	midiAlmaf1							BIT STRING (SIZE (10)),
	midiAlmL1Health						BIT STRING (SIZE (1)),
	midiAlmL2Health						BIT STRING (SIZE (1)),
	midiAlmL5Health						BIT STRING (SIZE (1))
}

GANSS-SAT-Info-Almanac-NAVkp ::=	SEQUENCE {
	svID								INTEGER(0..63),
	navAlmE								BIT STRING (SIZE (16)),
	navAlmDeltaI						BIT STRING (SIZE (16)),
	navAlmOMEGADOT						BIT STRING (SIZE (16)),
	navAlmSVHealth						BIT STRING (SIZE (8)),
	navAlmSqrtA							BIT STRING (SIZE (24)),
	navAlmOMEGAo						BIT STRING (SIZE (24)),
	navAlmOmega							BIT STRING (SIZE (24)),
	navAlmMo							BIT STRING (SIZE (24)),
	navAlmaf0							BIT STRING (SIZE (11)),
	navAlmaf1							BIT STRING (SIZE (11))
}

GANSS-SAT-Info-Almanac-REDkp ::=	SEQUENCE {
	svID								INTEGER(0..63),
	redAlmDeltaA						BIT STRING (SIZE (8)),
	redAlmOmega0						BIT STRING (SIZE (7)),
	redAlmPhi0							BIT STRING (SIZE (7)),
	redAlmL1Health						BIT STRING (SIZE (1)),
	redAlmL2Health						BIT STRING (SIZE (1)),
	redAlmL5Health						BIT STRING (SIZE (1))
}

GANSS-SAT-Info-Almanac-SBASecef ::=	SEQUENCE {
	sbasAlmDataID						BIT STRING (SIZE (2)),
	svID								INTEGER (0..63),
	sbasAlmHealth						BIT STRING (SIZE (8)),
	sbasAlmXg							BIT STRING (SIZE (15)),
	sbasAlmYg							BIT STRING (SIZE (15)),
	sbasAlmZg							BIT STRING (SIZE (9)),
	sbasAlmXgdot						BIT STRING (SIZE (3)),
	sbasAlmYgDot						BIT STRING (SIZE (3)),
	sbasAlmZgDot						BIT STRING (SIZE (4)),
	sbasAlmTo							BIT STRING (SIZE (11))
}

GANSS-SAT-Info-Almanac-BDSkpList ::=	SEQUENCE (SIZE (1..maxGANSSSat)) OF
											GANSS-SAT-Info-Almanac-BDSkp

GANSS-SAT-Info-Almanac-GLOkpList ::=	SEQUENCE (SIZE (1..maxGANSSSat)) OF
											GANSS-SAT-Info-Almanac-GLOkp

GANSS-SAT-Info-Almanac-KpList ::=	SEQUENCE (SIZE (1..maxGANSSSat)) OF
										GANSS-SAT-Info-Almanac-Kp

GANSS-SAT-Info-Almanac-MIDIkpList ::=	SEQUENCE (SIZE (1..maxGANSSSat)) OF
											GANSS-SAT-Info-Almanac-MIDIkp

GANSS-SAT-Info-Almanac-NAVkpList ::=	SEQUENCE (SIZE (1..maxGANSSSat)) OF
											GANSS-SAT-Info-Almanac-NAVkp

GANSS-SAT-Info-Almanac-REDkpList ::=	SEQUENCE (SIZE (1..maxGANSSSat)) OF
											GANSS-SAT-Info-Almanac-REDkp

GANSS-SAT-Info-Almanac-SBASecefList ::=	SEQUENCE (SIZE (1..maxGANSSSat)) OF
											GANSS-SAT-Info-Almanac-SBASecef

Ganss-Sat-Info-AddNav ::=			SEQUENCE {
	satId								INTEGER (0..63),
	svHealth							BIT STRING (SIZE (6)),
	iod									BIT STRING (SIZE (11)),
	ganssClockModel						UE-Positioning-GANSS-AddClockModels,
	ganssOrbitModel						UE-Positioning-GANSS-AddOrbitModels
}

Ganss-Sat-Info-AddNav-r12 ::=			SEQUENCE {
	satId								INTEGER (0..63),
	svHealth							BIT STRING (SIZE (6)),
	iod									BIT STRING (SIZE (11)),
	ganssClockModel						UE-Positioning-GANSS-AddClockModels-r12,
	ganssOrbitModel						UE-Positioning-GANSS-AddOrbitModels-r12
}

Ganss-Sat-Info-AddNav-vc50ext ::=			SEQUENCE {
	ganssClockModel				UE-Positioning-GANSS-AddClockModels-vc50ext,
	ganssOrbitModel				UE-Positioning-GANSS-AddOrbitModels-vc50ext
}

Ganss-Sat-Info-Nav ::=				SEQUENCE {
	satId								INTEGER (0..63),
	svHealth							BIT STRING (SIZE (9)),
	iod									BIT STRING (SIZE (10)),
	ganssClockModel						UE-Positioning-GANSS-ClockModel,
	ganssOrbitModel						UE-Positioning-GANSS-OrbitModel
}

Ganss-Sat-Info-AddNavList ::= 		SEQUENCE (SIZE (1..maxGANSSSat)) OF
										Ganss-Sat-Info-AddNav

Ganss-Sat-Info-AddNavList-r12 ::= 	SEQUENCE (SIZE (1..maxGANSSSat)) OF
										Ganss-Sat-Info-AddNav-r12

Ganss-Sat-Info-AddNavList-vc50ext ::= 	SEQUENCE (SIZE (1..maxGANSSSat)) OF
										Ganss-Sat-Info-AddNav-vc50ext

Ganss-Sat-Info-NavList ::=			SEQUENCE (SIZE (1..maxGANSSSat)) OF
										Ganss-Sat-Info-Nav

GANSS-Signal-Id ::=					INTEGER (0..7)

GANSS-Status-Health ::=				ENUMERATED {
										udre-scale-1dot0,
										udre-scale-0dot75,
										udre-scale-0dot5,
										udre-scale-0dot3,
										udre-scale-0dot2,
										udre-scale-0dot1,
										no-data,
										invalid-data }

GANSS-Storm-Flag ::=				SEQUENCE {
	storm-flag-one						BOOLEAN,
	storm-flag-two						BOOLEAN,
	storm-flag-three					BOOLEAN,
	storm-flag-four						BOOLEAN,
	storm-flag-five						BOOLEAN
}

GLONASSclockModel ::=				SEQUENCE {
	gloTau								BIT STRING (SIZE (22)),
	gloGamma							BIT STRING (SIZE (11)),
	gloDeltaTau							BIT STRING (SIZE (5)) 				OPTIONAL
}

GPS-MeasurementParam ::=			SEQUENCE {
	satelliteID							INTEGER (0..63),
	c-N0								INTEGER (0..63),
	doppler								INTEGER (-32768..32768),
	wholeGPS-Chips						INTEGER (0..1022),
	fractionalGPS-Chips					INTEGER (0..1023),
	multipathIndicator					MultipathIndicator,
	pseudorangeRMS-Error				INTEGER (0..63)
}

GPS-MeasurementParamList ::=		SEQUENCE (SIZE (1..maxSat)) OF
										GPS-MeasurementParam

GSM-CarrierRSSI ::=					BIT STRING (SIZE (6))

GSM-CellGroup ::=					SEQUENCE {
	startingARFCN						BCCH-ARFCN,
	bandIndicator						ENUMERATED { dcs1800, pcs1900 },
	followingARFCNs						CHOICE {
		explicitListOfARFCNs				SEQUENCE (SIZE (0..31)) OF BCCH-ARFCN,
		equallySpacedARFCNs					SEQUENCE {
			arfcn-Spacing						INTEGER (1..8),
			numberOfFollowingARFCNs				INTEGER (0..31)
		},
		variableBitMapOfARFCNs				OCTET STRING (SIZE (1..16)),
		continuousRangeOfARFCNs				SEQUENCE {
			endingARFCN							BCCH-ARFCN
		}
	}
}

GSM-MeasuredResults ::= 			SEQUENCE {
	gsm-CarrierRSSI						GSM-CarrierRSSI						OPTIONAL,
	-- dummy is not used in this version of the specification, it should
	-- not be sent and if received it should be ignored.
	dummy								INTEGER (46..173)					OPTIONAL,
	bsicReported						BSICReported,
	-- dummy2 is not used in this version of the specification, it should
	-- not be sent and if received it should be ignored.
	dummy2								ObservedTimeDifferenceToGSM			OPTIONAL
}

GSM-MeasuredResultsList ::=			SEQUENCE (SIZE (1..maxReportedGSMCells)) OF
										GSM-MeasuredResults

GPS-TOW-1msec ::=					INTEGER (0..604799999)

GPS-TOW-1sec ::=					INTEGER (0..604799)

GPS-TOW-Assist ::=					SEQUENCE {
	satID								SatID,
	tlm-Message							BIT STRING (SIZE (14)),
	tlm-Reserved						BIT STRING (SIZE (2)),
	alert								BOOLEAN,
	antiSpoof							BOOLEAN
}

GPS-TOW-AssistList ::=				SEQUENCE (SIZE (1..maxSat)) OF
										GPS-TOW-Assist

GSM-CellID ::=						SEQUENCE {
	gsm-CellID							INTEGER (0..maxCellMeas-1)
}

GSM-PriorityInfo ::=				SEQUENCE {
	gsmCellGroup						GSM-CellGroup,
	priority							INTEGER (0..maxPrio-1),
	-- Actual value = IE value * 2 + 1
	qRxLevMinGSM						INTEGER (-58..-13),
	-- Actual value = IE value * 2
	threshXhigh							INTEGER (0..31),
	-- Actual value = IE value * 2
	threshXlow							INTEGER (0..31)
}

GSM-PriorityInfoList ::=			SEQUENCE (SIZE (1..maxNumGSMCellGroup)) OF
										GSM-PriorityInfo

GSMCellGroupingList ::=				SEQUENCE (SIZE (1..maxCellMeas)) OF
										GSM-CellID

HCS-CellReselectInformation-RSCP ::=		SEQUENCE {
	-- TABULAR: The default value for penaltyTime is "notUsed"
	-- Temporary offset is nested inside PenaltyTime-RSCP
	penaltyTime									PenaltyTime-RSCP
}

HCS-CellReselectInformation-ECN0 ::=		SEQUENCE {
	-- TABULAR: The default value for penaltyTime is "notUsed"
	-- Temporary offset is nested inside PenaltyTime-ECN0
	penaltyTime							PenaltyTime-ECN0
}

HCS-NeighbouringCellInformation-RSCP ::= SEQUENCE {
	hcs-PRIO							HCS-PRIO							DEFAULT 0,
	q-HCS								Q-HCS								DEFAULT 0,
	hcs-CellReselectInformation			HCS-CellReselectInformation-RSCP
}

HCS-NeighbouringCellInformation-ECN0 ::= SEQUENCE {
	hcs-PRIO							HCS-PRIO							DEFAULT 0,
	q-HCS								Q-HCS								DEFAULT 0,
	hcs-CellReselectInformation			HCS-CellReselectInformation-ECN0
}

HCS-PRIO ::=						INTEGER (0..7)

HCS-ServingCellInformation ::=		SEQUENCE {
	hcs-PRIO							HCS-PRIO							DEFAULT 0,
	q-HCS								Q-HCS								DEFAULT 0,
	t-CR-Max							T-CRMax								OPTIONAL
}

HorizontalVelocity ::=				SEQUENCE {
	bearing								INTEGER (0..359),
	horizontalSpeed						INTEGER (0..2047)
	}

HorizontalWithVerticalVelocity ::=	SEQUENCE {
	verticalSpeedDirection				ENUMERATED { upward, downward },
	bearing								INTEGER (0..359),
	horizontalSpeed						INTEGER (0..2047),
	verticalSpeed						INTEGER (0..255)
}

HorizontalVelocityWithUncertainty ::=	SEQUENCE {
	bearing								INTEGER (0..359),
	horizontalSpeed						INTEGER (0..2047),
	horizontalSpeedUncertainty			INTEGER (0..255)
}

HorizontalWithVerticalVelocityAndUncertainty ::=	SEQUENCE {
	verticalSpeedDirection				ENUMERATED { upward, downward },
	bearing								INTEGER (0..359),
	horizontalSpeed						INTEGER (0..2047),
	verticalSpeed						INTEGER (0..255),
	horizontalUncertaintySpeed			INTEGER (0..255),
	verticalUncertaintySpeed			INTEGER (0..255)
}

-- Actual value Hysteresis = IE value * 0.5
Hysteresis ::=						INTEGER (0..15)

-- Actual value HysteresisInterFreq = IE value * 0.5
HysteresisInterFreq ::=				INTEGER (0..29)

IdleIntervalInfo ::=				SEQUENCE {
	k									INTEGER (2..3)						OPTIONAL,
	offset								INTEGER (0..7)						OPTIONAL
}

InterFreqCell ::=					SEQUENCE {
	frequencyInfo						FrequencyInfo,
	nonFreqRelatedEventResults			CellMeasurementEventResults
}

InterFreqCell-LCR-r4 ::=			SEQUENCE {
	frequencyInfo						FrequencyInfo,
	nonFreqRelatedEventResults			CellMeasurementEventResults-LCR-r4
}

InterFreqCellID ::=					INTEGER (0..maxCellMeas-1)

InterFreqCellID-r12 ::=				INTEGER (0..maxCellMeas-ext-1)

InterFreqCellInfoList ::=			SEQUENCE {
	removedInterFreqCellList			RemovedInterFreqCellList			OPTIONAL,
	newInterFreqCellList				NewInterFreqCellList				OPTIONAL,
	cellsForInterFreqMeasList			CellsForInterFreqMeasList			OPTIONAL
}

InterFreqCellInfoList-r4 ::=		SEQUENCE {
	removedInterFreqCellList			RemovedInterFreqCellList			OPTIONAL,
	newInterFreqCellList				NewInterFreqCellList-r4				OPTIONAL,
	cellsForInterFreqMeasList			CellsForInterFreqMeasList			OPTIONAL
}

InterFreqCellInfoList-r8 ::=	SEQUENCE {
	removedInterFreqCellList			RemovedInterFreqCellList			OPTIONAL,
	newInterFreqCellList				NewInterFreqCellList-r8				OPTIONAL,
	cellsForInterFreqMeasList			CellsForInterFreqMeasList			OPTIONAL
}

InterFreqCellInfoList-r9 ::=	SEQUENCE {
	removedInterFreqCellList			RemovedInterFreqCellList			OPTIONAL,
	newInterFreqCellList				NewInterFreqCellList-r9				OPTIONAL,
	cellsForInterFreqMeasList			CellsForInterFreqMeasList			OPTIONAL,
	cSGInterFreqCellInfoList			CSGInterFreqCellInfoList			OPTIONAL,
	interFreqSIAcquisition				InterFreqSIAcquisition				OPTIONAL
}

InterFreqCellInfoList-r10 ::=	SEQUENCE {
	removedInterFreqCellList			RemovedInterFreqCellList			OPTIONAL,
	newInterFreqCellList				NewInterFreqCellList-r10			OPTIONAL,
	cellsForInterFreqMeasList			CellsForInterFreqMeasList			OPTIONAL,
	cSGInterFreqCellInfoList			CSGInterFreqCellInfoList			OPTIONAL,
	interFreqSIAcquisition				InterFreqSIAcquisition				OPTIONAL
}

InterFreqCellInfoList-r12 ::=	SEQUENCE {
	removedInterFreqCellList			RemovedInterFreqCellList-r12		OPTIONAL,
	newInterFreqCellList				NewInterFreqCellList-r12			OPTIONAL,
	cellsForInterFreqMeasList			CellsForInterFreqMeasList-r12		OPTIONAL,
	cSGInterFreqCellInfoList			CSGInterFreqCellInfoList			OPTIONAL,
	interFreqSIAcquisition				InterFreqSIAcquisition				OPTIONAL,
	rmp-Frequency-List					RMP-Frequency-List					OPTIONAL
}

InterFreqSIAcquisition ::=			SEQUENCE {
	frequencyInfo						FrequencyInfo,
	modeSpecificInfo					CHOICE {
		fdd									SEQUENCE {
			primaryScramblingCode				PrimaryCPICH-Info
		},
		tdd								NULL
	}
}


InterFreqCellInfoSI-List-RSCP ::=		SEQUENCE {
	removedInterFreqCellList			RemovedInterFreqCellList			OPTIONAL,
	newInterFreqCellList				NewInterFreqCellSI-List-RSCP		OPTIONAL
}

InterFreqCellInfoSI-List-ECN0 ::=		SEQUENCE {
	removedInterFreqCellList			RemovedInterFreqCellList			OPTIONAL,
	newInterFreqCellList				NewInterFreqCellSI-List-ECN0		OPTIONAL
}

InterFreqCellInfoSI-List-HCS-RSCP ::=		SEQUENCE {
	removedInterFreqCellList			RemovedInterFreqCellList			OPTIONAL,
	newInterFreqCellList				NewInterFreqCellSI-List-HCS-RSCP	OPTIONAL
}
InterFreqCellInfoSI-List-HCS-ECN0 ::=		SEQUENCE {
	removedInterFreqCellList			RemovedInterFreqCellList			OPTIONAL,
	newInterFreqCellList				NewInterFreqCellSI-List-HCS-ECN0	OPTIONAL
}

InterFreqCellInfoSI-List-RSCP-LCR ::=		SEQUENCE {
	removedInterFreqCellList			RemovedInterFreqCellList			OPTIONAL,
	newInterFreqCellList				NewInterFreqCellSI-List-RSCP-LCR-r4		OPTIONAL
}

InterFreqCellInfoSI-List-ECN0-LCR ::=		SEQUENCE {
	removedInterFreqCellList			RemovedInterFreqCellList			OPTIONAL,
	newInterFreqCellList				NewInterFreqCellSI-List-ECN0-LCR-r4		OPTIONAL
}

InterFreqCellInfoSI-List-HCS-RSCP-LCR ::=		SEQUENCE {
	removedInterFreqCellList			RemovedInterFreqCellList			OPTIONAL,
	newInterFreqCellList				NewInterFreqCellSI-List-HCS-RSCP-LCR-r4	OPTIONAL
}
InterFreqCellInfoSI-List-HCS-ECN0-LCR ::=		SEQUENCE {
	removedInterFreqCellList			RemovedInterFreqCellList			OPTIONAL,
	newInterFreqCellList				NewInterFreqCellSI-List-HCS-ECN0-LCR-r4	OPTIONAL
}

InterFreqCellList ::=				SEQUENCE (SIZE (1..maxFreq)) OF
										InterFreqCell

InterFreqCellList-LCR-r4-ext ::=	SEQUENCE (SIZE (1..maxFreq)) OF
										InterFreqCell-LCR-r4

InterFreqCellMeasuredResultsList ::= SEQUENCE (SIZE (1..maxCellMeas)) OF
										CellMeasuredResults

InterFreqCellMeasuredResultsList-v920ext ::= SEQUENCE (SIZE (1..maxCellMeas)) OF
												CellMeasuredResults-v920ext

InterFreqCellMeasuredResultsList-vc50ext ::= SEQUENCE (SIZE (1..maxCellMeas)) OF
												CellMeasuredResults-vc50ext

InterFreqEvent ::=					CHOICE {
	event2a								Event2a,
	event2b								Event2b,
	event2c								Event2c,
	event2d								Event2d,
	event2e								Event2e,
	event2f								Event2f
}

InterFreqEvent-r6 ::=				CHOICE {
	event2a								Event2a-r6,
	event2b								Event2b-r6,
	event2c								Event2c-r6,
	event2d								Event2d-r6,
	event2e								Event2e-r6,
	event2f								Event2f-r6
}

InterFreqEvent-r10 ::=				CHOICE {
	event2a								Event2a-r10,
	event2b								Event2b-r10,
	event2c								Event2c-r10,
	event2d								Event2d-r10,
	event2e								Event2e-r10,
	event2f								Event2f-r10
}

InterFreqEvent-r11 ::=				CHOICE {
	event2a								Event2a-r11,
	event2b								Event2b-r11,
	event2c								Event2c-r11,
	event2d								Event2d-r10,
	event2e								Event2e-r11,
	event2f								Event2f-r10
}

InterFreqEvent-r12 ::=				CHOICE {
	event2a								Event2a-r11,
	event2b								Event2b-r11,
	event2c								Event2c-r11,
	event2d								Event2d-r10,
	event2e								Event2e-r11,
	event2f								Event2f-r10,
	event2g								Event2g
}

InterFreqEventList ::=				SEQUENCE (SIZE (1..maxMeasEvent)) OF
										InterFreqEvent

InterFreqEventList-r6 ::=			SEQUENCE (SIZE (1..maxMeasEvent)) OF
										InterFreqEvent-r6

InterFreqEventList-r10 ::=			SEQUENCE (SIZE (1..maxMeasEvent)) OF
										InterFreqEvent-r10

InterFreqEventList-r11 ::=			SEQUENCE (SIZE (1..maxMeasEvent)) OF
										InterFreqEvent-r11


InterFreqEventList-r12 ::=			SEQUENCE (SIZE (1..maxMeasEvent)) OF
										InterFreqEvent-r12

--Following IE shall be used regardless of CPICH RSCP(FDD) or Primary CCPCH RSCP(TDD)
--The order of the list corresponds to the order of the cells in InterFrequencyMeasuredResultsList
--The IE is only used for measured results and not for additional measured results.
InterFrequencyMeasuredResultsList-v590ext ::= SEQUENCE (SIZE (1..maxCellMeas)) OF
												DeltaRSCPPerCell

Inter-FreqEventCriteria-v590ext ::= SEQUENCE {
	threholdUsedFrequency-delta				DeltaRSCP,
	threholdNonUsedFrequency-deltaList		ThreholdNonUsedFrequency-deltaList  	OPTIONAL
}

--The order of the list corresponds to the order of the events in Inter-FreqEventList
Inter-FreqEventCriteriaList-v590ext ::= SEQUENCE (SIZE (1..maxMeasEvent)) OF
											Inter-FreqEventCriteria-v590ext

--The order of the list corresponds to the order of relevant events in Intra-FreqEventCriteriaList
--i.e. the first element of the list corresponds to the first occurance of event 1e, 1f, 1h, 1i,
--the second element of the list corresponds to the second occurance of event 1e, 1f, 1h, 1i
Intra-FreqEventCriteriaList-v590ext ::= SEQUENCE (SIZE (1..maxMeasEvent)) OF
											DeltaRSCP

--Following IE shall be used regardless of CPICH RSCP(FDD) or Primary CCPCH RSCP(TDD)
--The order of the list corresponds to the order of the cells in IntraFrequencyMeasuredResultsList
--The IE is only used for measured results and not for additional measured results.
IntraFrequencyMeasuredResultsList-v590ext ::= SEQUENCE (SIZE (1..maxCellMeas)) OF
												DeltaRSCPPerCell


InterFreqEventResults ::=			SEQUENCE {
	eventID								EventIDInterFreq,
	interFreqCellList					InterFreqCellList					OPTIONAL
}

InterFreqEventResults-va40ext ::=	SEQUENCE {
	detectedSetTrigger					ENUMERATED {true}			OPTIONAL
}

InterFreqEventResults-LCR-r4-ext ::=	SEQUENCE {
	eventID								EventIDInterFreq,
	interFreqCellList					InterFreqCellList-LCR-r4-ext		OPTIONAL
}

InterFreqMeasQuantity ::=			SEQUENCE {
	reportingCriteria					CHOICE {
		intraFreqReportingCriteria			SEQUENCE {
			intraFreqMeasQuantity				IntraFreqMeasQuantity
		},
		interFreqReportingCriteria			SEQUENCE {
			filterCoefficient					FilterCoefficient			DEFAULT fc0,
			modeSpecificInfo					CHOICE {
				fdd									SEQUENCE {
					freqQualityEstimateQuantity-FDD		FreqQualityEstimateQuantity-FDD
				},
				tdd									SEQUENCE {
					freqQualityEstimateQuantity-TDD		FreqQualityEstimateQuantity-TDD
				}
			}
		}
	}
}

InterFreqMeasuredResults ::=		SEQUENCE {
	frequencyInfo						FrequencyInfo						OPTIONAL,
	utra-CarrierRSSI					UTRA-CarrierRSSI					OPTIONAL,
	interFreqCellMeasuredResultsList	InterFreqCellMeasuredResultsList	OPTIONAL
}

InterFreqMeasuredResults-v920ext ::=	SEQUENCE {
	interFreqCellMeasuredResultsList		InterFreqCellMeasuredResultsList-v920ext	OPTIONAL
}
InterFreqMeasuredResults-vc50ext ::=	SEQUENCE {
	interFreqCellMeasuredResultsList		InterFreqCellMeasuredResultsList-vc50ext	OPTIONAL
}

InterFreqMeasuredResultsList ::=	SEQUENCE (SIZE (1..maxFreq)) OF
										InterFreqMeasuredResults

InterFreqMeasuredResultsList-v920ext ::= SEQUENCE (SIZE (1..maxFreq)) OF
												InterFreqMeasuredResults-v920ext

InterFreqMeasuredResultsList-vc50ext ::= SEQUENCE (SIZE (1..maxFreq)) OF
												InterFreqMeasuredResults-vc50ext

InterFreqMeasurementSysInfo-RSCP ::=	SEQUENCE {
	interFreqCellInfoSI-List				InterFreqCellInfoSI-List-RSCP		OPTIONAL
}

InterFreqMeasurementSysInfo-ECN0 ::=		SEQUENCE {
	interFreqCellInfoSI-List			InterFreqCellInfoSI-List-ECN0		OPTIONAL
}

InterFreqMeasurementSysInfo-HCS-RSCP ::=		SEQUENCE {
	interFreqCellInfoSI-List			InterFreqCellInfoSI-List-HCS-RSCP	OPTIONAL
}

InterFreqMeasurementSysInfo-HCS-ECN0 ::=		SEQUENCE {
	interFreqCellInfoSI-List			InterFreqCellInfoSI-List-HCS-ECN0	OPTIONAL
}

InterFreqMeasurementSysInfo-RSCP-LCR-r4 ::=	SEQUENCE {
	interFreqCellInfoSI-List				InterFreqCellInfoSI-List-RSCP-LCR		OPTIONAL
}

InterFreqMeasurementSysInfo-ECN0-LCR-r4 ::=		SEQUENCE {
	interFreqCellInfoSI-List			InterFreqCellInfoSI-List-ECN0-LCR		OPTIONAL
}

InterFreqMeasurementSysInfo-HCS-RSCP-LCR-r4 ::=		SEQUENCE {
	interFreqCellInfoSI-List			InterFreqCellInfoSI-List-HCS-RSCP-LCR	OPTIONAL
}

InterFreqMeasurementSysInfo-HCS-ECN0-LCR-r4 ::=		SEQUENCE {
	interFreqCellInfoSI-List			InterFreqCellInfoSI-List-HCS-ECN0-LCR	OPTIONAL
}

InterFreqRACHRepCellsList ::=			SEQUENCE (SIZE (1..maxFreq)) OF
InterFreqCellID

InterFreqRACHRepCellsList-r12 ::=			SEQUENCE (SIZE (1..maxFreq)) OF
InterFreqCellID-r12

Dummy-InterFreqRACHReportingInfo ::= SEQUENCE {
	modeSpecificInfo					CHOICE {
		fdd									SEQUENCE {
			interFreqRepQuantityRACH-FDD		InterFreqRepQuantityRACH-FDD
		},
		tdd									SEQUENCE {
			interFreqRepQuantityRACH-TDDList	InterFreqRepQuantityRACH-TDDList
		},
	interFreqRACHReportingThreshold		Threshold,
	maxReportedCellsOnRACHinterFreq		MaxReportedCellsOnRACHinterFreq
	}
}

InterFreqRACHReportingInfo ::= SEQUENCE {
	modeSpecificInfo					CHOICE {
		fdd									SEQUENCE {
			interFreqRepQuantityRACH-FDD		InterFreqRepQuantityRACH-FDD
		},
		tdd									SEQUENCE {
			interFreqRepQuantityRACH-TDDList	InterFreqRepQuantityRACH-TDDList
		}
	},
	interFreqRACHReportingThreshold		Threshold,
	maxReportedCellsOnRACHinterFreq		MaxReportedCellsOnRACHinterFreq
}

InterFreqExclude-listedCellsList-r12 ::=		SEQUENCE (SIZE (1..maxFreq)) OF
													InterFreqExclude-listedCells-r12

InterFreqExclude-listedCells-r12 ::=		SEQUENCE {
	frequencyInfo						FrequencyInfo,
	excludedCellInfoList				CellInfoListToBeExcluded
}

InterFreqReportCriteria ::=			CHOICE {
	intraFreqReportingCriteria			IntraFreqReportingCriteria,
	interFreqReportingCriteria			InterFreqReportingCriteria,
	periodicalReportingCriteria			PeriodicalWithReportingCellStatus,
	noReporting							ReportingCellStatusOpt
}

InterFreqReportCriteria-r4 ::=		CHOICE {
	intraFreqReportingCriteria			IntraFreqReportingCriteria-r4,
	interFreqReportingCriteria			InterFreqReportingCriteria,
	periodicalReportingCriteria			PeriodicalWithReportingCellStatus,
	noReporting							ReportingCellStatusOpt
}

InterFreqReportCriteria-r6 ::=		CHOICE {
	intraFreqReportingCriteria			IntraFreqReportingCriteria-r6,
	interFreqReportingCriteria			InterFreqReportingCriteria-r6,
	periodicalReportingCriteria			PeriodicalWithReportingCellStatus,
	noReporting							ReportingCellStatusOpt
}

InterFreqReportCriteria-r7 ::=		CHOICE {
	intraFreqReportingCriteria			IntraFreqReportingCriteria-r7,
	interFreqReportingCriteria			InterFreqReportingCriteria-r6,
	periodicalReportingCriteria			PeriodicalWithReportingCellStatus,
	noReporting							ReportingCellStatusOpt
}

InterFreqReportCriteria-r9 ::=		CHOICE {
	intraFreqReportingCriteria			IntraFreqReportingCriteria-r9,
	interFreqReportingCriteria			InterFreqReportingCriteria-r6,
	periodicalReportingCriteria			PeriodicalWithReportingCellStatus,
	noReporting							ReportingCellStatusOpt
}

InterFreqReportCriteria-r10 ::=		CHOICE {
	intraFreqReportingCriteria			IntraFreqReportingCriteria-r9,
	interFreqReportingCriteria			InterFreqReportingCriteria-r10,
	periodicalReportingCriteria			PeriodicalWithReportingCellStatus-r10,
	noReporting							ReportingCellStatusOpt-r10
}

InterFreqReportCriteria-r11 ::=		CHOICE {
	intraFreqReportingCriteria			IntraFreqReportingCriteria-r11,
	interFreqReportingCriteria			InterFreqReportingCriteria-r11,
	periodicalReportingCriteria			PeriodicalWithReportingCellStatus-r10,
	noReporting							ReportingCellStatusOpt-r10
}


InterFreqReportCriteria-r12 ::=		CHOICE {
	intraFreqReportingCriteria			IntraFreqReportingCriteria-r11,
	interFreqReportingCriteria			InterFreqReportingCriteria-r12,
	periodicalReportingCriteria			PeriodicalWithReportingCellStatus-r10,
	noReporting							ReportingCellStatusOpt-r10
}

InterFreqReportingCriteria ::=		SEQUENCE {
	interFreqEventList					InterFreqEventList					OPTIONAL
}

InterFreqReportingCriteria-r6 ::=	SEQUENCE {
	interFreqEventList					InterFreqEventList-r6				OPTIONAL
}

InterFreqReportingCriteria-r10 ::=	SEQUENCE {
	interFreqEventList					InterFreqEventList-r10			OPTIONAL
}

InterFreqReportingCriteria-r11 ::=	SEQUENCE {
	interFreqEventList					InterFreqEventList-r11			OPTIONAL
}

InterFreqReportingCriteria-r12 ::=	SEQUENCE {
	interFreqEventList					InterFreqEventList-r12			OPTIONAL,
	interFreqExclude-listedCellsList		InterFreqExclude-listedCellsList-r12	OPTIONAL
}

InterFreqReportingQuantity ::=		SEQUENCE {
	utra-Carrier-RSSI					BOOLEAN,
	frequencyQualityEstimate			BOOLEAN,
	nonFreqRelatedQuantities			CellReportingQuantities
}

InterFreqRepQuantityRACH-FDD ::=	ENUMERATED {
										cpich-EcN0, cpich-RSCP }

-- dummy is not used in this version of the specification, it should
-- not be sent and if received the UE behaviour is not specified.
InterFreqRepQuantityRACH-TDD ::=	ENUMERATED {
										dummy,
										primaryCCPCH-RSCP }

InterFreqRepQuantityRACH-TDDList ::= SEQUENCE (SIZE (1..2)) OF
										InterFreqRepQuantityRACH-TDD

InterFrequencyMeasurement ::=		SEQUENCE {
	interFreqCellInfoList				InterFreqCellInfoList,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	reportCriteria						InterFreqReportCriteria
}


InterFrequencyMeasurement-r4 ::=	SEQUENCE {
	interFreqCellInfoList				InterFreqCellInfoList-r4,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	reportCriteria						InterFreqReportCriteria-r4
}

InterFrequencyMeasurement-r6 ::=	SEQUENCE {
	interFreqCellInfoList				InterFreqCellInfoList-r4,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	reportCriteria						InterFreqReportCriteria-r6
}

InterFrequencyMeasurement-r7 ::=	SEQUENCE {
	interFreqCellInfoList				InterFreqCellInfoList-r4,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	reportCriteria						InterFreqReportCriteria-r7
}

InterFrequencyMeasurement-r8 ::=	SEQUENCE {
	interFreqCellInfoList				InterFreqCellInfoList-r8,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	adjacentFrequencyIndex				INTEGER (0..31)						OPTIONAL,
	reportCriteria						InterFreqReportCriteria-r7
}

InterFrequencyMeasurement-r9 ::=	SEQUENCE {
	interFreqCellInfoList				InterFreqCellInfoList-r9,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	adjacentFrequencyIndex				INTEGER (0..31)						OPTIONAL,
	interBandFrequencyIndex				INTEGER (0..31)						OPTIONAL,
	reportCriteria						InterFreqReportCriteria-r9
}

InterFrequencyMeasurement-r10 ::=	SEQUENCE {
	interFreqCellInfoList				InterFreqCellInfoList-r10,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	adjacentFrequencyIndex				INTEGER (0..31)						OPTIONAL,
	interBandFrequencyIndex				INTEGER (0..31)						OPTIONAL,
	freqIndexListForEnhancedMeas		FreqIndexListForEnhancedMeas		OPTIONAL,
	reportCriteria						InterFreqReportCriteria-r10
}

InterFrequencyMeasurement-r11 ::=	SEQUENCE {
	interFreqCellInfoList				InterFreqCellInfoList-r10,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	adjacentFrequencyIndex				INTEGER (0..31)						OPTIONAL,
	interBandFrequencyIndex				INTEGER (0..31)						OPTIONAL,
	freqIndexListForEnhancedMeas		FreqIndexListForEnhancedMeas		OPTIONAL,
	reportCriteria						InterFreqReportCriteria-r11
}


InterFrequencyMeasurement-r12 ::=	SEQUENCE {
	interFreqCellInfoList				InterFreqCellInfoList-r12,
	interFreqMeasQuantity				InterFreqMeasQuantity				OPTIONAL,
	interFreqReportingQuantity			InterFreqReportingQuantity			OPTIONAL,
	measurementValidity					MeasurementValidity					OPTIONAL,
	interFreqSetUpdate					UE-AutonomousUpdateMode				OPTIONAL,
	adjacentFrequencyIndex				INTEGER (0..79)						OPTIONAL,
	interBandFrequencyIndex				INTEGER (0..79)						OPTIONAL,
	freqIndexListForEnhancedMeas		FreqIndexListForEnhancedMeas-r12	OPTIONAL,
	reportCriteria						InterFreqReportCriteria-r12
}

InterRAT-TargetCellDescription ::=	SEQUENCE {
	technologySpecificInfo				CHOICE {
		gsm									SEQUENCE {
			bsic								BSIC,
			frequency-band						Frequency-Band,
			bcch-ARFCN							BCCH-ARFCN,
			ncMode								NC-Mode				OPTIONAL
		},
		is-2000								NULL,
		spare2								NULL,
		spare1								NULL
	}
}

InterRATCellID ::=				INTEGER (0..maxCellMeas-1)

InterRATCellInfoIndication ::=		INTEGER (0..3)

InterRATCellInfoList ::=			SEQUENCE {
	removedInterRATCellList			RemovedInterRATCellList,
	-- NOTE: Future revisions of dedicated messages including IE newInterRATCellList
	-- should use a corrected version of this IE
	newInterRATCellList				NewInterRATCellList,
	cellsForInterRATMeasList			CellsForInterRATMeasList			OPTIONAL
}

InterRATCellInfoList-B ::=			SEQUENCE {
	removedInterRATCellList			RemovedInterRATCellList,
	-- NOTE: IE newInterRATCellList should be optional.  However, system information
	-- does not support message versions.  Hence, this can not be corrected
	newInterRATCellList				NewInterRATCellList-B
}

InterRATCellInfoList-r4 ::=			SEQUENCE {
	removedInterRATCellList					RemovedInterRATCellList,
	newInterRATCellList						NewInterRATCellList					OPTIONAL,
	cellsForInterRATMeasList				CellsForInterRATMeasList			OPTIONAL
}

InterRATCellInfoList-r6 ::=			SEQUENCE {
	removedInterRATCellList					RemovedInterRATCellList,
	newInterRATCellList						NewInterRATCellList					OPTIONAL,
	cellsForInterRATMeasList				CellsForInterRATMeasList			OPTIONAL,
	interRATCellInfoIndication-r6			InterRATCellInfoIndication			OPTIONAL
}

InterRATCellIndividualOffset ::=			INTEGER (-50..50)

InterRATEvent ::=				CHOICE {
	event3a								Event3a,
	event3b								Event3b,
	event3c								Event3c,
	event3d								Event3d
}

InterRATEvent-r12 ::=				CHOICE {
	event3a								Event3a-r12,
	event3b								Event3b-r12,
	event3c								Event3c-r12,
	event3d								Event3d
}

InterRATEventList ::=			SEQUENCE (SIZE (1..maxMeasEvent)) OF
										InterRATEvent

InterRATEventList-r12 ::=			SEQUENCE (SIZE (1..maxMeasEvent)) OF
										InterRATEvent-r12

InterRATEventResults ::=			SEQUENCE {
	eventID								EventIDInterRAT,
	cellToReportList					CellToReportList
}

InterRATInfo ::=					ENUMERATED {
										gsm }

InterRATInfo-r6 ::=					SEQUENCE {
	rat									InterRATInfo,
	gsm-TargetCellInfoList				GSM-TargetCellInfoList			OPTIONAL
}

InterRATInfo-v860ext ::=			CHOICE {
	-- CHOICE gsm is provided in IE InterRATInfo or IE InterRATInfo-r6
	gsm									NULL,
	eutra								SEQUENCE {
		eutra-TargetFreqInfoList			EUTRA-TargetFreqInfoList
	}
}

InterRATMeasQuantity ::=				SEQUENCE {
	measQuantityUTRAN-QualityEstimate		IntraFreqMeasQuantity			OPTIONAL,
	ratSpecificInfo						CHOICE {
		gsm										SEQUENCE {
			measurementQuantity						MeasurementQuantityGSM,
			filterCoefficient						FilterCoefficient		DEFAULT fc0,
			bsic-VerificationRequired				BSIC-VerificationRequired
		},
		is-2000									SEQUENCE {
			tadd-EcIo								INTEGER (0..63),
			tcomp-EcIo								INTEGER (0..15),
			softSlope								INTEGER (0..63)			OPTIONAL,
			addIntercept							INTEGER (0..63)			OPTIONAL
		}
	}
}

InterRATMeasQuantity-r8 ::=				SEQUENCE {
	measQuantityUTRAN-QualityEstimate		IntraFreqMeasQuantity			OPTIONAL,
	ratSpecificInfo							CHOICE {
		gsm										SEQUENCE {
			measurementQuantity						MeasurementQuantityGSM,
			filterCoefficient						FilterCoefficient		DEFAULT fc0,
			bsic-VerificationRequired				BSIC-VerificationRequired
		},
		is-2000									SEQUENCE {
			tadd-EcIo								INTEGER (0..63),
			tcomp-EcIo								INTEGER (0..15),
			softSlope								INTEGER (0..63)			OPTIONAL,
			addIntercept							INTEGER (0..63)			OPTIONAL
		},
		e-UTRA									SEQUENCE {
			measurementQuantity						MeasurementQuantityEUTRA,
			filterCoefficient						FilterCoefficient		DEFAULT fc0
		}
	}
}

InterRATMeasuredResults ::=		CHOICE {
	gsm									GSM-MeasuredResultsList,
	spare								NULL
}

InterRATMeasuredResultsList ::= SEQUENCE (SIZE (1..maxOtherRAT-16)) OF
										InterRATMeasuredResults

InterRATMeasurement ::=			SEQUENCE {
	interRATCellInfoList				InterRATCellInfoList				OPTIONAL,
	interRATMeasQuantity				InterRATMeasQuantity				OPTIONAL,
	interRATReportingQuantity			InterRATReportingQuantity		OPTIONAL,
	reportCriteria						InterRATReportCriteria
}

InterRATMeasurement-r4 ::=			SEQUENCE {
	interRATCellInfoList				InterRATCellInfoList-r4				OPTIONAL,
	interRATMeasQuantity				InterRATMeasQuantity				OPTIONAL,
	interRATReportingQuantity			InterRATReportingQuantity		OPTIONAL,
	reportCriteria						InterRATReportCriteria
}

InterRATMeasurement-r6 ::=			SEQUENCE {
	interRATCellInfoList				InterRATCellInfoList-r6				OPTIONAL,
	interRATMeasQuantity				InterRATMeasQuantity				OPTIONAL,
	interRATReportingQuantity			InterRATReportingQuantity		OPTIONAL,
	reportCriteria						InterRATReportCriteria
}

InterRATMeasurement-r8 ::=			SEQUENCE {
	interRATMeasurementObjects			CHOICE {
		interRATCellInfoList				InterRATCellInfoList-r6,
		eutra-FrequencyList					EUTRA-FrequencyList
	}		OPTIONAL,
	interRATMeasQuantity				InterRATMeasQuantity-r8				OPTIONAL,
	interRATReportingQuantity			InterRATReportingQuantity-r8		OPTIONAL,
	reportCriteria						InterRATReportCriteria,
	idleIntervalInfo					IdleIntervalInfo					OPTIONAL
}

InterRATMeasurement-r9 ::=			SEQUENCE {
	interRATMeasurementObjects			CHOICE {
		interRATCellInfoList				InterRATCellInfoList-r6,
		eutra-FrequencyList					EUTRA-FrequencyList-r9
	}		OPTIONAL,
	interRATMeasQuantity				InterRATMeasQuantity-r8				OPTIONAL,
	interRATReportingQuantity			InterRATReportingQuantity-r8		OPTIONAL,
	reportCriteria						InterRATReportCriteria,
	idleIntervalInfo					IdleIntervalInfo					OPTIONAL
}

InterRATMeasurement-r11 ::=			SEQUENCE {
	interRATMeasurementObjects			CHOICE {
		interRATCellInfoList				InterRATCellInfoList-r6,
		eutra-FrequencyList					EUTRA-FrequencyList-r11
	}		OPTIONAL,
	interRATMeasQuantity				InterRATMeasQuantity-r8				OPTIONAL,
	interRATReportingQuantity			InterRATReportingQuantity-r8		OPTIONAL,
	reportCriteria						InterRATReportCriteria,
	idleIntervalInfo					IdleIntervalInfo					OPTIONAL
}

InterRATMeasurement-r12 ::=			SEQUENCE {
	interRATMeasurementObjects			CHOICE {
		interRATCellInfoList				InterRATCellInfoList-r6,
		eutra-FrequencyList					EUTRA-FrequencyList-r12
	}		OPTIONAL,
	interRATMeasQuantity				InterRATMeasQuantity-r8				OPTIONAL,
	interRATReportingQuantity			InterRATReportingQuantity-r8		OPTIONAL,
	reportCriteria						InterRATReportCriteria-r12,
	idleIntervalInfo					IdleIntervalInfo					OPTIONAL
}


InterRATMeasurementSysInfo ::=	SEQUENCE {
	interRATCellInfoList				InterRATCellInfoList				OPTIONAL
}

InterRATMeasurementSysInfo-B ::=	SEQUENCE {
	interRATCellInfoList				InterRATCellInfoList-B			OPTIONAL
}

InterRATReportCriteria ::=		CHOICE {
	interRATReportingCriteria			InterRATReportingCriteria,
	periodicalReportingCriteria			PeriodicalWithReportingCellStatus,
	noReporting							ReportingCellStatusOpt
}

InterRATReportCriteria-r12 ::=		CHOICE {
	interRATReportingCriteria			InterRATReportingCriteria-r12,
	periodicalReportingCriteria			PeriodicalWithReportingCellStatus,
	noReporting							ReportingCellStatusOpt
}

InterRATReportingCriteria ::= 	SEQUENCE {
	interRATEventList				InterRATEventList				OPTIONAL
}

InterRATReportingCriteria-r12 ::= 	SEQUENCE {
	interRATEventList				InterRATEventList-r12				OPTIONAL
}

InterRATReportingQuantity ::=	SEQUENCE {
	utran-EstimatedQuality				BOOLEAN,
	ratSpecificInfo					CHOICE {
		gsm									SEQUENCE {
			-- dummy and dummy2 are not used in this version of the specification
			-- and when received they should be ignored.
			dummy								BOOLEAN,
			dummy2								BOOLEAN,
			gsm-Carrier-RSSI					BOOLEAN
		}
	}
}

InterRATReportingQuantity-r8 ::=	SEQUENCE {
	utran-EstimatedQuality				BOOLEAN,
	ratSpecificInfo						CHOICE {
		gsm									SEQUENCE {
			gsm-Carrier-RSSI					BOOLEAN
		},
		eutra								SEQUENCE {
			reportingQuantity					ENUMERATED { measurementQuantity,
													both }
		}
	}
}

IntraFreqCellID ::=					INTEGER (0..maxCellMeas-1)

IntraFreqCellIDOnSecULFreq ::=		INTEGER (0..maxCellMeasOnSecULFreq-1)

IntraFreqCellInfoList ::=			SEQUENCE {
	removedIntraFreqCellList			RemovedIntraFreqCellList			OPTIONAL,
	newIntraFreqCellList				NewIntraFreqCellList				OPTIONAL,
	cellsForIntraFreqMeasList			CellsForIntraFreqMeasList			OPTIONAL
}

IntraFreqCellInfoList-r4 ::=		SEQUENCE {
	removedIntraFreqCellList			RemovedIntraFreqCellList			OPTIONAL,
	newIntraFreqCellList				NewIntraFreqCellList-r4				OPTIONAL,
	cellsForIntraFreqMeasList			CellsForIntraFreqMeasList			OPTIONAL
}

IntraFreqCellInfoListInfoOnSecULFreq ::=		SEQUENCE {
	removedIntraFreqCellList			RemovedIntraFreqCellListOnSecULFreq			OPTIONAL,
	newIntraFreqCellList				NewIntraFreqCellListOnSecULFreq				OPTIONAL,
	cellsForIntraFreqMeasList			CellsForIntraFreqMeasListOnSecULFreq		OPTIONAL
}

IntraFreqCellInfoListOnSecULFreq ::=		SEQUENCE {
	intraFreqCellInfoListOnSecULFreq		IntraFreqCellInfoListInfoOnSecULFreq
}

IntraFreqCellInfoList-r9 ::=		SEQUENCE {
	removedIntraFreqCellList			RemovedIntraFreqCellList			OPTIONAL,
	newIntraFreqCellList				NewIntraFreqCellList-r9				OPTIONAL,
	cellsForIntraFreqMeasList			CellsForIntraFreqMeasList			OPTIONAL,
	cSGIntraFreqCellInfoList			CSGIntraFreqCellInfoList			OPTIONAL,
	intraFreqSIAcquisition				IntraFreqSIAcquisition				OPTIONAL

}

IntraFreqCellInfoList-r10 ::=		SEQUENCE {
	removedIntraFreqCellList			RemovedIntraFreqCellList			OPTIONAL,
	newIntraFreqCellList				NewIntraFreqCellList-r10			OPTIONAL,
	cellsForIntraFreqMeasList			CellsForIntraFreqMeasList			OPTIONAL,
	cSGIntraFreqCellInfoList			CSGIntraFreqCellInfoList			OPTIONAL,
	intraFreqSIAcquisition				IntraFreqSIAcquisition				OPTIONAL
}

IntraFreqSIAcquisitionInfo::=		SEQUENCE (SIZE (1..maxSIrequest)) OF
										PrimaryCPICH-Info

IntraFreqSIAcquisition ::=			SEQUENCE {
	modeSpecificInfo					CHOICE {
		fdd									SEQUENCE {
			intraFreqSIAcquisitionInfo		IntraFreqSIAcquisitionInfo		OPTIONAL
		},
		tdd								NULL
	}
}

IntraFreqCellInfoSI-List-RSCP ::=	SEQUENCE {
	removedIntraFreqCellList			RemovedIntraFreqCellList			OPTIONAL,
	newIntraFreqCellList				NewIntraFreqCellSI-List-RSCP
}

IntraFreqCellInfoSI-List-ECN0 ::=		SEQUENCE {
	removedIntraFreqCellList			RemovedIntraFreqCellList			OPTIONAL,
	newIntraFreqCellList				NewIntraFreqCellSI-List-ECN0
}

IntraFreqCellInfoSI-List-HCS-RSCP ::=		SEQUENCE {
	removedIntraFreqCellList			RemovedIntraFreqCellList			OPTIONAL,
	newIntraFreqCellList				NewIntraFreqCellSI-List-HCS-RSCP
}

IntraFreqCellInfoSI-List-HCS-ECN0 ::=		SEQUENCE {
	removedIntraFreqCellList			RemovedIntraFreqCellList			OPTIONAL,
	newIntraFreqCellList				NewIntraFreqCellSI-List-HCS-ECN0
}

IntraFreqCellInfoSI-List-RSCP-LCR-r4 ::=	SEQUENCE {
	removedIntraFreqCellList			RemovedIntraFreqCellList			OPTIONAL,
	newIntraFreqCellList				NewIntraFreqCellSI-List-RSCP-LCR-r4
}

IntraFreqCellInfoSI-List-ECN0-LCR-r4 ::=		SEQUENCE {
	removedIntraFreqCellList			RemovedIntraFreqCellList			OPTIONAL,
	newIntraFreqCellList				NewIntraFreqCellSI-List-ECN0-LCR-r4
}

IntraFreqCellInfoSI-List-HCS-RSCP-LCR-r4 ::=		SEQUENCE {
	removedIntraFreqCellList			RemovedIntraFreqCellList			OPTIONAL,
	newIntraFreqCellList				NewIntraFreqCellSI-List-HCS-RSCP-LCR-r4
}

IntraFreqCellInfoSI-List-HCS-ECN0-LCR-r4 ::=		SEQUENCE {
	removedIntraFreqCellList			RemovedIntraFreqCellList			OPTIONAL,
	newIntraFreqCellList				NewIntraFreqCellSI-List-HCS-ECN0-LCR-r4
}

IntraFreqEvent ::=					CHOICE {
	e1a									Event1a,
	e1b									Event1b,
	e1c									Event1c,
	e1d									NULL,
	e1e									Event1e,
	e1f									Event1f,
	e1g									NULL,
	e1h									ThresholdUsedFrequency,
	e1i									ThresholdUsedFrequency
}

IntraFreqEvent-r4 ::=				CHOICE {
	e1a									Event1a-r4,
	e1b									Event1b-r4,
	e1c									Event1c,
	e1d									NULL,
	e1e									Event1e,
	e1f									Event1f,
	e1g									NULL,
	e1h									ThresholdUsedFrequency,
	e1i									ThresholdUsedFrequency
}

IntraFreqEvent-LCR-r4 ::=			CHOICE {
	e1a									Event1a-LCR-r4,
	e1b									Event1b-LCR-r4,
	e1c									Event1c,
	e1d									NULL,
	e1e									Event1e,
	e1f									Event1f,
	e1g									NULL,
	e1h									ThresholdUsedFrequency,
	e1i									ThresholdUsedFrequency
}

IntraFreqEvent-r6 ::=				CHOICE {
	e1a									Event1a-r4,
	e1b									Event1b-r4,
	e1c									Event1c,
	e1d									Event1d,
	e1e									Event1e-r6,
	e1f									Event1f-r6,
	e1g									NULL,
	e1h									ThresholdUsedFrequency-r6,
	e1i									ThresholdUsedFrequency-r6,
	e1j									Event1j-r6
}

IntraFreqEvent-r7 ::=				CHOICE {
	e1a									Event1a-r4,
	e1b									Event1b-r7,
	e1c									Event1c,
	e1d									Event1d,
	e1e									Event1e-r6,
	e1f									Event1f-r6,
	e1g									NULL,
	e1h									ThresholdUsedFrequency-r6,
	e1i									ThresholdUsedFrequency-r6,
	e1j									Event1j-r6
}

IntraFreqEventOnSecULFreq ::=		CHOICE {
	e1a									Event1a-OnSecUlFreq-r9,
	e1b									Event1b-OnSecUlFreq-r9,
	e1c									Event1c,
	e1e									Event1e-r6,
	e1f									Event1f-r6
}

IntraFreqEvent-1d-r5 ::=		SEQUENCE {
	triggeringCondition					TriggeringCondition2	OPTIONAL,
	useCIO								BOOLEAN					OPTIONAL
}

IntraFreqEventCriteria ::=			SEQUENCE {
	event								IntraFreqEvent,
	hysteresis							Hysteresis,
	timeToTrigger						TimeToTrigger,
	reportingCellStatus					ReportingCellStatus					OPTIONAL
}

IntraFreqEventCriteria-r4 ::=		SEQUENCE {
	event								IntraFreqEvent-r4,
	hysteresis							Hysteresis,
	timeToTrigger						TimeToTrigger,
	reportingCellStatus					ReportingCellStatus					OPTIONAL
}

IntraFreqEventCriteria-LCR-r4 ::=	SEQUENCE {
	event								IntraFreqEvent-LCR-r4,
	hysteresis							Hysteresis,
	timeToTrigger						TimeToTrigger,
	reportingCellStatus					ReportingCellStatus					OPTIONAL
}

IntraFreqEventCriteria-r6 ::=	SEQUENCE {
	event								IntraFreqEvent-r6,
	hysteresis							Hysteresis,
	timeToTrigger						TimeToTrigger,
	reportingCellStatus					ReportingCellStatus					OPTIONAL
}

IntraFreqEventCriteria-r7 ::=	SEQUENCE {
	event								IntraFreqEvent-r7,
	hysteresis							Hysteresis,
	timeToTrigger						TimeToTrigger,
	reportingCellStatus					ReportingCellStatus					OPTIONAL
}

IntraFreqEventCriteriaOnSecULFreq ::=	SEQUENCE {
	event								IntraFreqEventOnSecULFreq,
	hysteresis							Hysteresis,
	timeToTrigger						TimeToTrigger,
	reportingCellStatus					ReportingCellStatus					OPTIONAL
}

IntraFreqEventCriteriaList ::=		SEQUENCE (SIZE (1..maxMeasEvent)) OF
										IntraFreqEventCriteria

IntraFreqEventCriteriaList-r4 ::=	SEQUENCE (SIZE (1..maxMeasEvent)) OF
										IntraFreqEventCriteria-r4

IntraFreqEventCriteriaList-LCR-r4 ::=	SEQUENCE (SIZE (1..maxMeasEvent)) OF
										IntraFreqEventCriteria-LCR-r4

IntraFreqEventCriteriaList-r6 ::=		SEQUENCE (SIZE (1..maxMeasEvent)) OF
										IntraFreqEventCriteria-r6

IntraFreqEventCriteriaList-r7 ::=		SEQUENCE (SIZE (1..maxMeasEvent)) OF
										IntraFreqEventCriteria-r7

IntraFreqEventCriteriaListOnSecULFreq ::= 		SEQUENCE{
	frequencyInfo						FrequencyInfo,
	intraFreqEventCriteria				SEQUENCE (SIZE (1..maxMeasEventOnSecULFreq)) OF
										IntraFreqEventCriteriaOnSecULFreq
}

IntraFreqEventResults ::=			SEQUENCE {
	eventID								EventIDIntraFreq,
	cellMeasurementEventResults			CellMeasurementEventResults
}

IntraFreqEventResultsOnSecUlFreq ::=			SEQUENCE {
	eventID										EventIDIntraFreq,
	cellMeasurementEventResultsOnSecUlFreq		CellMeasurementEventResultsOnSecUlFreq
}

IntraFreqMeasQuantity ::=			SEQUENCE {
	filterCoefficient					FilterCoefficient					DEFAULT fc0,
	modeSpecificInfo 					CHOICE {
		fdd								SEQUENCE {
			intraFreqMeasQuantity-FDD		IntraFreqMeasQuantity-FDD
		},
		tdd								SEQUENCE {
			intraFreqMeasQuantity-TDDList	IntraFreqMeasQuantity-TDDList
		}
	}
}

-- If IntraFreqMeasQuantity-FDD is used in InterRATMeasQuantity, then only
-- cpich-Ec-N0 and cpich-RSCP are allowed.
-- dummy is not used in this version of the specification, it should
-- not be sent and if received the UE behaviour is not specified.
IntraFreqMeasQuantity-FDD ::=		ENUMERATED {
										cpich-Ec-N0,
										cpich-RSCP,
										pathloss,
										dummy }

IntraFreqMeasQuantity-FDD-sib3 ::=	ENUMERATED {
										cpich-Ec-N0, cpich-RSCP }

-- dummy is not used in this version of the specification, it should
-- not be sent and if received the UE behaviour is not specified.
IntraFreqMeasQuantity-TDD ::=		ENUMERATED {
										primaryCCPCH-RSCP,
										pathloss,
										timeslotISCP,
										dummy }

IntraFreqMeasQuantity-TDDList ::=	SEQUENCE (SIZE (1..4)) OF
										IntraFreqMeasQuantity-TDD

IntraFreqMeasQuantity-TDD-sib3List ::= SEQUENCE (SIZE (1..2)) OF
										ENUMERATED { primaryCCPCH-RSCP, timeslotISCP }

IntraFreqMeasuredResultsList ::=	SEQUENCE (SIZE (1..maxCellMeas)) OF
										CellMeasuredResults

IntraFreqMeasuredResultsList-v920ext ::= SEQUENCE (SIZE (1..maxCellMeas)) OF
												CellMeasuredResults-v920ext

IntraFreqMeasuredResultsList-vc50ext ::= SEQUENCE (SIZE (1..maxCellMeas)) OF
												CellMeasuredResults-vc50ext

IntraFreqMeasurementSysInfo-RSCP ::=	SEQUENCE {
	intraFreqMeasurementID				MeasurementIdentity			DEFAULT 1,
	intraFreqCellInfoSI-List			IntraFreqCellInfoSI-List-RSCP		OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqMeasurementSysInfo-ECN0 ::=		SEQUENCE {
	intraFreqMeasurementID				MeasurementIdentity			DEFAULT 1,
	intraFreqCellInfoSI-List			IntraFreqCellInfoSI-List-ECN0		OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqMeasurementSysInfo-HCS-RSCP ::=	SEQUENCE {
	intraFreqMeasurementID				MeasurementIdentity			DEFAULT 1,
	intraFreqCellInfoSI-List			IntraFreqCellInfoSI-List-HCS-RSCP	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqMeasurementSysInfo-HCS-ECN0 ::=	SEQUENCE {
	intraFreqMeasurementID				MeasurementIdentity			DEFAULT 1,
	intraFreqCellInfoSI-List			IntraFreqCellInfoSI-List-HCS-ECN0	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqMeasurementSysInfo-RSCP-LCR-r4 ::=	SEQUENCE {
	intraFreqMeasurementID				MeasurementIdentity			DEFAULT 1,
	intraFreqCellInfoSI-List			IntraFreqCellInfoSI-List-RSCP-LCR-r4	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH-LCR-r4		OPTIONAL
}

IntraFreqMeasurementSysInfo-ECN0-LCR-r4 ::=		SEQUENCE {
	intraFreqMeasurementID				MeasurementIdentity			DEFAULT 1,
	intraFreqCellInfoSI-List			IntraFreqCellInfoSI-List-ECN0-LCR-r4	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH-LCR-r4		OPTIONAL
}

IntraFreqMeasurementSysInfo-HCS-RSCP-LCR-r4 ::=	SEQUENCE {
	intraFreqMeasurementID				MeasurementIdentity			DEFAULT 1,
	intraFreqCellInfoSI-List			IntraFreqCellInfoSI-List-HCS-RSCP-LCR-r4	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH-LCR-r4		OPTIONAL
}

IntraFreqMeasurementSysInfo-HCS-ECN0-LCR-r4 ::=	SEQUENCE {
	intraFreqMeasurementID				MeasurementIdentity			DEFAULT 1,
	intraFreqCellInfoSI-List			IntraFreqCellInfoSI-List-HCS-ECN0-LCR-r4	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH-LCR-r4		OPTIONAL
}

IntraFreqReportCriteria ::=			CHOICE {
	intraFreqReportingCriteria			IntraFreqReportingCriteria,
	periodicalReportingCriteria			PeriodicalWithReportingCellStatus,
	noReporting							ReportingCellStatusOpt
}

IntraFreqReportCriteria-r4 ::=		CHOICE {
	intraFreqReportingCriteria			IntraFreqReportingCriteria-r4,
	periodicalReportingCriteria			PeriodicalWithReportingCellStatus,
	noReporting							ReportingCellStatusOpt
}

IntraFreqReportCriteria-r6 ::=		CHOICE {
	intraFreqReportingCriteria			IntraFreqReportingCriteria-r6,
	periodicalReportingCriteria			PeriodicalWithReportingCellStatus,
	noReporting							ReportingCellStatusOpt
}

IntraFreqReportCriteria-r7 ::=		CHOICE {
	intraFreqReportingCriteria			IntraFreqReportingCriteria-r7,
	periodicalReportingCriteria			PeriodicalWithReportingCellStatus,
	noReporting							ReportingCellStatusOpt
}

IntraFreqReportCriteria-r9 ::=		CHOICE {
	intraFreqReportingCriteria			IntraFreqReportingCriteria-r9,
	periodicalReportingCriteria			PeriodicalWithReportingCellStatus,
	noReporting							ReportingCellStatusOpt
}

IntraFreqReportCriteria-r11 ::=		CHOICE {
	intraFreqReportingCriteria			IntraFreqReportingCriteria-r11,
	periodicalReportingCriteria			PeriodicalWithReportingCellStatus,
	noReporting							ReportingCellStatusOpt
}

IntraFreqReportingCriteria ::=		SEQUENCE {
	eventCriteriaList					IntraFreqEventCriteriaList		OPTIONAL
}

IntraFreqReportingCriteria-r4 ::=	SEQUENCE {
	eventCriteriaList					IntraFreqEventCriteriaList-r4	OPTIONAL
}

IntraFreqReportingCriteria-LCR-r4 ::=	SEQUENCE {
	eventCriteriaList					IntraFreqEventCriteriaList-LCR-r4	OPTIONAL
}

IntraFreqReportingCriteria-r6 ::= SEQUENCE {
	eventCriteriaList					IntraFreqEventCriteriaList-r6	OPTIONAL
}

IntraFreqReportingCriteria-r7 ::= SEQUENCE {
	eventCriteriaList					IntraFreqEventCriteriaList-r7	OPTIONAL
}

IntraFreqReportingCriteria-r9 ::= SEQUENCE {
	eventCriteriaList					IntraFreqEventCriteriaList-r7			OPTIONAL,
	eventCriteriaListOnSecULFreq		IntraFreqEventCriteriaListOnSecULFreq	OPTIONAL
}

IntraFreqReportingCriteria-r11 ::= SEQUENCE {
	eventCriteriaList					IntraFreqEventCriteriaList-r7			OPTIONAL,
	eventCriteriaListOnSecULFreq		IntraFreqEventCriteriaListOnSecULFreq	OPTIONAL,
	excludedCellInfoList				CellInfoListToBeExcluded				OPTIONAL
}

IntraFreqReportingCriteria-1b-r5 ::= SEQUENCE {
	periodicReportingInfo-1b			PeriodicReportingInfo-1b
}

IntraFreqReportingQuantity ::=		SEQUENCE {
	activeSetReportingQuantities		CellReportingQuantities,
	monitoredSetReportingQuantities		CellReportingQuantities,
	detectedSetReportingQuantities		CellReportingQuantities				OPTIONAL
}

IntraFreqReportingQuantityForRACH ::= SEQUENCE {
	sfn-SFN-OTD-Type					SFN-SFN-OTD-Type,
	modeSpecificInfo					CHOICE {
		fdd									SEQUENCE {
			intraFreqRepQuantityRACH-FDD		IntraFreqRepQuantityRACH-FDD
		},
		tdd									SEQUENCE {
			intraFreqRepQuantityRACH-TDDList	IntraFreqRepQuantityRACH-TDDList
		}
	}
}

IntraFreqReportingQuantityForRACH-vc50ext ::= SEQUENCE {
	intraFreqRepQuantityRACH-FDD		ENUMERATED {
											cpich-EcN0-RSCP, spare1}
}

IntraFreqRepQuantityRACH-FDD ::=	ENUMERATED {
										cpich-EcN0, cpich-RSCP,
										pathloss, noReport }

IntraFreqRepQuantityRACH-TDD ::=	ENUMERATED {
										timeslotISCP,
										primaryCCPCH-RSCP,
										noReport }

IntraFreqRepQuantityRACH-TDDList ::= SEQUENCE (SIZE (1..2)) OF
										IntraFreqRepQuantityRACH-TDD

IntraFrequencyMeasurement ::=		SEQUENCE {
	intraFreqCellInfoList				IntraFreqCellInfoList				OPTIONAL,
	intraFreqMeasQuantity				IntraFreqMeasQuantity				OPTIONAL,
	intraFreqReportingQuantity			IntraFreqReportingQuantity			OPTIONAL,
	measurementValidity					MeasurementValidity					OPTIONAL,
	reportCriteria						IntraFreqReportCriteria				OPTIONAL
}

IntraFrequencyMeasurement-r4 ::=	SEQUENCE {
	intraFreqCellInfoList				IntraFreqCellInfoList-r4			OPTIONAL,
	intraFreqMeasQuantity				IntraFreqMeasQuantity				OPTIONAL,
	intraFreqReportingQuantity			IntraFreqReportingQuantity			OPTIONAL,
	measurementValidity					MeasurementValidity					OPTIONAL,
	reportCriteria						IntraFreqReportCriteria-r4			OPTIONAL
}

IntraFrequencyMeasurement-r6 ::=		SEQUENCE {
	intraFreqCellInfoList				IntraFreqCellInfoList-r4			OPTIONAL,
	intraFreqMeasQuantity				IntraFreqMeasQuantity				OPTIONAL,
	intraFreqReportingQuantity			IntraFreqReportingQuantity			OPTIONAL,
	measurementValidity					MeasurementValidity					OPTIONAL,
	-- reportCriteria is optional in later versions of this message
	reportCriteria						IntraFreqReportCriteria-r6
}

IntraFrequencyMeasurement-r7 ::=		SEQUENCE {
	intraFreqCellInfoList				IntraFreqCellInfoList-r4			OPTIONAL,
	intraFreqMeasQuantity				IntraFreqMeasQuantity				OPTIONAL,
	intraFreqReportingQuantity			IntraFreqReportingQuantity			OPTIONAL,
	measurementValidity					MeasurementValidity					OPTIONAL,
	reportCriteria						IntraFreqReportCriteria-r7			OPTIONAL
}

IntraFrequencyMeasurement-r9 ::=		SEQUENCE {
	intraFreqCellInfoList				IntraFreqCellInfoList-r9			OPTIONAL,
	intraFreqCellInfoListOnSecULFreq	IntraFreqCellInfoListOnSecULFreq	OPTIONAL,
	intraFreqMeasQuantity				IntraFreqMeasQuantity				OPTIONAL,
	intraFreqReportingQuantity			IntraFreqReportingQuantity			OPTIONAL,
	measurementValidity					MeasurementValidity					OPTIONAL,
	reportCriteria						IntraFreqReportCriteria-r9			OPTIONAL
}

IntraFrequencyMeasurement-r10 ::=		SEQUENCE {
	intraFreqCellInfoList				IntraFreqCellInfoList-r10			OPTIONAL,
	intraFreqCellInfoListOnSecULFreq	IntraFreqCellInfoListOnSecULFreq	OPTIONAL,
	intraFreqMeasQuantity				IntraFreqMeasQuantity				OPTIONAL,
	intraFreqReportingQuantity			IntraFreqReportingQuantity			OPTIONAL,
	measurementValidity					MeasurementValidity					OPTIONAL,
	reportCriteria						IntraFreqReportCriteria-r9			OPTIONAL
}

IntraFrequencyMeasurement-r11 ::=		SEQUENCE {
	intraFreqCellInfoList				IntraFreqCellInfoList-r10			OPTIONAL,
	intraFreqCellInfoListOnSecULFreq	IntraFreqCellInfoListOnSecULFreq	OPTIONAL,
	intraFreqMeasQuantity				IntraFreqMeasQuantity				OPTIONAL,
	intraFreqReportingQuantity			IntraFreqReportingQuantity			OPTIONAL,
	measurementValidity					MeasurementValidity					OPTIONAL,
	reportCriteria						IntraFreqReportCriteria-r11			OPTIONAL,
	periodicalReportingCriteriaOnSecULFreq
										PeriodicalWithReportingCellStatusOnSecULFreq	OPTIONAL
}

IntraFrequencyMeasuredResultsListOnSecULFreq ::= SEQUENCE (SIZE (1..maxCellMeasOnSecULFreq)) OF
												CellMeasuredResults-r9

IntraFrequencyMeasuredResultsListOnSecULFreq-vc50ext ::= SEQUENCE (SIZE (1..maxCellMeasOnSecULFreq))
															 OF	CellMeasuredResults-vc50ext

IntraUTRAANR ::= SEQUENCE {
	loggingAbsoluteThreshold			LoggingAbsoluteThreshold,
	loggingRelativeThreshold			LoggingRelativeThreshold			OPTIONAL
}

IODE ::=							INTEGER (0..255)

IP-Length ::=						ENUMERATED {
										ipl5, ipl10 }

IP-PCCPCH-r4 ::=					BOOLEAN

IP-Spacing ::=						ENUMERATED {
										e5, e7, e10, e15, e20,
										e30, e40, e50 }

IP-Spacing-TDD ::=						ENUMERATED {
										e30, e40, e50, e70, e100}

IS-2000SpecificMeasInfo ::=			ENUMERATED {
										frequency, timeslot, colourcode,
										outputpower, pn-Offset }

LoggedANRConfigurationInfo ::= SEQUENCE {
	loggingDuration						ENUMERATED { min10, min30, hr1, spare2, spare1 },
	intraUTRAANR						IntraUTRAANR					OPTIONAL,
	interRATANRforEUTRAIndicator		ENUMERATED { true }				OPTIONAL,
	interRATANRforGSMIndicator			ENUMERATED { true }				OPTIONAL
}

LoggedANRReportInfoList ::= SEQUENCE (SIZE (1..maxNumANRLoggedItems)) OF
								LoggedANRReportInfo

LoggedANRReportInfoList-vb50ext ::= SEQUENCE (SIZE (1..maxNumANRLoggedItems)) OF
										LoggedANRReportInfo-vb50ext

LoggedANRReportInfo ::= SEQUENCE {
	plmn-Identity 						PLMN-Identity,
	servingCell							CellIdentity,
	loggedCellInfo						LoggedCellInfo
}

LoggedANRReportInfo-vb50ext ::= SEQUENCE {
	loggedCellInfo						LoggedCellInfo-vb50ext
}

LoggedCellInfo ::= CHOICE {
	loggedUTRACellInfo					LoggedUTRACellInfo,
	loggedEUTRACellInfo					LoggedEUTRACellInfo,
	loggedGSMCellInfo					LoggedGSMCellInfo
}

LoggedCellInfo-vb50ext ::= CHOICE {
	loggedEUTRACellInfo					LoggedEUTRACellInfo-vb50ext
}

LoggedConnectionEstablishmentFailureInfo-FDD ::=		SEQUENCE {
	loggedConnectionEstablishmentFailureAccessInfo-FDD
				LoggedConnectionEstablishmentFailureAccessInfo-FDD,
	loggedMeasFailedCellMeas				LoggedMeasServingCellMeas-FDD,
	loggedMeasIntrafreqNeighbourList		LoggedMeasIntrafreqNeighbourList-FDD		OPTIONAL,
	loggedMeasInterfreqList					LoggedMeasInterfreqList-FDD					OPTIONAL,
	loggedMeasInterRATNeighbourMeas			LoggedMeasInterRATNeighbourMeas-vb50ext		OPTIONAL,
	loggedConnectionEstablishmentFailureLocationInfo
								LoggedConnectionEstablishmentFailureLocationInfo		OPTIONAL
}

LoggedConnectionEstablishmentFailureInfo-FDD-vc50ext ::=		SEQUENCE {
	loggedMeasInterRATNeighbourMeas			LoggedMeasInterRATNeighbourMeas-vc50ext		OPTIONAL
}

LoggedConnectionEstablishmentFailureInfo-FDD-r11 ::=		SEQUENCE {
	loggedConnectionEstablishmentFailureAccessInfo-FDD
				LoggedConnectionEstablishmentFailureAccessInfo-FDD,
	loggedMeasFailedCellMeas				LoggedMeasServingCellMeas-FDD,
	loggedMeasIntrafreqNeighbourList		LoggedMeasIntrafreqNeighbourList-FDD		OPTIONAL,
	loggedMeasInterfreqList					LoggedMeasInterfreqList-FDD					OPTIONAL,
	loggedMeasInterRATNeighbourMeas			LoggedMeasInterRATNeighbourMeas-r11			OPTIONAL,
	loggedConnectionEstablishmentFailureLocationInfo
								LoggedConnectionEstablishmentFailureLocationInfo		OPTIONAL
}

LoggedConnectionEstablishmentFailureInfo-TDD128 ::=		SEQUENCE {
	loggedConnectionEstablishmentFailureAccessInfo-TDD
				LoggedConnectionEstablishmentFailureAccessInfo-TDD,
	loggedMeasFailedCellMeas				LoggedMeasServingCellMeas-TDD128,
	loggedMeasIntrafreqNeighbourList		LoggedMeasIntrafreqNeighbourMeasList-TDD128	OPTIONAL,
	loggedMeasInterfreqList					LoggedMeasInterfreqList-TDD128				OPTIONAL,
	loggedMeasInterRATNeighbourMeas			LoggedMeasInterRATNeighbourMeas-vb50ext		OPTIONAL,
	loggedConnectionEstablishmentFailureLocationInfo
 								LoggedConnectionEstablishmentFailureLocationInfo		OPTIONAL
}

LoggedConnectionEstablishmentFailureInfo-TDD128-r11 ::=		SEQUENCE {
	loggedConnectionEstablishmentFailureAccessInfo-TDD
				LoggedConnectionEstablishmentFailureAccessInfo-TDD,
	loggedMeasFailedCellMeas				LoggedMeasServingCellMeas-TDD128,
	loggedMeasIntrafreqNeighbourList		LoggedMeasIntrafreqNeighbourMeasList-TDD128	OPTIONAL,
	loggedMeasInterfreqList					LoggedMeasInterfreqList-TDD128				OPTIONAL,
	loggedMeasInterRATNeighbourMeas			LoggedMeasInterRATNeighbourMeas-r11			OPTIONAL,
	loggedConnectionEstablishmentFailureLocationInfo
 								LoggedConnectionEstablishmentFailureLocationInfo		OPTIONAL
}

LoggedConnectionEstablishmentFailureInfo-TDD128-vc50ext ::= 		SEQUENCE {
	loggedMeasInterRATNeighbourMeas			LoggedMeasInterRATNeighbourMeas-vc50ext			OPTIONAL
}


LoggedConnectionEstablishmentFailureAccessInfo-FDD ::= SEQUENCE {
	numberOfRRCMsgTransmitted 				INTEGER (0..8)
}

LoggedConnectionEstablishmentFailureAccessInfo-TDD ::= SEQUENCE {
	numberOfRRCMsgTransmitted 				INTEGER (0..8),
	fpachReceived							BOOLEAN,
	e-RUCCHFailure							BOOLEAN		OPTIONAL
}

LoggedConnectionEstablishmentFailureLocationInfo ::= SEQUENCE {
	location	CHOICE {
		ellipsoidPoint						EllipsoidPoint,
		ellipsoidPointUncertCircle			EllipsoidPointUncertCircle,
		ellipsoidPointUncertEllipse			EllipsoidPointUncertEllipse,
		ellipsoidPointAltitude				EllipsoidPointAltitude,
		ellipsoidPointAltitudeEllipse		EllipsoidPointAltitudeEllipsoide
	},
	horizontalVelocity			HorizontalVelocity		OPTIONAL
}

ConnectionEstablishmentFailureReport ::=		SEQUENCE {
	timeSinceFailure				INTEGER (0..172800),
	modeSpecificInfo				CHOICE {
		fdd								SEQUENCE {
			loggedConnectionEstablishmentFailureInfo
											LoggedConnectionEstablishmentFailureInfo-FDD
		},
		tdd								SEQUENCE {
			loggedConnectionEstablishmentFailureInfo
											LoggedConnectionEstablishmentFailureInfo-TDD128
		}
	}
}

ConnectionEstablishmentFailureReport-r11 ::=	SEQUENCE {
	timeSinceFailure				INTEGER (0..172800),
	modeSpecificInfo				CHOICE {
		fdd								SEQUENCE {
			loggedConnectionEstablishmentFailureInfo
											LoggedConnectionEstablishmentFailureInfo-FDD-r11
		},
		tdd								SEQUENCE {
			loggedConnectionEstablishmentFailureInfo
											LoggedConnectionEstablishmentFailureInfo-TDD128-r11
		}
	}
}

ConnectionEstablishmentFailureReport-vc50ext ::=		SEQUENCE {
	modeSpecificInfo				CHOICE {
		fdd								SEQUENCE {
			loggedConnectionEstablishmentFailureInfo
											LoggedConnectionEstablishmentFailureInfo-FDD-vc50ext
		},
		tdd								SEQUENCE {
			loggedConnectionEstablishmentFailureInfo
											LoggedConnectionEstablishmentFailureInfo-TDD128-vc50ext
		}

	}
}

LoggedEUTRACellInfo ::= SEQUENCE {
	plmn-Identity 							PLMN-Identity,
	trackingAreaCode 						BIT STRING (SIZE (16)),
	eutraCellIdentity 						BIT STRING (SIZE (28)),
	earfcn									EARFCN,
	physicalCellIdentity					EUTRA-PhysicalCellIdentity
}

LoggedEUTRACellInfo-vb50ext ::= SEQUENCE {
	earfcn									EARFCNExtension						OPTIONAL
}

LoggedGSMCellInfo ::= SEQUENCE {
	plmn-Identity 							PLMN-Identity,
	lac										BIT STRING (SIZE (16)),
	gsmCellIdentity 						BIT STRING (SIZE (16)),
	bcch-ARFCN								BCCH-ARFCN,
	bandIndicator							Frequency-Band,
	bsic									BSIC
}

LoggedMeasurementsConfigurationInfo ::= SEQUENCE {
	absoluteTimeInfo			BIT STRING (SIZE(48)),
	loggingDuration				ENUMERATED {min10, min20, min40, hr1, hr1min30,hr2,spare2,spare1},
	loggingInterval				ENUMERATED {li128,li256,li512,li1024,li2048,li3072,li4096,li6144},
	traceReference				TraceReference,
	traceRecordingSession		TraceRecordingSession,
	tce-Id						TCE-Id,
	areaConfiguration		CHOICE {
		cellIDList	SEQUENCE (SIZE (1..32)) OF
		CellIdentity,
		locationAreaList	SEQUENCE (SIZE (1..8)) OF
			LAI,
		routingAreaList		SEQUENCE (SIZE (1..8)) OF
			RAI
	}	OPTIONAL
}

LoggedMeasurementsConfigurationInfo-r11 ::= SEQUENCE {
	absoluteTimeInfo			BIT STRING (SIZE(48)),
	loggingDuration				ENUMERATED {min10, min20, min40, hr1, hr1min30,hr2,spare2,spare1},
	loggingInterval				ENUMERATED {li128,li256,li512,li1024,li2048,li3072,li4096,li6144},
	traceReference				TraceReference,
	traceRecordingSession		TraceRecordingSession,
	tce-Id						TCE-Id,
	plmnList					PlmnList		OPTIONAL,
	areaConfiguration		CHOICE {
		cellIDList	SEQUENCE (SIZE (1..32)) OF CellIDListItem,
		locationAreaList	SEQUENCE (SIZE (1..8)) OF
			LAI,
		routingAreaList		SEQUENCE (SIZE (1..8)) OF
			RAI
	}	OPTIONAL
}

LoggedMeasInterfreqList-FDD ::=	SEQUENCE (SIZE (1..maxNumFDDFreqs)) OF
	LoggedMeasInterfreqInfo-FDD

LoggedMeasInterfreqInfo-FDD ::= SEQUENCE {
	frequencyInfo		FrequencyInfo,
	loggedMeasInterfreqNeighbourList	SEQUENCE (SIZE (1..maxnumLoggedMeas)) OF
		LoggedMeasNeighbourInfo-FDD
}

LoggedMeasInterfreqInfo-TDD128 ::=	SEQUENCE {
	frequencyInfo							FrequencyInfo,
	loggedMeasInterfreqNeighbourList		LoggedMeasInterfreqNeighbourList-TDD128
}

LoggedMeasInterRATNeighbourMeas ::=		SEQUENCE {
	loggedMeasEUTRAFreqList					LoggedMeasEUTRAFreqList			OPTIONAL,
	loggedMeasGSMNeighbourCellsList			LoggedMeasGSMNeighbourCellsList	OPTIONAL
}

LoggedMeasInterRATNeighbourMeas-vb50ext ::=		SEQUENCE {
	loggedMeasEUTRAFreqList					LoggedMeasEUTRAFreqList-vb50ext
}

LoggedMeasInterRATNeighbourMeas-vc50ext ::=		SEQUENCE {
	loggedMeasEUTRAFreqList					LoggedMeasEUTRAFreqList-vc50ext			OPTIONAL
}

LoggedMeasInterRATNeighbourMeas-r11 ::=		SEQUENCE {
	loggedMeasEUTRAFreqList					LoggedMeasEUTRAFreqList-r11 	OPTIONAL,
	loggedMeasGSMNeighbourCellsList			LoggedMeasGSMNeighbourCellsList	OPTIONAL
}

LoggedMeasIntrafreqNeighbourList-FDD ::=	SEQUENCE (SIZE (1..maxnumLoggedMeas)) OF
	LoggedMeasNeighbourInfo-FDD

LoggedMeasNeighbourInfo-FDD ::= SEQUENCE {
	primaryCPICH-Info	PrimaryCPICH-Info,
	cpich-RSCP			CPICH-RSCP,
	cpich-Ec-N0			CPICH-Ec-N0
}

LoggedMeasIntrafreqNeighbourMeasList-TDD128 ::=		SEQUENCE (SIZE (1..maxnumLoggedMeas)) OF
	LoggedMeasNeighbourMeas-TDD128

LoggedMeasNeighbourMeas-TDD128 ::=	SEQUENCE {
	cellParametersID					CellParametersID,
	primaryCCPCH-RSCP					PrimaryCCPCH-RSCP
}

LoggedMeasGSMNeighbourCellsList ::=	SEQUENCE (SIZE (1..maxnumLoggedMeas)) OF
	LoggedMeasGSMNeighbourCellsinfo

LoggedMeasGSMNeighbourCellsinfo ::= SEQUENCE {
	bsic			BSIC,
	frequency-band	Frequency-Band,
	bcch-ARFCN		BCCH-ARFCN,
	gsm-CarrierRSSI	GSM-CarrierRSSI
}

LoggedMeasEUTRAFreqList ::= SEQUENCE (SIZE (1..maxNumEUTRAFreqs))OF
	LoggedMeasEUTRAFreqInfo

LoggedMeasEUTRAFreqList-vb50ext ::= SEQUENCE (SIZE (1..maxNumEUTRAFreqs)) OF
										LoggedMeasEUTRAFreqInfo-vb50ext

LoggedMeasEUTRAFreqList-r11 ::= SEQUENCE (SIZE (1..maxNumEUTRAFreqs)) OF
										LoggedMeasEUTRAFreqInfo-r11

LoggedMeasEUTRAFreqList-vc50ext ::= SEQUENCE (SIZE (1..maxNumEUTRAFreqs)) OF
										LoggedMeasEUTRAFreqInfo-vc50ext

LoggedMeasEUTRAFreqInfo		::= SEQUENCE {
	earfcn										EARFCN,
	loggedMeasEUTRAFreqNeighbourInfoList		SEQUENCE (SIZE (1.. maxnumLoggedMeas)) OF
		LoggedMeasEUTRAFreqNeighbourInfo
}

LoggedMeasEUTRAFreqInfo-vb50ext	::= SEQUENCE {
	earfcn						EARFCNExtension										OPTIONAL
}

LoggedMeasEUTRAFreqInfo-r11		::= SEQUENCE {
	earfcn										EARFCNRange,
	loggedMeasEUTRAFreqNeighbourInfoList		SEQUENCE (SIZE (1.. maxnumLoggedMeas)) OF
		LoggedMeasEUTRAFreqNeighbourInfo
}

LoggedMeasEUTRAFreqInfo-vc50ext		::= SEQUENCE {
	rSRQType								RsrqType			OPTIONAL,
	loggedMeasEUTRAFreqNeighbourInfoList	SEQUENCE (SIZE (1.. maxnumLoggedMeas)) OF
		LoggedMeasEUTRAFreqNeighbourInfo-vc50ext
}

LoggedMeasEUTRAFreqNeighbourInfo ::= SEQUENCE {
	physicalCellIdentity		EUTRA-PhysicalCellIdentity,
	rSRP						INTEGER (0..97)	,
	rSRQ						INTEGER (0..33)
}

LoggedMeasEUTRAFreqNeighbourInfo-vc50ext ::= SEQUENCE {
	rSRQExtension						INTEGER (-30..46)		OPTIONAL
}

LoggedMeasInfo-FDD ::=		SEQUENCE {
	relativeTimeStamp						INTEGER (0..7200),
	loggedMeasServingCellMeas				LoggedMeasServingCellMeas-FDD,
	loggedMeasIntrafreqNeighbourList		LoggedMeasIntrafreqNeighbourList-FDD	OPTIONAL,
	loggedMeasInterfreqList					LoggedMeasInterfreqList-FDD				OPTIONAL,
	loggedMeasInterRATNeighbourMeas			LoggedMeasInterRATNeighbourMeas			OPTIONAL,
	loggedMeasLocationInfo 					LoggedMeasLocationInfo					OPTIONAL
}

LoggedMeasInfo-FDD-vb50ext ::=		SEQUENCE {
	loggedMeasServingCellMeas				LoggedMeasServingCellMeas-FDD-vb50ext	OPTIONAL,
	loggedMeasLocationInfo 					LoggedMeasLocationInfo-vb50ext			OPTIONAL,
	loggedMeasInterRATNeighbourMeas			LoggedMeasInterRATNeighbourMeas-vb50ext	OPTIONAL
}

LoggedMeasInfo-FDD-vc50ext ::=		SEQUENCE {
	loggedMeasInterRATNeighbourMeas			LoggedMeasInterRATNeighbourMeas-vc50ext	OPTIONAL
}

LoggedMeasInfo-TDD128 ::=			SEQUENCE {
	relativeTimeStamp						INTEGER (0..7200),
	loggedMeasServingCellMeas				LoggedMeasServingCellMeas-TDD128,
	loggedMeasIntrafreqNeighbourList		LoggedMeasIntrafreqNeighbourMeasList-TDD128	OPTIONAL,
	loggedMeasInterfreqList					LoggedMeasInterfreqList-TDD128			OPTIONAL,
	loggedMeasInterRATNeighbourMeas			LoggedMeasInterRATNeighbourMeas			OPTIONAL,
	loggedMeasLocationInfo 					LoggedMeasLocationInfo					OPTIONAL
}

LoggedMeasInfo-TDD128-vb50ext ::=		SEQUENCE {
	loggedMeasServingCellMeas				LoggedMeasServingCellMeas-TDD128-vb50ext	OPTIONAL,
	loggedMeasLocationInfo 					LoggedMeasLocationInfo-vb50ext				OPTIONAL,
	loggedMeasInterRATNeighbourMeas			LoggedMeasInterRATNeighbourMeas-vb50ext		OPTIONAL
}

LoggedMeasInfo-TDD128-vc50ext ::=		SEQUENCE {
	loggedMeasInterRATNeighbourMeas			LoggedMeasInterRATNeighbourMeas-vc50ext		OPTIONAL
}

LoggedMeasInfoList-FDD ::=		SEQUENCE (SIZE (1.. maxLoggedMeasReport)) OF LoggedMeasInfo-FDD

LoggedMeasInfoList-FDD-vb50ext ::=		SEQUENCE (SIZE (1..maxLoggedMeasReport)) OF LoggedMeasInfo-FDD-vb50ext

LoggedMeasInfoList-FDD-vc50ext ::=		SEQUENCE (SIZE (1..maxLoggedMeasReport)) OF LoggedMeasInfo-FDD-vc50ext

LoggedMeasInfoList-TDD128 ::=	SEQUENCE (SIZE (1.. maxLoggedMeasReport)) OF LoggedMeasInfo-TDD128

LoggedMeasInfoList-TDD128-vb50ext ::=	SEQUENCE (SIZE (1..maxLoggedMeasReport)) OF LoggedMeasInfo-TDD128-vb50ext

LoggedMeasInfoList-TDD128-vc50ext ::=	SEQUENCE (SIZE (1..maxLoggedMeasReport)) OF LoggedMeasInfo-TDD128-vc50ext

LoggedMeasInfoList ::=			SEQUENCE {
	modeSpecificInfo				CHOICE {
		fdd								SEQUENCE {
			loggedMeasInfoList				LoggedMeasInfoList-FDD
		},
		tdd								SEQUENCE {
			loggedMeasInfoList				LoggedMeasInfoList-TDD128
		}
	}
}

LoggedMeasInfoList-vb50ext ::=			SEQUENCE {
	modeSpecificInfo				CHOICE {
		fdd								SEQUENCE {
			loggedMeasInfoList				LoggedMeasInfoList-FDD-vb50ext
		},
		tdd								SEQUENCE {
			loggedMeasInfoList				LoggedMeasInfoList-TDD128-vb50ext
		}
	}
}

LoggedMeasInfoList-vc50ext ::=			SEQUENCE {
	modeSpecificInfo				CHOICE {
		fdd								SEQUENCE {
			loggedMeasInfoList				LoggedMeasInfoList-FDD-vc50ext
		},
		tdd								SEQUENCE {
			loggedMeasInfoList				LoggedMeasInfoList-TDD128-vc50ext
		}
	}
}

LoggedMeasInterfreqList-TDD128 ::=	SEQUENCE (SIZE (1..maxNumTDDFreqs)) OF
	LoggedMeasInterfreqInfo-TDD128

LoggedMeasInterfreqNeighbourList-TDD128 ::=	SEQUENCE (SIZE (1..maxnumLoggedMeas)) OF
	LoggedMeasNeighbourMeas-TDD128

LoggedMeasLocationInfo ::= CHOICE {
	ellipsoidPoint				EllipsoidPoint,
	ellipsoidPointAltitude		EllipsoidPointAltitude
}

LoggedMeasLocationInfo-vb50ext ::= CHOICE {
	ellipsoidPointUncertCircle			EllipsoidPointUncertCircle,
	ellipsoidPointUncertEllipse			EllipsoidPointUncertEllipse,
	ellipsoidPointAltitudeEllipse		EllipsoidPointAltitudeEllipsoide
}

LoggedMeasReport ::=			SEQUENCE {
	absoluteTimeInfo					BIT STRING (SIZE(48)),
	traceReference						TraceReference,
	traceRecordingSession				TraceRecordingSession,
	tce-Id								TCE-Id,
	loggedMeasInfoList					LoggedMeasInfoList		OPTIONAL,
	loggedMeasAvailable					ENUMERATED { true }		OPTIONAL
}

LoggedMeasReport-vb50ext ::=	SEQUENCE {
	loggedMeasInfoList					LoggedMeasInfoList-vb50ext		OPTIONAL
}

LoggedMeasReport-vc50ext ::=	SEQUENCE {
	loggedMeasInfoList					LoggedMeasInfoList-vc50ext		OPTIONAL
}

LoggedMeasServingCellMeas-FDD ::=		SEQUENCE {
	cellIdentity					CellIdentity,
	cpich-RSCP						CPICH-RSCP,
	cpich-Ec-N0						CPICH-Ec-N0
}

LoggedMeasServingCellMeas-FDD-vb50ext ::=		SEQUENCE {
	plmnIdentity					PLMN-Identity		OPTIONAL
}

LoggedMeasServingCellMeas-TDD128 ::=		SEQUENCE {
	cellIdentity					CellIdentity,
	primaryCCPCH-RSCP				PrimaryCCPCH-RSCP
}

LoggedMeasServingCellMeas-TDD128-vb50ext ::=		SEQUENCE {
	plmnIdentity					PLMN-Identity		OPTIONAL
}

LoggedUTRACellInfo ::= SEQUENCE {
	plmn-Identity 							PLMN-Identity,
	cellIdentity							CellIdentity,
	uarfcn									UARFCN,
	cellParametersID						CellParametersID			OPTIONAL,
	primaryScramblingCode					PrimaryScramblingCode		OPTIONAL
}

LoggingAbsoluteThreshold ::= CHOICE {
	rscpforANR							RSCPforANR,
	ec-N0forANR							Ec-N0forANR
}

-- it applies to RSCP by step of 2 and Ec/N0 by step of 1
-- Actual value LoggingRelativeThreshold = IE value * 2	(RSCP)
-- Actual value LoggingRelativeThreshold = IE value 	(Ec/N0)
LoggingRelativeThreshold ::= 			INTEGER (-4..16)

KeplerianParameters ::=				SEQUENCE {
	toe-nav								BIT STRING (SIZE (14)),
	ganss-omega-nav						BIT STRING (SIZE (32)),
	delta-n-nav							BIT STRING (SIZE (16)),
	m-zero-nav							BIT STRING (SIZE (32)),
	omegadot-nav						BIT STRING (SIZE (24)),
	ganss-e-nav							BIT STRING (SIZE (32)),
	idot-nav							BIT STRING (SIZE (14)),
	a-sqrt-nav							BIT STRING (SIZE (32)),
	i-zero-nav							BIT STRING (SIZE (32)),
	omega-zero-nav						BIT STRING (SIZE (32)),
	c-rs-nav							BIT STRING (SIZE (16)),
	c-is-nav							BIT STRING (SIZE (16)),
	c-us-nav							BIT STRING (SIZE (16)),
	c-rc-nav							BIT STRING (SIZE (16)),
	c-ic-nav							BIT STRING (SIZE (16)),
	c-uc-nav							BIT STRING (SIZE (16))
}

MaxNumberOfReportingCellsType1 ::=	ENUMERATED {
										e1, e2, e3, e4, e5, e6}

MaxNumberOfReportingCellsType2 ::=	ENUMERATED {
										e1, e2, e3, e4, e5, e6, e7, e8, e9, e10, e11, e12}

MaxNumberOfReportingCellsType3 ::=	ENUMERATED {
										viactCellsPlus1,
										viactCellsPlus2,
										viactCellsPlus3,
										viactCellsPlus4,
										viactCellsPlus5,
										viactCellsPlus6 }

MaxReportedCellsOnRACH ::=			ENUMERATED {
										noReport,
										currentCell,
										currentAnd-1-BestNeighbour,
										currentAnd-2-BestNeighbour,
										currentAnd-3-BestNeighbour,
										currentAnd-4-BestNeighbour,
										currentAnd-5-BestNeighbour,
										currentAnd-6-BestNeighbour }

MaxReportedCellsOnRACHinterFreq ::=		INTEGER (1..8)

MeasuredResults ::=					CHOICE {
	intraFreqMeasuredResultsList		IntraFreqMeasuredResultsList,
	interFreqMeasuredResultsList		InterFreqMeasuredResultsList,
	interRATMeasuredResultsList			InterRATMeasuredResultsList,
	trafficVolumeMeasuredResultsList	TrafficVolumeMeasuredResultsList,
	qualityMeasuredResults				QualityMeasuredResults,
	ue-InternalMeasuredResults			UE-InternalMeasuredResults,
	ue-positioning-MeasuredResults		UE-Positioning-MeasuredResults,
	spare								NULL
}

MeasuredResultsOnSecUlFreq ::=		SEQUENCE {
	intraFreqMeasuredResultsList		IntraFrequencyMeasuredResultsListOnSecULFreq
}

MeasuredResultsOnSecUlFreq-vc50ext ::=	SEQUENCE {
	intraFreqMeasuredResultsList		IntraFrequencyMeasuredResultsListOnSecULFreq-vc50ext
}

MeasuredResults-v390ext ::=					SEQUENCE {
	ue-positioning-MeasuredResults-v390ext					UE-Positioning-MeasuredResults-v390ext
}


MeasuredResults-v590ext ::= CHOICE {
	intraFrequencyMeasuredResultsList		IntraFrequencyMeasuredResultsList-v590ext,
	interFrequencyMeasuredResultsList		InterFrequencyMeasuredResultsList-v590ext
}

MeasuredResults-v770ext ::= CHOICE {
	ueInternalMeasuredResults				UE-InternalMeasuredResults-v770ext,
	ue-positioning-MeasuredResults			UE-Positioning-MeasuredResults-v770ext
}

MeasuredResults-v860ext ::= CHOICE {
	ue-positioning-MeasuredResults		UE-Positioning-MeasuredResults-v860ext
}

MeasuredResults-vd20ext ::= CHOICE {
	ue-positioning-MeasuredResults		UE-Positioning-MeasuredResults-vd20ext
}

MeasuredResults-ve30ext ::= CHOICE {
	ueInternalMeasuredResults				UE-InternalMeasuredResults-ve30ext
}


MeasuredResultsList-v920ext ::=		SEQUENCE (SIZE (1..maxAdditionalMeas)) OF
										MeasuredResults-v920ext

MeasuredResultsList-vc50ext ::=		SEQUENCE (SIZE (1..maxAdditionalMeas)) OF
										MeasuredResults-vc50ext

MeasuredResultsList-vd20ext ::=		SEQUENCE (SIZE (1..maxAdditionalMeas)) OF
										MeasuredResults-vd20ext

MeasuredResultsListOnSecUlFreq ::=	SEQUENCE (SIZE (1..maxAdditionalMeas)) OF
										MeasuredResultsOnSecUlFreq

MeasuredResultsListOnSecUlFreq-vc50ext ::=	SEQUENCE (SIZE (1..maxAdditionalMeas)) OF
										MeasuredResultsOnSecUlFreq-vc50ext

MeasuredResults-v920ext ::= CHOICE {
	intraFreqMeasuredResultsList		IntraFreqMeasuredResultsList-v920ext,
	interFreqMeasuredResultsList		InterFreqMeasuredResultsList-v920ext
}

MeasuredResults-vc50ext ::= CHOICE {
	intraFreqMeasuredResultsList		IntraFreqMeasuredResultsList-vc50ext,
	interFreqMeasuredResultsList		InterFreqMeasuredResultsList-vc50ext,
	ue-positioning-MeasuredResults		UE-Positioning-MeasuredResults-vc50ext
}

MeasuredResults-LCR-r4 ::=			CHOICE {
	intraFreqMeasuredResultsList		IntraFreqMeasuredResultsList,
	interFreqMeasuredResultsList		InterFreqMeasuredResultsList,
	interRATMeasuredResultsList			InterRATMeasuredResultsList,
	trafficVolumeMeasuredResultsList	TrafficVolumeMeasuredResultsList,
	qualityMeasuredResults				QualityMeasuredResults,
	ue-InternalMeasuredResults			UE-InternalMeasuredResults-LCR-r4,
	ue-positioniing-MeasuredResults		UE-Positioning-MeasuredResults,
	spare								NULL
}

MeasuredResultsList ::=				SEQUENCE (SIZE (1..maxAdditionalMeas)) OF
										MeasuredResults

MeasuredResultsList-LCR-r4-ext ::=	SEQUENCE (SIZE (1..maxAdditionalMeas)) OF
										MeasuredResults-LCR-r4

MeasuredResultsList-v770xet ::=		SEQUENCE (SIZE (1..maxAdditionalMeas)) OF SEQUENCE {
	-- The 'measuredResults' element shall be present, if 'v770' extended measurement results
	-- associated with the corresponding element in the IE 'MeasuredResultList' shall be
	-- provided, otherwise it is not needed
	measuredResults						MeasuredResults-v770ext					OPTIONAL
}

MeasuredResultsList-v860ext ::=		SEQUENCE (SIZE (1..maxAdditionalMeas)) OF SEQUENCE {
	-- The 'measuredResults' element shall be present, if 'v860' extended measurement results
	-- associated with the corresponding element in the IE 'MeasuredResultList' shall be
	-- provided, otherwise it is not needed
	measuredResults						MeasuredResults-v860ext					OPTIONAL
}

MeasuredResultsOnRACH ::=			SEQUENCE {
	currentCell 						SEQUENCE {
		modeSpecificInfo					CHOICE {
			fdd									SEQUENCE {
				measurementQuantity					CHOICE {
					cpich-Ec-N0							CPICH-Ec-N0,
					cpich-RSCP							CPICH-RSCP,
					pathloss							Pathloss,
					cpich-Ec-N0-RSCP					CPICH-Ec-N0-RSCP
				}
			},
			tdd									SEQUENCE {
				-- For 3.84 Mcps, 7.68 Mcps and 1.28 Mcps TDD
				timeslotISCP						TimeslotISCP-List		OPTIONAL,
				primaryCCPCH-RSCP					PrimaryCCPCH-RSCP		OPTIONAL
			}
		}
	},
	monitoredCells						MonitoredCellRACH-List				OPTIONAL
}

MeasuredResultsOnRACH-v7g0ext ::= 	SEQUENCE {
		currentCell-DeltaRSCP				DeltaRSCPPerCell					OPTIONAL,
		monitoredCellRACH-List-v7g0ext		MonitoredCellRACH-List-v7g0ext		OPTIONAL
}

--The order of the list corresponds to the order of the cells in MonitoredCellRACH-List
MonitoredCellRACH-List-v7g0ext ::= SEQUENCE (SIZE (1..8)) OF
												DeltaRSCPPerCell

--TDD choice is removed, compared to tabular, in order to optimise FDD format
MeasuredResultsOnRACHFDD-r11 ::=	SEQUENCE {
	currentCell 						SEQUENCE {
		measurementQuantity					CHOICE {
			cpich-Ec-N0							CPICH-Ec-N0,
			cpich-RSCP							CPICH-RSCP,
			pathloss							Pathloss,
			cpich-Ec-N0-RSCP				CPICH-Ec-N0-RSCP
		}
	},
	measuredResultsUsedFreq				MonitoredCellRACH-ListFDD-r11	OPTIONAL,
	measuredResultsNonUsedFreq			MeasuredResultsOnRACHinterFreq	OPTIONAL,
	measuredResultsEUTRAFreq			MeasuredResultsOnRACH-EUTRAFreq	OPTIONAL
}

MeasuredResultsOnRACHinterFreq ::=		SEQUENCE {
	interFreqCellIndication-SIB11			INTEGER (0..1),
	interFreqCellIndication-SIB12			INTEGER (0..1),
	interFreqRACHRepCellsList				InterFreqRACHRepCellsList
}

MeasuredResultsOnRACHinterFreq-vc50ext ::=		SEQUENCE {
	interFreqRACHRepCellsList			InterFreqRACHRepCellsList-r12
}

MeasuredResultsOnRACH-vc50ext ::=		SEQUENCE {
	measuredResultsNonUsedFreq			MeasuredResultsOnRACHinterFreq-vc50ext		OPTIONAL,
	measuredResultsEUTRAFreq			MeasuredResultsOnRACH-EUTRAFreq-vc50ext		OPTIONAL
}

MeasuredResultsOnRACH-EUTRAFreq ::=		SEQUENCE {
	eutraFrequencyIndication-SIB19			INTEGER (0..1),
	eutraFrequencyIndicator					BIT STRING (SIZE (maxNumEUTRAFreqs-FACH))
}

MeasuredResultsOnRACH-EUTRAFreq-vc50ext ::=		SEQUENCE {
	eutraFrequencyIndicator					BIT STRING (SIZE (maxNumEUTRAFreqs-FACH))
}

MeasurementCommand ::=				CHOICE {
	setup								MeasurementType,
	modify								SEQUENCE {
		measurementType						MeasurementType					OPTIONAL
	},
	release								NULL
}

MeasurementCommand-r4 ::=			CHOICE {
	setup								MeasurementType-r4,
	modify								SEQUENCE {
		measurementType						MeasurementType-r4				OPTIONAL
	},
	release								NULL
}

MeasurementCommand-r6 ::=			CHOICE {
	setup								MeasurementType-r6,
	modify								SEQUENCE {
		measurementType						MeasurementType-r6				OPTIONAL
	},
	release								NULL
}

MeasurementCommand-r7 ::=			CHOICE {
	setup								MeasurementType-r7,
	modify								SEQUENCE {
		measurementType						MeasurementType-r7				OPTIONAL
	},
	release								NULL
}

MeasurementCommand-r8 ::=			CHOICE {
	setup								MeasurementType-r8,
	modify								SEQUENCE {
		measurementType						MeasurementType-r8				OPTIONAL
	},
	release								NULL
}

MeasurementCommand-r9 ::=			CHOICE {
	setup								MeasurementType-r9,
	modify								SEQUENCE {
		measurementType						MeasurementType-r9				OPTIONAL
	},
	release								NULL
}

MeasurementCommand-r10 ::=			CHOICE {
	setup								MeasurementType-r10,
	modify								SEQUENCE {
		measurementType						MeasurementType-r10				OPTIONAL
	},
	release								NULL
}

MeasurementCommand-r11 ::=			CHOICE {
	setup								MeasurementType-r11,
	modify								SEQUENCE {
		measurementType						MeasurementType-r11				OPTIONAL
	},
	release								NULL
}

MeasurementCommand-r12 ::=			CHOICE {
	setup								MeasurementType-r12,
	modify								SEQUENCE {
		measurementType						MeasurementType-r12				OPTIONAL
	},
	release								NULL,
	releaseAll							NULL,
	releaseSome						MeasurementsToRelease
}

MeasurementCommand-r13 ::=			CHOICE {
	setup								MeasurementType-r13,
	modify								SEQUENCE {
		measurementType						MeasurementType-r13				OPTIONAL
	},
	release								NULL,
	releaseAll							NULL,
	releaseSome						MeasurementsToRelease
}

MeasurementCommand-r14 ::=			CHOICE {
	setup								MeasurementType-r14,
	modify								SEQUENCE {
		measurementType						MeasurementType-r14				OPTIONAL
	},
	release								NULL,
	releaseAll							NULL,
	releaseSome						MeasurementsToRelease
}

MeasurementCommand-r15 ::=			CHOICE {
	setup								MeasurementType-r15,
	modify								SEQUENCE {
		measurementType						MeasurementType-r15				OPTIONAL
	},
	release								NULL,
	releaseAll							NULL,
	releaseSome						MeasurementsToRelease
}

MeasurementControlSysInfo ::=		SEQUENCE {
	-- CHOICE cellSelectQualityMeasure represents PCCPCH-RSCP in TDD mode.
	use-of-HCS							CHOICE {
		hcs-not-used 						SEQUENCE {
			cellSelectQualityMeasure			CHOICE {
				cpich-RSCP							SEQUENCE {
					intraFreqMeasurementSysInfo			IntraFreqMeasurementSysInfo-RSCP	OPTIONAL,
					interFreqMeasurementSysInfo			InterFreqMeasurementSysInfo-RSCP	OPTIONAL
				},
				cpich-Ec-N0							SEQUENCE {
					intraFreqMeasurementSysInfo			IntraFreqMeasurementSysInfo-ECN0	OPTIONAL,
					interFreqMeasurementSysInfo			InterFreqMeasurementSysInfo-ECN0	OPTIONAL
				}
			},
			interRATMeasurementSysInfo			InterRATMeasurementSysInfo-B		OPTIONAL
		},
		hcs-used							SEQUENCE {
			cellSelectQualityMeasure			CHOICE {
				cpich-RSCP							SEQUENCE {
					intraFreqMeasurementSysInfo			IntraFreqMeasurementSysInfo-HCS-RSCP	OPTIONAL,
					interFreqMeasurementSysInfo			InterFreqMeasurementSysInfo-HCS-RSCP	OPTIONAL
				},
				cpich-Ec-N0							SEQUENCE {
					intraFreqMeasurementSysInfo			IntraFreqMeasurementSysInfo-HCS-ECN0	OPTIONAL,
					interFreqMeasurementSysInfo			InterFreqMeasurementSysInfo-HCS-ECN0	OPTIONAL
				}
			},
			interRATMeasurementSysInfo			InterRATMeasurementSysInfo		OPTIONAL
		}
	},
	trafficVolumeMeasSysInfo			TrafficVolumeMeasSysInfo			OPTIONAL,
	-- dummy is not used in this version of specification and it shall be ignored by the UE.
	dummy		UE-InternalMeasurementSysInfo		OPTIONAL
}

MeasurementControlSysInfo-vc50ext ::=	SEQUENCE {
	intraFreqReportingQuantityForRACH	IntraFreqReportingQuantityForRACH-vc50ext 	OPTIONAL,
	rmp-Frequency-List					RMP-Frequency-List							OPTIONAL
}

MeasurementControlSysInfoExtension ::= SEQUENCE {
	-- CHOICE cellSelectQualityMeasure represents PCCPCH-RSCP in TDD mode.
	use-of-HCS						CHOICE {
		hcs-not-used 					SEQUENCE {
			cellSelectQualityMeasure		CHOICE {
				cpich-RSCP						SEQUENCE {
					newIntraFreqCellList			NewIntraFreqCellSI-List-RSCP	OPTIONAL,
					newInterFreqCellList			NewInterFreqCellSI-List-RSCP	OPTIONAL
				},
				cpich-Ec-N0						SEQUENCE {
					newIntraFreqCellList			NewIntraFreqCellSI-List-ECN0	OPTIONAL,
					newInterFreqCellList			NewInterFreqCellSI-List-ECN0	OPTIONAL
				}
			},
			newInterRATCellList				NewInterRATCellList				OPTIONAL
		},
		hcs-used						SEQUENCE {
			cellSelectQualityMeasure		CHOICE {
				cpich-RSCP						SEQUENCE {
					newIntraFreqCellList			NewIntraFreqCellSI-List-HCS-RSCP	OPTIONAL,
					newInterFreqCellList			NewInterFreqCellSI-List-HCS-RSCP	OPTIONAL
				},
				cpich-Ec-N0						SEQUENCE {
					newIntraFreqCellList			NewIntraFreqCellSI-List-HCS-ECN0	OPTIONAL,
					newInterFreqCellList			NewInterFreqCellSI-List-HCS-ECN0	OPTIONAL
				}
			},
			newInterRATCellList				NewInterRATCellList				OPTIONAL
		}
	}
}

MeasurementControlSysInfoExtensionAddon-r5 ::= SEQUENCE {
	--The order of the list corresponds to the order of cell in newIntraFrequencyCellInfoList
	newIntraFrequencyCellInfoListAddon-r5	SEQUENCE (SIZE (1..maxCellMeas)) OF
												CellSelectReselectInfo-v590ext	OPTIONAL,
	--The order of the list corresponds to the order of cell in newInterFrequencyCellInfoList
	newInterFrequencyCellInfoListAddon-r5	SEQUENCE (SIZE (1..maxCellMeas)) OF
												CellSelectReselectInfo-v590ext	OPTIONAL,
	--The order of the list corresponds to the order of cell in newInterRATCellInfoList
	newInterRATCellInfoListAddon-r5			SEQUENCE (SIZE (1..maxCellMeas)) OF
												CellSelectReselectInfo-v590ext	OPTIONAL
}

MeasureControlSysInfoInterFreqExt	::= SEQUENCE {
	-- CHOICE cellSelectQualityMeasure represents PCCPCH-RSCP in TDD mode.
	use-of-HCS						CHOICE {
		hcs-not-used 					SEQUENCE {
			cellSelectQualityMeasure		CHOICE {
				cpich-RSCP						SEQUENCE {
					newInterFreqCellList			NewInterFreqCellSI-List-RSCP-ext	OPTIONAL
				},
				cpich-Ec-N0						SEQUENCE {
					newInterFreqCellList			NewInterFreqCellSI-List-ECN0-ext	OPTIONAL
				}
			}
		},
		hcs-used						SEQUENCE {
			cellSelectQualityMeasure		CHOICE {
				cpich-RSCP						SEQUENCE {
					newInterFreqCellList			NewInterFreqCellSI-List-HCS-RSCP-ext	OPTIONAL
				},
				cpich-Ec-N0						SEQUENCE {
					newInterFreqCellList			NewInterFreqCellSI-List-HCS-ECN0-ext	OPTIONAL
				}
			}
		}
	},
	rmp-Frequency-List					RMP-Frequency-List							OPTIONAL
}

MeasurementControlSysInfoExtension-LCR-r4 ::= SEQUENCE {
	-- CHOICE cellSelectQualityMeasure represents PCCPCH-RSCP in TDD mode.
	use-of-HCS					CHOICE {
		hcs-not-used 				SEQUENCE {
			cellSelectQualityMeasure	CHOICE {
				cpich-RSCP					SEQUENCE {
					newIntraFreqCellList		NewIntraFreqCellSI-List-RSCP-LCR-r4	OPTIONAL,
					newInterFreqCellList		NewInterFreqCellSI-List-RSCP-LCR-r4	OPTIONAL
				},
				cpich-Ec-N0					SEQUENCE {
					newIntraFreqCellList		NewIntraFreqCellSI-List-ECN0-LCR-r4	OPTIONAL,
					newInterFreqCellList		NewInterFreqCellSI-List-ECN0-LCR-r4	OPTIONAL
				}
			},
			newInterRATCellList			NewInterRATCellList					OPTIONAL
		},
		hcs-used					SEQUENCE {
			cellSelectQualityMeasure	CHOICE {
				cpich-RSCP					SEQUENCE {
					newIntraFreqCellList		NewIntraFreqCellSI-List-HCS-RSCP-LCR-r4	OPTIONAL,
					newInterFreqCellList		NewInterFreqCellSI-List-HCS-RSCP-LCR-r4	OPTIONAL
				},
				cpich-Ec-N0					SEQUENCE {
					newIntraFreqCellList		NewIntraFreqCellSI-List-HCS-ECN0-LCR-r4	OPTIONAL,
					newInterFreqCellList		NewInterFreqCellSI-List-HCS-ECN0-LCR-r4	OPTIONAL
				}
			},
			newInterRATCellList			NewInterRATCellList					OPTIONAL
		}
	}
}

MeasurementControlSysInfo-LCR-r4-ext ::=	SEQUENCE {
	-- CHOICE use-of-HCS shall have the same value as the use-of-HCS
	-- in MeasurementControlSysInfo
	-- CHOICE cellSelectQualityMeasure represents PCCPCH-RSCP in TDD mode.
	use-of-HCS							CHOICE	{
		hcs-not-used 					SEQUENCE	{
			-- CHOICE cellSelectQualityMeasure shall have the same value as the
			-- cellSelectQualityMeasure in MeasurementControlSysInfo
			cellSelectQualityMeasure	CHOICE	{
				cpich-RSCP				SEQUENCE	{
					intraFreqMeasurementSysInfo	IntraFreqMeasurementSysInfo-RSCP-LCR-r4	OPTIONAL,
					interFreqMeasurementSysInfo	InterFreqMeasurementSysInfo-RSCP-LCR-r4	OPTIONAL
				},
				cpich-Ec-N0				SEQUENCE	{
					intraFreqMeasurementSysInfo	IntraFreqMeasurementSysInfo-ECN0-LCR-r4	OPTIONAL,
					interFreqMeasurementSysInfo	InterFreqMeasurementSysInfo-ECN0-LCR-r4	OPTIONAL
				}
			}
		},
		hcs-used						SEQUENCE	{
			-- CHOICE cellSelectQualityMeasure shall have the same value as the
			-- cellSelectQualityMeasure in MeasurementControlSysInfo
			cellSelectQualityMeasure	CHOICE	{
				cpich-RSCP				SEQUENCE	{
					intraFreqMeasurementSysInfo	IntraFreqMeasurementSysInfo-HCS-RSCP-LCR-r4	OPTIONAL,
					interFreqMeasurementSysInfo	InterFreqMeasurementSysInfo-HCS-RSCP-LCR-r4	OPTIONAL
				},
				cpich-Ec-N0				SEQUENCE	{
					intraFreqMeasurementSysInfo	IntraFreqMeasurementSysInfo-HCS-ECN0-LCR-r4	OPTIONAL,
					interFreqMeasurementSysInfo	InterFreqMeasurementSysInfo-HCS-ECN0-LCR-r4	OPTIONAL
				}
			}
		}
	}
}

MeasurementIdentity ::=		INTEGER (1..16)

MeasurementIdentityExt ::=		INTEGER (17..32)

MeasurementIdentity-r9 ::=		INTEGER (1..32)

MeasurementOccasionPatternParameter ::=		SEQUENCE {
	measurement-Occasion-Coeff			INTEGER (1..9),
	measurement-Occasion-Offset			INTEGER (0..511),
	measurement-Occasion-Length			INTEGER	(1..512),
	timeslotBitmap						BIT STRING (SIZE (7))	OPTIONAL
}

MeasurementReleaseEnhancement ::=	CHOICE {
		releaseAllMeasurements			NULL,
		releaseSomeMeasurements			MeasurementsToRelease
}

MeasurementsToRelease ::= SEQUENCE (SIZE (1..maxMeasIdentity)) OF
						MeasurementIdentity-r9

MeasurementQuantityGSM ::=			ENUMERATED {
										gsm-CarrierRSSI,
										dummy }

MeasurementQuantityEUTRA ::=		ENUMERATED {
										rsrp,
										rsrq }

MeasurementReportingMode ::=		SEQUENCE {
	measurementReportTransferMode		TransferMode,
	periodicalOrEventTrigger			PeriodicalOrEventTrigger
}

MeasurementType ::=					CHOICE {
	intraFrequencyMeasurement			IntraFrequencyMeasurement,
	interFrequencyMeasurement			InterFrequencyMeasurement,
	interRATMeasurement					InterRATMeasurement,
	ue-positioning-Measurement			UE-Positioning-Measurement,
	trafficVolumeMeasurement			TrafficVolumeMeasurement,
	qualityMeasurement					QualityMeasurement,
	ue-InternalMeasurement				UE-InternalMeasurement
}

MeasurementType-r4 ::=				CHOICE {
	intraFrequencyMeasurement			IntraFrequencyMeasurement-r4,
	interFrequencyMeasurement			InterFrequencyMeasurement-r4,
	interRATMeasurement					InterRATMeasurement-r4,
	up-Measurement						UE-Positioning-Measurement-r4,
	trafficVolumeMeasurement			TrafficVolumeMeasurement,
	qualityMeasurement					QualityMeasurement,
	ue-InternalMeasurement				UE-InternalMeasurement-r4
}

MeasurementType-r6 ::=				CHOICE {
	intraFrequencyMeasurement			IntraFrequencyMeasurement-r6,
	interFrequencyMeasurement			InterFrequencyMeasurement-r6,
	interRATMeasurement					InterRATMeasurement-r6,
	up-Measurement						UE-Positioning-Measurement-r4,
	trafficVolumeMeasurement			TrafficVolumeMeasurement,
	qualityMeasurement					QualityMeasurement,
	ue-InternalMeasurement				UE-InternalMeasurement-r4
}

MeasurementType-r7 ::=				CHOICE {
	intraFrequencyMeasurement			IntraFrequencyMeasurement-r7,
	interFrequencyMeasurement			InterFrequencyMeasurement-r7,
	interRATMeasurement					InterRATMeasurement-r6,
	up-Measurement						UE-Positioning-Measurement-r7,
	trafficVolumeMeasurement			TrafficVolumeMeasurement,
	qualityMeasurement					QualityMeasurement,
	ue-InternalMeasurement				UE-InternalMeasurement-r4
}

MeasurementType-r8 ::=				CHOICE {
	intraFrequencyMeasurement			IntraFrequencyMeasurement-r7,
	interFrequencyMeasurement			InterFrequencyMeasurement-r8,
	interRATMeasurement					InterRATMeasurement-r8,
	up-Measurement						UE-Positioning-Measurement-r8,
	trafficVolumeMeasurement			TrafficVolumeMeasurement,
	qualityMeasurement					QualityMeasurement,
	ue-InternalMeasurement				UE-InternalMeasurement-r4
}

MeasurementType-r9 ::=				CHOICE {
	intraFrequencyMeasurement			IntraFrequencyMeasurement-r9,
	interFrequencyMeasurement			InterFrequencyMeasurement-r9,
	interRATMeasurement					InterRATMeasurement-r9,
	up-Measurement						UE-Positioning-Measurement-r9,
	trafficVolumeMeasurement			TrafficVolumeMeasurement,
	qualityMeasurement					QualityMeasurement,
	ue-InternalMeasurement				UE-InternalMeasurement-r4,
	csgProximityDetection				CSGProximityDetection
}

MeasurementType-r10 ::=				CHOICE {
	intraFrequencyMeasurement			IntraFrequencyMeasurement-r10,
	interFrequencyMeasurement			InterFrequencyMeasurement-r10,
	interRATMeasurement					InterRATMeasurement-r9,
	up-Measurement						UE-Positioning-Measurement-r10,
	trafficVolumeMeasurement			TrafficVolumeMeasurement,
	qualityMeasurement					QualityMeasurement,
	ue-InternalMeasurement				UE-InternalMeasurement-r4,
	csgProximityDetection				CSGProximityDetection
}

MeasurementType-r11 ::=				CHOICE {
	intraFrequencyMeasurement			IntraFrequencyMeasurement-r11,
	interFrequencyMeasurement			InterFrequencyMeasurement-r11,
	interRATMeasurement					InterRATMeasurement-r11,
	up-Measurement						UE-Positioning-Measurement-r10,
	trafficVolumeMeasurement			TrafficVolumeMeasurement,
	qualityMeasurement					QualityMeasurement,
	ue-InternalMeasurement				UE-InternalMeasurement-r4,
	csgProximityDetection				CSGProximityDetection,
	eutraMeasurementForCELLFACH			EUTRA-MeasurementForCELLFACH
}

MeasurementType-r12 ::=				CHOICE {
	intraFrequencyMeasurement			IntraFrequencyMeasurement-r11,
	interFrequencyMeasurement			InterFrequencyMeasurement-r12,
	interRATMeasurement					InterRATMeasurement-r12,
	up-Measurement						UE-Positioning-Measurement-r12,
	trafficVolumeMeasurement			TrafficVolumeMeasurement,
	qualityMeasurement					QualityMeasurement,
	ue-InternalMeasurement				UE-InternalMeasurement-r4,
	csgProximityDetection				CSGProximityDetection,
	eutraMeasurementForCELLFACH			EUTRA-MeasurementForCELLFACH-r12
}

MeasurementType-r13 ::=				CHOICE {
	intraFrequencyMeasurement			IntraFrequencyMeasurement-r11,
	interFrequencyMeasurement			InterFrequencyMeasurement-r12,
	interRATMeasurement				InterRATMeasurement-r12,
	up-Measurement						UE-Positioning-Measurement-r13,
	trafficVolumeMeasurement			TrafficVolumeMeasurement,
	qualityMeasurement					QualityMeasurement,
	ue-InternalMeasurement			UE-InternalMeasurement-r4,
	csgProximityDetection				CSGProximityDetection,
	eutraMeasurementForCELLFACH		EUTRA-MeasurementForCELLFACH-r12
}

MeasurementType-r14 ::=							CHOICE {
	intraFrequencyMeasurement						IntraFrequencyMeasurement-r11,
	interFrequencyMeasurement						InterFrequencyMeasurement-r12,
	interRATMeasurement							InterRATMeasurement-r12,
	up-Measurement									UE-Positioning-Measurement-r13,
	trafficVolumeMeasurement						TrafficVolumeMeasurement,
	qualityMeasurement								QualityMeasurement,
	ue-InternalMeasurement						UE-InternalMeasurement-r14,
	csgProximityDetection							CSGProximityDetection,
	eutraMeasurementForCELLFACH					EUTRA-MeasurementForCELLFACH-r12,
	applicationLayerMeasurementConfiguration	ApplicationLayerMeasurementConfiguration
}

MeasurementType-r15 ::=							CHOICE {
	intraFrequencyMeasurement						IntraFrequencyMeasurement-r11,
	interFrequencyMeasurement						InterFrequencyMeasurement-r12,
	interRATMeasurement							InterRATMeasurement-r12,
	up-Measurement									UE-Positioning-Measurement-r13,
	trafficVolumeMeasurement						TrafficVolumeMeasurement,
	qualityMeasurement								QualityMeasurement,
	ue-InternalMeasurement						UE-InternalMeasurement-r14,
	csgProximityDetection							CSGProximityDetection,
	eutraMeasurementForCELLFACH					EUTRA-MeasurementForCELLFACH-r12,
	applicationLayerMeasurementConfiguration 	ApplicationLayerMeasurementConfiguration,
	applicationLayerMeasurementConfiguration-r15 ApplicationLayerMeasurementConfiguration-r15
}


MeasurementType-Relocation-r14 ::=				CHOICE {
	intraFrequencyMeasurement						IntraFrequencyMeasurement-r11,
	interFrequencyMeasurement						InterFrequencyMeasurement-r12,
	interRATMeasurement							InterRATMeasurement-r12,
	up-Measurement									UE-Positioning-Measurement-r13,
	trafficVolumeMeasurement						TrafficVolumeMeasurement,
	qualityMeasurement								QualityMeasurement,
	ue-InternalMeasurement						UE-InternalMeasurement-r14,
	csgProximityDetection							CSGProximityDetection,
	eutraMeasurementForCELLFACH					EUTRA-MeasurementForCELLFACH-r12,
	applicationLayerMeasurement					NULL
}

MeasurementType-Relocation-r15 ::=				CHOICE {
	intraFrequencyMeasurement						IntraFrequencyMeasurement-r11,
	interFrequencyMeasurement						InterFrequencyMeasurement-r12,
	interRATMeasurement							InterRATMeasurement-r12,
	up-Measurement									UE-Positioning-Measurement-r13,
	trafficVolumeMeasurement						TrafficVolumeMeasurement,
	qualityMeasurement								QualityMeasurement,
	ue-InternalMeasurement						UE-InternalMeasurement-r14,
	csgProximityDetection							CSGProximityDetection,
	eutraMeasurementForCELLFACH					EUTRA-MeasurementForCELLFACH-r12,
	applicationLayerMeasurement					NULL,
	applicationLayerMeasurement-r15				NULL

}

MeasurementValidity ::=				SEQUENCE {
	ue-State							ENUMERATED {
											cell-DCH, all-But-Cell-DCH, all-States }
}

MonitoredCellRACH-List ::=			SEQUENCE (SIZE (1..8)) OF
										MonitoredCellRACH-Result

MonitoredCellRACH-Result ::=		SEQUENCE {
	sfn-SFN-ObsTimeDifference			SFN-SFN-ObsTimeDifference			OPTIONAL,
	modeSpecificInfo					CHOICE {
		fdd									SEQUENCE {
			primaryCPICH-Info					PrimaryCPICH-Info,
			measurementQuantity					CHOICE {
				cpich-Ec-N0							CPICH-Ec-N0,
				cpich-RSCP							CPICH-RSCP,
				pathloss							Pathloss,
				spare								NULL
			}																OPTIONAL
		},
		tdd									SEQUENCE {
			cellParametersID					CellParametersID,
			primaryCCPCH-RSCP					PrimaryCCPCH-RSCP
		}
	}
}

MonitoredCellRACH-ListFDD-r11 ::=	SEQUENCE (SIZE (1..8)) OF
										MonitoredCellRACH-ResultFDD-r11

--TDD choice is removed, compared to tabular, in order to optimise FDD format
MonitoredCellRACH-ResultFDD-r11 ::=	SEQUENCE {
	sfn-SFN-ObsTimeDifference			SFN-SFN-ObsTimeDifference			OPTIONAL,
	primaryCPICH-Info					PrimaryCPICH-Info,
		measurementQuantity					CHOICE {
			cpich-Ec-N0							CPICH-Ec-N0,
			cpich-RSCP							CPICH-RSCP,
			pathloss							Pathloss,
			spare								NULL
	}
}

MultipathIndicator ::=				ENUMERATED {
										nm,
										low,
										medium,
										high }

MultipleEUTRAFrequencyBandIndicatorList ::=	SEQUENCE (SIZE (1.. maxMultipleFrequencyBandsEUTRA)) OF
												RadioFrequencyBandEUTRA

MultipleEUTRAFrequencyBandIndicatorExtensionList ::= SEQUENCE (SIZE (1.. maxMultipleFrequencyBandsEUTRA))
														OF	RadioFrequencyBandEUTRAExt

MultipleEUTRAFrequencyBandInfo ::=	SEQUENCE {
	multipleEUTRAFrequencyBandIndicatorlist		MultipleEUTRAFrequencyBandIndicatorList		OPTIONAL
}

MultipleEUTRAFrequencyBandExtensionInfo ::=	SEQUENCE {
	multipleEUTRAFrequencyBandIndicatorlist		MultipleEUTRAFrequencyBandIndicatorExtensionList	OPTIONAL
}

MultipleEUTRAFrequencyInfoList ::=	SEQUENCE (SIZE (1.. maxNumEUTRAFreqs)) OF
												MultipleEUTRAFrequencyBandInfo

MultipleEUTRAFrequencyInfoExtensionList ::=	SEQUENCE (SIZE (1.. maxNumEUTRAFreqs)) OF
												MultipleEUTRAFrequencyBandExtensionInfo

MultipleFrequencyBandIndicatorListFDD::=	SEQUENCE (SIZE (1..maxMultipleFrequencyBandsFDD)) OF
												FrequencyBandsIndicatorFDD

MultipleFrequencyBandInfo ::=	SEQUENCE {
	multipleFrequencyBandIndicatorListFDD		MultipleFrequencyBandIndicatorListFDD		OPTIONAL
}

MultipleFrequencyInfoListFDD ::=	SEQUENCE (SIZE (1.. maxNumFDDFreqs)) OF
												MultipleFrequencyBandInfo

N-CR-T-CRMaxHyst ::=				SEQUENCE {
	n-CR								INTEGER (1..16)						DEFAULT 8,
	t-CRMaxHyst							T-CRMaxHyst
}

NAVclockModel ::=					SEQUENCE {
	navToc								BIT STRING (SIZE (16)),
	navaf2								BIT STRING (SIZE (8)),
	navaf1								BIT STRING (SIZE (16)),
	navaf0								BIT STRING (SIZE (22)),
	navTgd								BIT STRING (SIZE (8))
}

NavigationModelSatInfo ::=			SEQUENCE {
	satID								SatID,
	satelliteStatus						SatelliteStatus,
	ephemerisParameter					EphemerisParameter		OPTIONAL
}

NavigationModelSatInfoList ::=		SEQUENCE (SIZE (1..maxSat)) OF
										NavigationModelSatInfo

NavModel-BDSKeplerianSet ::= 		SEQUENCE {
	bdsAODE				BIT STRING (SIZE (5)),
	bdsURAI				BIT STRING (SIZE (4)),
	bdsToe				BIT STRING (SIZE (17)),
	bdsAPowerHalf		BIT STRING (SIZE (32)),
	bdsE				BIT STRING (SIZE (32)),
	bdsW				BIT STRING (SIZE (32)),
	bdsDeltaN			BIT STRING (SIZE (16)),
	bdsM0				BIT STRING (SIZE (32)),
	bdsOmega0			BIT STRING (SIZE (32)),
	bdsOmegaDot			BIT STRING (SIZE (24)),
	bdsI0				BIT STRING (SIZE (32)),
	bdsIDot				BIT STRING (SIZE (14)),
	bdsCuc				BIT STRING (SIZE (18)),
	bdsCus				BIT STRING (SIZE (18)),
	bdsCrc				BIT STRING (SIZE (18)),
	bdsCrs				BIT STRING (SIZE (18)),
	bdsCic				BIT STRING (SIZE (18)),
	bdsCis				BIT STRING (SIZE (18))
}

NavModel-CNAVKeplerianSet ::= 		SEQUENCE {
	cnavTop								BIT STRING (SIZE (11)),
	cnavURAindex						BIT STRING (SIZE (5)),
	cnavDeltaA							BIT STRING (SIZE (26)),
	cnavAdot							BIT STRING (SIZE (25)),
	cnavDeltaNo							BIT STRING (SIZE (17)),
	cnavDeltaNoDot						BIT STRING (SIZE (23)),
	cnavMo								BIT STRING (SIZE (33)),
	cnavE								BIT STRING (SIZE (33)),
	cnavOmega							BIT STRING (SIZE (33)),
	cnavOMEGA0							BIT STRING (SIZE (33)),
	cnavDeltaOmegaDot					BIT STRING (SIZE (17)),
	cnavIo								BIT STRING (SIZE (33)),
	cnavIoDot							BIT STRING (SIZE (15)),
	cnavCis								BIT STRING (SIZE (16)),
	cnavCic								BIT STRING (SIZE (16)),
	cnavCrs								BIT STRING (SIZE (24)),
	cnavCrc								BIT STRING (SIZE (24)),
	cnavCus								BIT STRING (SIZE (21)),
	cnavCuc								BIT STRING (SIZE (21))
}

NavModel-GLONASSecef ::=			SEQUENCE {
	gloEn								BIT STRING (SIZE (5)),
	gloP1								BIT STRING (SIZE (2)),
	gloP2								BIT STRING (SIZE (1)),
	gloM								BIT STRING (SIZE (2))				OPTIONAL,
	gloX								BIT STRING (SIZE (27)),
	gloXdot								BIT STRING (SIZE (24)),
	gloXdotdot							BIT STRING (SIZE (5)),
	gloY								BIT STRING (SIZE (27)),
	gloYdot								BIT STRING (SIZE (24)),
	gloYdotdot							BIT STRING (SIZE (5)),
	gloZ								BIT STRING (SIZE (27)),
	gloZdot								BIT STRING (SIZE (24)),
	gloZdotdot							BIT STRING (SIZE (5))
}

NavModel-NAVKeplerianSet ::=		SEQUENCE {
	navURA								BIT STRING (SIZE (4)),
	navFitFlag							BIT STRING (SIZE (1)),
	navToe								BIT STRING (SIZE (16)),
	navOmega							BIT STRING (SIZE (32)),
	navDeltaN							BIT STRING (SIZE (16)),
	navM0								BIT STRING (SIZE (32)),
	navOmegaADot						BIT STRING (SIZE (24)),
	navE								BIT STRING (SIZE (32)),
	navIDot								BIT STRING (SIZE (14)),
	navAPowerHalf						BIT STRING (SIZE (32)),
	navI0								BIT STRING (SIZE (32)),
	navOmegaA0							BIT STRING (SIZE (32)),
	navCrs								BIT STRING (SIZE (16)),
	navCis								BIT STRING (SIZE (16)),
	navCus								BIT STRING (SIZE (16)),
	navCrc								BIT STRING (SIZE (16)),
	navCic								BIT STRING (SIZE (16)),
	navCuc								BIT STRING (SIZE (16))
}

NavModel-SBASecef ::=				SEQUENCE {
	sbasTo								BIT STRING (SIZE (13))				OPTIONAL,
	sbasAccuracy						BIT STRING (SIZE (4)),
	sbasXg								BIT STRING (SIZE (30)),
	sbasYg								BIT STRING (SIZE (30)),
	sbasZg								BIT STRING (SIZE (25)),
	sbasXgDot							BIT STRING (SIZE (17)),
	sbasYgDot							BIT STRING (SIZE (17)),
	sbasZgDot							BIT STRING (SIZE (18)),
	sbasXgDotDot						BIT STRING (SIZE (10)),
	sbagYgDotDot						BIT STRING (SIZE (10)),
	sbasZgDotDot						BIT STRING (SIZE (10))
}

EphemerisParameter ::=						SEQUENCE {
	codeOnL2							BIT STRING (SIZE (2)),
	uraIndex							BIT STRING (SIZE (4)),
	satHealth							BIT STRING (SIZE (6)),
	iodc								BIT STRING (SIZE (10)),
	l2Pflag								BIT STRING (SIZE (1)),
	sf1Revd								SubFrame1Reserved,
	t-GD								BIT STRING (SIZE (8)),
	t-oc								BIT STRING (SIZE (16)),
	af2									BIT STRING (SIZE (8)),
	af1									BIT STRING (SIZE (16)),
	af0									BIT STRING (SIZE (22)),
	c-rs								BIT STRING (SIZE (16)),
	delta-n								BIT STRING (SIZE (16)),
	m0									BIT STRING (SIZE (32)),
	c-uc								BIT STRING (SIZE (16)),
	e									BIT STRING (SIZE (32)),
	c-us								BIT STRING (SIZE (16)),
	a-Sqrt								BIT STRING (SIZE (32)),
	t-oe								BIT STRING (SIZE (16)),
	fitInterval							BIT STRING (SIZE (1)),
	aodo								BIT STRING (SIZE (5)),
	c-ic								BIT STRING (SIZE (16)),
	omega0								BIT STRING (SIZE (32)),
	c-is								BIT STRING (SIZE (16)),
	i0									BIT STRING (SIZE (32)),
	c-rc								BIT STRING (SIZE (16)),
	omega								BIT STRING (SIZE (32)),
	omegaDot							BIT STRING (SIZE (24)),
	iDot								BIT STRING (SIZE (14))
}
NC-Mode ::=							BIT STRING (SIZE (3))

Neighbour ::=						SEQUENCE {
	modeSpecificInfo				CHOICE {
		fdd								SEQUENCE {
			neighbourIdentity					PrimaryCPICH-Info					OPTIONAL,
			uE-RX-TX-TimeDifferenceType2Info	UE-RX-TX-TimeDifferenceType2Info	OPTIONAL
		},
		tdd								SEQUENCE {
			neighbourAndChannelIdentity		CellAndChannelIdentity					OPTIONAL
		}
	},
	neighbourQuality					NeighbourQuality,
	sfn-SFN-ObsTimeDifference2			SFN-SFN-ObsTimeDifference2}

Neighbour-v390ext ::=						SEQUENCE {
	modeSpecificInfo				CHOICE {
		fdd								SEQUENCE {
			frequencyInfo						FrequencyInfo
		},
		tdd								NULL
	}
}

NeighbourList ::=					SEQUENCE (SIZE (1..maxCellMeas)) OF
										Neighbour

Neighbour-TDD-r7 ::=				SEQUENCE {
	uarfcn								UARFCN									OPTIONAL
}

-- The order of the cells in IE NeighbourList-TDD-r7 shall be the
-- same as the order in IE NeighbourList
NeighbourList-TDD-r7 ::=			SEQUENCE (SIZE (1..maxCellMeas)) OF Neighbour-TDD-r7

-- The order of the cells in IE NeighbourList-v390ext shall be the
-- same as the order in IE NeighbourList
NeighbourList-v390ext ::=					SEQUENCE (SIZE (1..maxCellMeas)) OF
										Neighbour-v390ext

NeighbourQuality ::=				SEQUENCE {
	ue-Positioning-OTDOA-Quality		UE-Positioning-OTDOA-Quality
}

NewInterFreqCell ::=				SEQUENCE {
	interFreqCellID						InterFreqCellID						OPTIONAL,
	frequencyInfo						FrequencyInfo						OPTIONAL,
	cellInfo							CellInfo
}

NewInterFreqCell-r4 ::=				SEQUENCE {
	interFreqCellID						InterFreqCellID						OPTIONAL,
	frequencyInfo						FrequencyInfo						OPTIONAL,
	cellInfo							CellInfo-r4
}

NewInterFreqCell-v7b0ext ::=		SEQUENCE {
	intraSecondaryFreqIndicator			BOOLEAN
}

NewInterFreqCell-LCR-v8a0ext ::=		SEQUENCE {
	cellInfo-LCR-r8							CellInfo-LCR-r8-ext				OPTIONAL
}

NewInterFreqCell-r8 ::= SEQUENCE {
	interFreqCellID						InterFreqCellID					OPTIONAL,
	frequencyInfo						FrequencyInfo					OPTIONAL,
	cellInfo							CellInfo-r4,
	modeSpecificInfo					CHOICE {
		noInfo								NULL,
		tdd128								SEQUENCE {
			intraSecondaryFreqIndicator			BOOLEAN
		}
	}
}

NewInterFreqCell-r9 ::= SEQUENCE {
	interFreqCellID						InterFreqCellID					OPTIONAL,
	frequencyInfo						FrequencyInfo					OPTIONAL,
	cellInfo							CellInfo-r9,
	modeSpecificInfo					CHOICE {
		noInfo								NULL,
		tdd128								SEQUENCE {
			intraSecondaryFreqIndicator			BOOLEAN
		}
	}
}

NewInterFreqCell-r10 ::= SEQUENCE {
	interFreqCellID						InterFreqCellID					OPTIONAL,
	frequencyInfo						FrequencyInfo					OPTIONAL,
	cellInfo							CellInfo-r9,
	modeSpecificInfo					CHOICE {
		noInfo								NULL,
		tdd128								SEQUENCE {
			intraSecondaryFreqIndicator			BOOLEAN,
			sNPLMonitorSetIndicator-TDD128		BIT STRING (SIZE (5))		OPTIONAL
		}
	}
}

NewInterFreqCell-r12 ::= SEQUENCE {
	interFreqCellID						InterFreqCellID-r12				OPTIONAL,
	frequencyInfo						FrequencyInfo					OPTIONAL,
	cellInfo							CellInfo-r9,
	modeSpecificInfo					CHOICE {
		noInfo								NULL,
		tdd128								SEQUENCE {
			intraSecondaryFreqIndicator			BOOLEAN,
			sNPLMonitorSetIndicator-TDD128		BIT STRING (SIZE (5))	OPTIONAL
		}
	}
}

NewInterFreqCellList ::=			SEQUENCE (SIZE (1..maxCellMeas)) OF
										NewInterFreqCell

NewInterFreqCellList-r4 ::=			SEQUENCE (SIZE (1..maxCellMeas)) OF
										NewInterFreqCell-r4

NewInterFreqCellList-r12 ::=			SEQUENCE (SIZE (1..maxCellMeas-ext)) OF
										NewInterFreqCell-r12

-- The order of the list corresponds to the order of cells in newInterFreqCellList
NewInterFreqCellList-v7b0ext ::=	SEQUENCE (SIZE (1..maxCellMeas)) OF
										NewInterFreqCell-v7b0ext

-- The order of the list corresponds to the order of cells in newInterFreqCellList
NewInterFreqCellList-LCR-v8a0ext ::=	SEQUENCE (SIZE (1..maxCellMeas)) OF
											NewInterFreqCell-LCR-v8a0ext

NewInterFreqCellList-r8 ::=			SEQUENCE (SIZE (1..maxCellMeas)) OF
										NewInterFreqCell-r8

NewInterFreqCellList-r9 ::=			SEQUENCE (SIZE (1..maxCellMeas)) OF
										NewInterFreqCell-r9

NewInterFreqCellList-r10 ::=			SEQUENCE (SIZE (1..maxCellMeas)) OF
										NewInterFreqCell-r10

NewInterFreqCellSI-RSCP ::=				SEQUENCE {
	interFreqCellID						InterFreqCellID						OPTIONAL,
	frequencyInfo						FrequencyInfo						OPTIONAL,
	cellInfo							CellInfoSI-RSCP
}

NewInterFreqCellSI-RSCP-ext ::=				SEQUENCE {
	interFreqCellID						InterFreqCellID-r12					OPTIONAL,
	frequencyInfo						FrequencyInfo						OPTIONAL,
	cellInfo							CellInfoSI-RSCP
}

NewInterFreqCellSI-ECN0 ::=				SEQUENCE {
	interFreqCellID						InterFreqCellID						OPTIONAL,
	frequencyInfo						FrequencyInfo						OPTIONAL,
	cellInfo							CellInfoSI-ECN0
}

NewInterFreqCellSI-ECN0-ext ::=				SEQUENCE {
	interFreqCellID						InterFreqCellID-r12					OPTIONAL,
	frequencyInfo						FrequencyInfo						OPTIONAL,
	cellInfo							CellInfoSI-ECN0
}

NewInterFreqCellSI-HCS-RSCP ::=				SEQUENCE {
	interFreqCellID						InterFreqCellID						OPTIONAL,
	frequencyInfo						FrequencyInfo						OPTIONAL,
	cellInfo							CellInfoSI-HCS-RSCP
}

NewInterFreqCellSI-HCS-RSCP-ext ::=				SEQUENCE {
	interFreqCellID						InterFreqCellID-r12					OPTIONAL,
	frequencyInfo						FrequencyInfo						OPTIONAL,
	cellInfo							CellInfoSI-HCS-RSCP
}

NewInterFreqCellSI-HCS-ECN0 ::=				SEQUENCE {
	interFreqCellID						InterFreqCellID						OPTIONAL,
	frequencyInfo						FrequencyInfo						OPTIONAL,
	cellInfo							CellInfoSI-HCS-ECN0
}

NewInterFreqCellSI-HCS-ECN0-ext ::=				SEQUENCE {
	interFreqCellID						InterFreqCellID-r12					OPTIONAL,
	frequencyInfo						FrequencyInfo						OPTIONAL,
	cellInfo							CellInfoSI-HCS-ECN0
}

NewInterFreqCellSI-RSCP-LCR-r4 ::=			SEQUENCE {
	interFreqCellID						InterFreqCellID						OPTIONAL,
	frequencyInfo						FrequencyInfo						OPTIONAL,
	cellInfo							CellInfoSI-RSCP-LCR-r4
}

NewInterFreqCellSI-ECN0-LCR-r4 ::=			SEQUENCE {
	interFreqCellID						InterFreqCellID						OPTIONAL,
	frequencyInfo						FrequencyInfo						OPTIONAL,
	cellInfo							CellInfoSI-ECN0-LCR-r4
}

NewInterFreqCellSI-HCS-RSCP-LCR-r4 ::=		SEQUENCE {
	interFreqCellID						InterFreqCellID						OPTIONAL,
	frequencyInfo						FrequencyInfo						OPTIONAL,
	cellInfo							CellInfoSI-HCS-RSCP-LCR-r4
}

NewInterFreqCellSI-HCS-ECN0-LCR-r4 ::=		SEQUENCE {
	interFreqCellID						InterFreqCellID						OPTIONAL,
	frequencyInfo						FrequencyInfo						OPTIONAL,
	cellInfo							CellInfoSI-HCS-ECN0-LCR-r4
}

NewInterFreqCellSI-List-ECN0 ::=			SEQUENCE (SIZE (1..maxCellMeas)) OF
										NewInterFreqCellSI-ECN0

NewInterFreqCellSI-List-ECN0-ext ::=	SEQUENCE (SIZE (1..maxCellMeas-ext2)) OF
										NewInterFreqCellSI-ECN0-ext

NewInterFreqCellSI-List-HCS-RSCP ::=			SEQUENCE (SIZE (1..maxCellMeas)) OF
										NewInterFreqCellSI-HCS-RSCP

NewInterFreqCellSI-List-HCS-RSCP-ext ::=		SEQUENCE (SIZE (1..maxCellMeas-ext2)) OF
										NewInterFreqCellSI-HCS-RSCP-ext

NewInterFreqCellSI-List-HCS-ECN0 ::=			SEQUENCE (SIZE (1..maxCellMeas)) OF
										NewInterFreqCellSI-HCS-ECN0

NewInterFreqCellSI-List-HCS-ECN0-ext ::=		SEQUENCE (SIZE (1..maxCellMeas-ext2)) OF
										NewInterFreqCellSI-HCS-ECN0-ext

NewInterFreqCellSI-List-RSCP ::=		SEQUENCE (SIZE (1..maxCellMeas)) OF
										NewInterFreqCellSI-RSCP

NewInterFreqCellSI-List-RSCP-ext ::=	SEQUENCE (SIZE (1..maxCellMeas-ext2)) OF
										NewInterFreqCellSI-RSCP-ext

NewInterFreqCellSI-List-ECN0-LCR-r4 ::=		SEQUENCE (SIZE (1..maxCellMeas)) OF
										NewInterFreqCellSI-ECN0-LCR-r4

NewInterFreqCellSI-List-HCS-RSCP-LCR-r4 ::=	SEQUENCE (SIZE (1..maxCellMeas)) OF
										NewInterFreqCellSI-HCS-RSCP-LCR-r4

NewInterFreqCellSI-List-HCS-ECN0-LCR-r4 ::=	SEQUENCE (SIZE (1..maxCellMeas)) OF
										NewInterFreqCellSI-HCS-ECN0-LCR-r4

NewInterFreqCellSI-List-RSCP-LCR-r4 ::=		SEQUENCE (SIZE (1..maxCellMeas)) OF
										NewInterFreqCellSI-RSCP-LCR-r4

NewInterRATCell ::=				SEQUENCE {
	interRATCellID						InterRATCellID			OPTIONAL,
	technologySpecificInfo				CHOICE {
		gsm									SEQUENCE {
			cellSelectionReselectionInfo		CellSelectReselectInfoSIB-11-12		OPTIONAL,
			interRATCellIndividualOffset 		InterRATCellIndividualOffset,
			bsic								BSIC,
			frequency-band						Frequency-Band,
			bcch-ARFCN							BCCH-ARFCN,
			-- dummy is not used in this version of the specification, it should
			-- not be sent and if received it should be ignored.
			dummy								NULL				OPTIONAL
		},
		is-2000								SEQUENCE {
			is-2000SpecificMeasInfo				IS-2000SpecificMeasInfo
		},
		-- ASN.1 inconsistency: NewInterRATCellList should be optional within
		-- InterRATCellInfoList. The UE shall consider IE NewInterRATCell with
		-- technologySpecificInfo set to "absent" as valid and handle the
		-- message as if the IE NewInterRATCell was absent
		absent								NULL,
		spare1								NULL
	}
}

NewInterRATCell-B ::=				SEQUENCE {
	interRATCellID						InterRATCellID				OPTIONAL,
	technologySpecificInfo				CHOICE {
		gsm									SEQUENCE {
			cellSelectionReselectionInfo		CellSelectReselectInfoSIB-11-12		OPTIONAL,
			interRATCellIndividualOffset 		InterRATCellIndividualOffset,
			bsic								BSIC,
			frequency-band						Frequency-Band,
			bcch-ARFCN							BCCH-ARFCN,
			-- dummy is not used in this version of the specification, it should
			-- not be sent and if received it should be ignored.
			dummy								NULL				OPTIONAL
		},
		is-2000								SEQUENCE {
			is-2000SpecificMeasInfo				IS-2000SpecificMeasInfo
		},
		-- ASN.1 inconsistency: NewInterRATCellList-B should be optional within
		-- InterRATCellInfoList-B. The UE shall consider IE NewInterRATCell-B with
		-- technologySpecificInfo set to "absent" as valid and handle the
		-- message as if the IE NewInterRATCell-B was absent
		absent								NULL,
		spare1								NULL
	}
}

NewInterRATCellList ::=			SEQUENCE (SIZE (1..maxCellMeas)) OF
										NewInterRATCell

NewInterRATCellList-B ::=			SEQUENCE (SIZE (1..maxCellMeas)) OF
										NewInterRATCell-B

NewIntraFreqCell ::=				SEQUENCE {
	intraFreqCellID						IntraFreqCellID						OPTIONAL,
	cellInfo							CellInfo
}

NewIntraFreqCell-r4 ::=				SEQUENCE {
	intraFreqCellID						IntraFreqCellID						OPTIONAL,
	cellInfo							CellInfo-r4
}
NewIntraFreqCell-r9 ::=				SEQUENCE {
	intraFreqCellID						IntraFreqCellID						OPTIONAL,
	cellInfo							CellInfo-r9
}

NewIntraFreqCell-r10 ::=				SEQUENCE {
	intraFreqCellID						IntraFreqCellID						OPTIONAL,
	cellInfo							CellInfo-r9,
	modeSpecificInfo					CHOICE {
		noInfo								NULL,
		tdd128								SEQUENCE {
			sNPLMonitorSetIndicator-TDD128		BIT STRING (SIZE (5))		OPTIONAL
		}
	}
}

NewIntraFreqCellOnSecULFreq ::=		SEQUENCE {
	intraFreqCellIDOnSecULFreq			IntraFreqCellIDOnSecULFreq			OPTIONAL,
	cellInfo							CellInfo-r4
}

NewIntraFreqCellList ::=			SEQUENCE (SIZE (1..maxCellMeas)) OF
										NewIntraFreqCell

NewIntraFreqCellList-r4 ::=			SEQUENCE (SIZE (1..maxCellMeas)) OF
										NewIntraFreqCell-r4

NewIntraFreqCellList-r9 ::=			SEQUENCE (SIZE (1..maxCellMeas)) OF
										NewIntraFreqCell-r9

NewIntraFreqCellList-r10 ::=		SEQUENCE (SIZE (1..maxCellMeas)) OF
										NewIntraFreqCell-r10

NewIntraFreqCell-LCR-v8a0ext ::=		SEQUENCE {
	cellInfo-LCR-r8							CellInfo-LCR-r8-ext				OPTIONAL
}

-- The order of the list corresponds to the order of cells in newIntraFreqCellList
NewIntraFreqCellList-LCR-v8a0ext ::=		SEQUENCE (SIZE (1..maxCellMeas)) OF
												NewIntraFreqCell-LCR-v8a0ext

NewIntraFreqCellListOnSecULFreq ::=	SEQUENCE (SIZE (1..maxCellMeasOnSecULFreq)) OF
										NewIntraFreqCellOnSecULFreq

NewIntraFreqCellSI-RSCP ::=				SEQUENCE {
	intraFreqCellID						IntraFreqCellID						OPTIONAL,
	cellInfo							CellInfoSI-RSCP
}

NewIntraFreqCellSI-ECN0 ::=			SEQUENCE {
	intraFreqCellID						IntraFreqCellID						OPTIONAL,
	cellInfo							CellInfoSI-ECN0
}
NewIntraFreqCellSI-HCS-RSCP ::=		SEQUENCE {
	intraFreqCellID						IntraFreqCellID						OPTIONAL,
	cellInfo							CellInfoSI-HCS-RSCP
}

NewIntraFreqCellSI-HCS-ECN0 ::=		SEQUENCE {
	intraFreqCellID						IntraFreqCellID						OPTIONAL,
	cellInfo							CellInfoSI-HCS-ECN0
}

NewIntraFreqCellSI-RSCP-LCR-r4 ::=		SEQUENCE {
	intraFreqCellID						IntraFreqCellID						OPTIONAL,
	cellInfo							CellInfoSI-RSCP-LCR-r4
}

NewIntraFreqCellSI-ECN0-LCR-r4 ::=		SEQUENCE {
	intraFreqCellID						IntraFreqCellID						OPTIONAL,
	cellInfo							CellInfoSI-ECN0-LCR-r4
}
NewIntraFreqCellSI-HCS-RSCP-LCR-r4 ::=	SEQUENCE {
	intraFreqCellID						IntraFreqCellID						OPTIONAL,
	cellInfo							CellInfoSI-HCS-RSCP-LCR-r4
}

NewIntraFreqCellSI-HCS-ECN0-LCR-r4 ::=	SEQUENCE {
	intraFreqCellID						IntraFreqCellID						OPTIONAL,
	cellInfo							CellInfoSI-HCS-ECN0-LCR-r4
}

NewIntraFreqCellSI-List-RSCP ::=		SEQUENCE (SIZE (1..maxCellMeas)) OF
											NewIntraFreqCellSI-RSCP

NewIntraFreqCellSI-List-ECN0 ::=		SEQUENCE (SIZE (1..maxCellMeas)) OF
										NewIntraFreqCellSI-ECN0

NewIntraFreqCellSI-List-HCS-RSCP ::=	SEQUENCE (SIZE (1..maxCellMeas)) OF
										NewIntraFreqCellSI-HCS-RSCP

NewIntraFreqCellSI-List-HCS-ECN0 ::=	SEQUENCE (SIZE (1..maxCellMeas)) OF
										NewIntraFreqCellSI-HCS-ECN0

NewIntraFreqCellSI-List-RSCP-LCR-r4 ::=		SEQUENCE (SIZE (1..maxCellMeas)) OF
											NewIntraFreqCellSI-RSCP-LCR-r4

NewIntraFreqCellSI-List-ECN0-LCR-r4 ::=		SEQUENCE (SIZE (1..maxCellMeas)) OF
										NewIntraFreqCellSI-ECN0-LCR-r4

NewIntraFreqCellSI-List-HCS-RSCP-LCR-r4 ::=	SEQUENCE (SIZE (1..maxCellMeas)) OF
										NewIntraFreqCellSI-HCS-RSCP-LCR-r4

NewIntraFreqCellSI-List-HCS-ECN0-LCR-r4 ::=	SEQUENCE (SIZE (1..maxCellMeas)) OF
										NewIntraFreqCellSI-HCS-ECN0-LCR-r4

	-- IE "nonUsedFreqThreshold" is not needed in case of event 2a
	-- In case of event 2a UTRAN should include value 0 within IE "nonUsedFreqThreshold"
	-- In case of event 2a, the UE shall be ignore IE "nonUsedFreqThreshold"
	-- In later versions of the message including this IE, a special version of
	-- IE "NonUsedFreqParameterList" may be defined for event 2a, namely a
	-- version not including IE "nonUsedFreqThreshold"
NonUsedFreqParameter ::=			SEQUENCE {
	nonUsedFreqThreshold				Threshold,
	nonUsedFreqW						W
}

NonUsedFreqParameter-r6 ::=			SEQUENCE {
	nonUsedFreqThreshold				Threshold-r6,
	nonUsedFreqW						W
}

NonUsedFreqParameter-r10 ::=		SEQUENCE {
	nonUsedFreqThreshold				Threshold-r6,
	nonUsedFreqW						W,
	nonUsedFreqTriggeringConditionDetectedCells	ENUMERATED { true }			OPTIONAL
}

NonUsedFreqParameter-r11 ::=		SEQUENCE {
	nonUsedFreqThreshold						Threshold-r6,
	nonUsedFreqW								W,
	nonUsedFreqTriggeringConditionDetectedCells	ENUMERATED { true }				OPTIONAL,
	-- dummy is not used in this version of the specification and
	-- it should be ignored by the receiver.
	dummy						CellInfoListToBeExcluded		OPTIONAL
}

NonUsedFreq2aParameter-r10 ::=	SEQUENCE {
	nonUsedFreqW						W,
	nonUsedFreqTriggeringConditionDetectedCells	ENUMERATED { true }			OPTIONAL
}

NonUsedFreq2aParameter-r11 ::=	SEQUENCE {
	nonUsedFreqW								W,
	nonUsedFreqTriggeringConditionDetectedCells	ENUMERATED { true }				OPTIONAL,
	-- dummy is not used in this version of the specification and
	-- it should be ignored by the receiver.
	dummy						CellInfoListToBeExcluded		OPTIONAL
}

NonUsedFreqParameterList ::=		SEQUENCE (SIZE (1..maxFreq)) OF
										NonUsedFreqParameter

NonUsedFreqParameterList-r6 ::=		SEQUENCE (SIZE (1..maxFreq)) OF
										NonUsedFreqParameter-r6

NonUsedFreqParameterList-r10 ::=	SEQUENCE (SIZE (1..maxFreq)) OF
										NonUsedFreqParameter-r10

NonUsedFreqParameterList-r11 ::=	SEQUENCE (SIZE (1..maxFreq)) OF
										NonUsedFreqParameter-r11

NonUsedFreq2aParameterList-r10 ::=	SEQUENCE (SIZE (1..maxFreq)) OF
										NonUsedFreq2aParameter-r10

NonUsedFreq2aParameterList-r11 ::=	SEQUENCE (SIZE (1..maxFreq)) OF
										NonUsedFreq2aParameter-r11

NonUsedFreqWList-r6 ::=		SEQUENCE (SIZE (1..maxFreq)) OF W

ApplicationLayerMeasurementConfiguration ::=		SEQUENCE {
	containerForApplicationLayerMeasurementConfiguration	OCTET STRING ( SIZE (1..1000))
}

ApplicationLayerMeasurementConfiguration-r15 ::=	 SEQUENCE {
	containerForApplicationLayerMeasurementConfiguration	 OCTET STRING ( SIZE (1..1000)),
	serviceType										ENUMERATED { qoe, qoemtsi }
}

ApplicationLayerMeasurementReporting ::=		SEQUENCE {
	containerForApplicationLayerMeasurementReporting		OCTET STRING ( SIZE (1..8000))
}

ApplicationLayerMeasurementReporting-r15 ::=		SEQUENCE {
	containerForApplicationLayerMeasurementReporting		OCTET STRING ( SIZE (1..8000)),
	serviceType										ENUMERATED { qoe, qoemtsi }
}

ObservedTimeDifferenceToGSM ::=		INTEGER (0..4095)

OTDOA-SearchWindowSize ::=			ENUMERATED {
										c20, c40, c80, c160, c320,
										c640, c1280, moreThan1280 }

-- SPARE: Pathloss, Max = 158
-- Values above Max are spare
Pathloss ::=						INTEGER (46..173)

PenaltyTime-RSCP ::=				CHOICE {
	notUsed								NULL,
	pt10								TemporaryOffset1,
	pt20								TemporaryOffset1,
	pt30								TemporaryOffset1,
	pt40								TemporaryOffset1,
	pt50								TemporaryOffset1,
	pt60								TemporaryOffset1
}

PenaltyTime-ECN0 ::=				CHOICE {
	notUsed								NULL,
	pt10								TemporaryOffsetList,
	pt20								TemporaryOffsetList,
	pt30								TemporaryOffsetList,
	pt40								TemporaryOffsetList,
	pt50								TemporaryOffsetList,
	pt60								TemporaryOffsetList
}

PendingTimeAfterTrigger ::=			ENUMERATED {
										ptat0-25, ptat0-5, ptat1,
										ptat2, ptat4, ptat8, ptat16 }

PeriodicalOrEventTrigger ::=		ENUMERATED {
										periodical,
										eventTrigger }

PeriodicalReportingCriteria ::=		SEQUENCE {
	reportingAmount						ReportingAmount					DEFAULT ra-Infinity,
	reportingInterval					ReportingIntervalLong
}

PeriodicReportingInfo-1b ::= SEQUENCE {
	reportingAmount						ReportingAmount,
	reportingInterval					ReportingInterval
}

PeriodicalWithReportingCellStatus ::= SEQUENCE {
	periodicalReportingCriteria			PeriodicalReportingCriteria,
	reportingCellStatus					ReportingCellStatus					OPTIONAL
}

PeriodicalWithReportingCellStatus-r10 ::= SEQUENCE {
	periodicalReportingCriteria			PeriodicalReportingCriteria,
	reportingCellStatus					ReportingCellStatus-r10				OPTIONAL
}

PeriodicalWithReportingCellStatusOnSecULFreq ::= SEQUENCE {
	frequencyInfo						FrequencyInfo,
	periodicalWithReportingCellStatus 	PeriodicalWithReportingCellStatus-r10
}

PLMNIdentitiesOfNeighbourCells ::=	SEQUENCE {
		plmnsOfIntraFreqCellsList		PLMNsOfIntraFreqCellsList			OPTIONAL,
		plmnsOfInterFreqCellsList		PLMNsOfInterFreqCellsList			OPTIONAL,
		plmnsOfInterRATCellsList		PLMNsOfInterRATCellsList			OPTIONAL
}

PLMNIdentitiesOfNeighbourCells-v860ext ::=	SEQUENCE {
		multipleplmnsOfIntraFreqCellsList	MultiplePLMNsOfIntraFreqCellsList	OPTIONAL,
		multipleplmnsOfInterFreqCellsList	MultiplePLMNsOfInterFreqCellsList	OPTIONAL
}

PLMNIdentitiesOfNeighbourCells-vc50ext	::=	SEQUENCE {
		plmnsOfInterFreqCellsList 			PLMNsOfInterFreqCellsList-vc50ext			OPTIONAL,
		multipleplmnsOfInterFreqCellsList	MultiplePLMNsOfInterFreqCellsList-vc50ext	OPTIONAL
}

PlmnList ::= SEQUENCE (SIZE (1..maxNumMDTPLMN)) OF  PLMN-Identity

PLMNsOfInterFreqCellsList ::=			SEQUENCE (SIZE (1..maxCellMeas)) OF
											SEQUENCE {
	plmn-Identity								PLMN-Identity				OPTIONAL
}

PLMNsOfInterFreqCellsList-vc50ext ::=		SEQUENCE (SIZE (1..maxCellMeas-ext)) OF	InterFreqCellPLMN

InterFreqCellPLMN ::=						SEQUENCE {
	plmn-Identity								PLMN-Identity				OPTIONAL
}

MultiplePLMNsOfInterFreqCellsList ::=	SEQUENCE (SIZE (1..maxCellMeas)) OF
											SEQUENCE {
	multiplePLMN-list							SEQUENCE (SIZE (1..6)) OF
													PLMN-IdentityWithOptionalMCC-r6		OPTIONAL
}

MultiplePLMNsOfInterFreqCellsList-vc50ext ::=	SEQUENCE (SIZE (1..maxCellMeas-ext)) OF 	MultiplePLMNInfo

MultiplePLMNInfo ::=					SEQUENCE {
	multiplePLMN-list						MultiplePLMN-List			OPTIONAL
}

MultiplePLMN-List ::=					SEQUENCE (SIZE (1..6)) OF	PLMN-IdentityWithOptionalMCC-r6

PLMNsOfIntraFreqCellsList ::=			SEQUENCE (SIZE (1..maxCellMeas)) OF
											SEQUENCE {
	plmn-Identity								PLMN-Identity				OPTIONAL
}

MultiplePLMNsOfIntraFreqCellsList ::=	SEQUENCE (SIZE (1..maxCellMeas)) OF
											SEQUENCE {
	multiplePLMN-list							SEQUENCE (SIZE (1..6)) OF
													PLMN-IdentityWithOptionalMCC-r6		OPTIONAL
}

PLMNsOfInterRATCellsList ::=			SEQUENCE (SIZE (1..maxCellMeas)) OF
											SEQUENCE {
	plmn-Identity								PLMN-Identity				OPTIONAL
}

PositionEstimate ::=				CHOICE {
	ellipsoidPoint						EllipsoidPoint,
	ellipsoidPointUncertCircle			EllipsoidPointUncertCircle,
	ellipsoidPointUncertEllipse			EllipsoidPointUncertEllipse,
	ellipsoidPointAltitude				EllipsoidPointAltitude,
	ellipsoidPointAltitudeEllipse		EllipsoidPointAltitudeEllipsoide
}

PositioningMethod ::=				ENUMERATED {
										otdoa,
										gps,
										otdoaOrGPS, cellID }

-- Actual value PRC = IE value * 0.32
PRC ::=								INTEGER (-2047..2047)

-- SPARE: PrimaryCCPCH-RSCP, Max = 91
-- Values above Max are spare
PrimaryCCPCH-RSCP ::=				INTEGER (0..127)

Q-HCS ::=							INTEGER (0..99)

Q-OffsetS-N ::=						INTEGER (-50..50)

Q-QualMin ::=						INTEGER (-24..0)

Q-QualMin-Offset ::=				INTEGER (1..16)

-- Actual value Q-RxlevMin = (IE value * 2) + 1
Q-RxlevMin ::=						INTEGER (-58..-13)

-- Actual value Q-RxlevMin-Offset = (IE value * 2)
Q-RxlevMin-Offset ::=				INTEGER (1..8)

QualityEventResults ::=				SEQUENCE (SIZE (1..maxTrCH)) OF
										TransportChannelIdentity

QualityMeasuredResults ::=			SEQUENCE {
	blerMeasurementResultsList			BLER-MeasurementResultsList			OPTIONAL,
	modeSpecificInfo					CHOICE {
		fdd									NULL,
		tdd									SEQUENCE {
			sir-MeasurementResults				SIR-MeasurementList			OPTIONAL
		}
	}
}

QualityMeasurement ::=				SEQUENCE {
	qualityReportingQuantity			QualityReportingQuantity			OPTIONAL,
	reportCriteria						QualityReportCriteria
}

QualityReportCriteria ::=			CHOICE {
	qualityReportingCriteria			QualityReportingCriteria,
	periodicalReportingCriteria			PeriodicalReportingCriteria,
	noReporting							NULL
}

QualityReportingCriteria ::=		SEQUENCE (SIZE (1..maxTrCH)) OF
										QualityReportingCriteriaSingle

QualityReportingCriteriaSingle ::=	SEQUENCE {
	transportChannelIdentity			TransportChannelIdentity,
	totalCRC							INTEGER (1..512),
	badCRC								INTEGER (1..512),
	pendingAfterTrigger					INTEGER (1..512)
}

QualityReportingQuantity ::=		SEQUENCE {
	dl-TransChBLER						BOOLEAN,
	bler-dl-TransChIdList				BLER-TransChIdList					OPTIONAL,
	modeSpecificInfo					CHOICE {
		fdd									NULL,
		tdd									SEQUENCE {
			sir-TFCS-List						SIR-TFCS-List				OPTIONAL
		}
	}
}

RAT-Type ::=						ENUMERATED {
										gsm, is2000 }

ReferenceCellPosition ::=			CHOICE {
	ellipsoidPoint						EllipsoidPoint,
	ellipsoidPointWithAltitude			EllipsoidPointAltitude
}

-- ReferenceLocation, as defined in 23.032
ReferenceLocation ::=			SEQUENCE {
	ellipsoidPointAltitudeEllipsoide		EllipsoidPointAltitudeEllipsoide
}

ReferenceLocationGANSS ::=			SEQUENCE {
	ellipsoidPointAltitudeEllipsoide	EllipsoidPointAltitudeEllipsoide
}

ReferenceTimeDifferenceToCell ::= 	CHOICE {
	-- Actual value accuracy40 = IE value * 40
	accuracy40							INTEGER (0..960),
	-- Actual value accuracy256 = IE value * 256
	accuracy256							INTEGER (0..150),
	-- Actual value accuracy2560 = IE value * 2560
	accuracy2560						INTEGER (0..15)
}

RemovedInterFreqCellList ::=		CHOICE {
	removeAllInterFreqCells				NULL,
	removeSomeInterFreqCells			SEQUENCE (SIZE (1..maxCellMeas)) OF
											InterFreqCellID,
	removeNoInterFreqCells				NULL
}

RemovedInterFreqCellList-r12 ::=		CHOICE {
	removeAllInterFreqCells				NULL,
	removeSomeInterFreqCells			SEQUENCE (SIZE (1..maxCellMeas-ext)) OF
											InterFreqCellID-r12,
	removeNoInterFreqCells				NULL
}

RemovedInterRATCellList ::=		CHOICE {
	removeAllInterRATCells			NULL,
	removeSomeInterRATCells			SEQUENCE (SIZE (1..maxCellMeas)) OF
											InterRATCellID,
	removeNoInterRATCells			NULL
}

RemovedIntraFreqCellList ::=		CHOICE {
	removeAllIntraFreqCells				NULL,
	removeSomeIntraFreqCells			SEQUENCE (SIZE (1..maxCellMeas)) OF
											IntraFreqCellID,
	removeNoIntraFreqCells				NULL
}

RemovedIntraFreqCellListOnSecULFreq ::=		CHOICE {
	removeAllIntraFreqCells				NULL,
	removeSomeIntraFreqCells			SEQUENCE (SIZE (1..maxCellMeasOnSecULFreq)) OF
											IntraFreqCellIDOnSecULFreq,
	removeNoIntraFreqCells				NULL
}

ReplacementActivationThreshold ::= 	ENUMERATED {
										notApplicable, t1, t2,
										t3, t4, t5, t6, t7 }

ReportDeactivationThreshold ::=		ENUMERATED {
										notApplicable, t1, t2,
										t3, t4, t5, t6, t7 }

ReportingAmount ::=					ENUMERATED {
										ra1, ra2, ra4, ra8, ra16, ra32,
										ra64, ra-Infinity }

ReportingCellStatus ::=				CHOICE{
	withinActiveSet						MaxNumberOfReportingCellsType1,
	withinMonitoredSetUsedFreq			MaxNumberOfReportingCellsType1,
	withinActiveAndOrMonitoredUsedFreq	MaxNumberOfReportingCellsType1,
	withinDetectedSetUsedFreq			MaxNumberOfReportingCellsType1,
	withinMonitoredAndOrDetectedUsedFreq
										MaxNumberOfReportingCellsType1,
	allActiveplusMonitoredSet			MaxNumberOfReportingCellsType3,
	allActivePlusDetectedSet			MaxNumberOfReportingCellsType3,
	allActivePlusMonitoredAndOrDetectedSet
										MaxNumberOfReportingCellsType3,
	withinVirtualActSet				MaxNumberOfReportingCellsType1,
	withinMonitoredSetNonUsedFreq		MaxNumberOfReportingCellsType1,
	withinMonitoredAndOrVirtualActiveSetNonUsedFreq
										MaxNumberOfReportingCellsType1,
	allVirtualActSetplusMonitoredSetNonUsedFreq
										MaxNumberOfReportingCellsType3,
	withinActSetOrVirtualActSet-InterRATcells
										MaxNumberOfReportingCellsType2,
	withinActSetAndOrMonitoredUsedFreqOrVirtualActSetAndOrMonitoredNonUsedFreq
										MaxNumberOfReportingCellsType2
}

ReportingCellStatus-r10 ::=				CHOICE{
	withinActiveSet						MaxNumberOfReportingCellsType1,
	withinMonitoredSetUsedFreq			MaxNumberOfReportingCellsType1,
	withinActiveAndOrMonitoredUsedFreq	MaxNumberOfReportingCellsType1,
	withinDetectedSetUsedFreq			MaxNumberOfReportingCellsType1,
	withinMonitoredAndOrDetectedUsedFreq
										MaxNumberOfReportingCellsType1,
	allActiveplusMonitoredSet			MaxNumberOfReportingCellsType3,
	allActivePlusDetectedSet			MaxNumberOfReportingCellsType3,
	allActivePlusMonitoredAndOrDetectedSet
										MaxNumberOfReportingCellsType3,
	withinVirtualActSet				MaxNumberOfReportingCellsType1,
	withinMonitoredSetNonUsedFreq		MaxNumberOfReportingCellsType1,
	withinMonitoredAndOrVirtualActiveSetNonUsedFreq
										MaxNumberOfReportingCellsType1,
	allVirtualActSetplusMonitoredSetNonUsedFreq
										MaxNumberOfReportingCellsType3,
	withinActSetOrVirtualActSet-InterRATcells
										MaxNumberOfReportingCellsType2,
	withinActSetAndOrMonitoredUsedFreqOrVirtualActSetAndOrMonitoredNonUsedFreq
										MaxNumberOfReportingCellsType2,
	allVirtualActSetplusMonitoredSetplusDetectedSetNonUsedFreq
										MaxNumberOfReportingCellsType3
}

ReportingCellStatusOpt ::=			SEQUENCE {
	reportingCellStatus					ReportingCellStatus					OPTIONAL
}

ReportingCellStatusOpt-r10 ::=		SEQUENCE {
	reportingCellStatus					ReportingCellStatus-r10			OPTIONAL
}

ReportingInfoForCellDCH ::=			SEQUENCE {
	intraFreqReportingQuantity			IntraFreqReportingQuantity,
	measurementReportingMode			MeasurementReportingMode,
	reportCriteria						CellDCH-ReportCriteria
}

ReportingInfoForCellDCH-LCR-r4 ::=	SEQUENCE {
	intraFreqReportingQuantity			IntraFreqReportingQuantity,
	measurementReportingMode			MeasurementReportingMode,
	reportCriteria						CellDCH-ReportCriteria-LCR-r4
}

ReportingInterval ::=				ENUMERATED {
										noPeriodicalreporting, ri0-25,
										ri0-5, ri1, ri2, ri4, ri8, ri16 }

ReportingIntervalLong ::=			ENUMERATED {
										ril0, ril0-25, ril0-5, ril1,
										ril2, ril3, ril4, ril6, ril8,
										ril12, ril16, ril20, ril24,
										ril28, ril32, ril64 }
									-- When the value "ril0" is used, the UE behaviour is not
									-- defined.

-- Actual value ReportingRange = IE value * 0.5
ReportingRange ::=					INTEGER (0..29)

ReqDataBitAssistance ::=			SEQUENCE {
	ganssSignalID						DGANSS-Sig-Id-Req,
	ganssDataBitInterval				INTEGER(0..15),
	ganssSatelliteInfo					SEQUENCE (SIZE (1..maxGANSSSat)) OF INTEGER(0..63) OPTIONAL
}

RL-AdditionInfoList ::=				SEQUENCE (SIZE (1..maxRL)) OF
										PrimaryCPICH-Info

RL-InformationLists ::=				SEQUENCE {
	rl-AdditionInfoList					RL-AdditionInfoList					OPTIONAL,
	rL-RemovalInformationList			RL-RemovalInformationList			OPTIONAL
}

RLC-BuffersPayload ::=				ENUMERATED {
										pl0, pl4, pl8, pl16, pl32,
										pl64, pl128, pl256, pl512, pl1024,
										pl2k, pl4k, pl8k, pl16k, pl32k,
										pl64k, pl128k, pl256k, pl512k, pl1024k,
										spare12, spare11, spare10, spare9, spare8,
										spare7, spare6, spare5, spare4, spare3,
										spare2, spare1 }


RMP-Frequency-List ::=				SEQUENCE (SIZE (1..maxRMPfrequencies)) OF
										BOOLEAN

-- Actual value RRC = IE value * 0.032
RRC ::=								INTEGER (-127..127)

RSCPforANR ::= SEQUENCE {
	rSCP 								INTEGER (-120..-25)					OPTIONAL
}

RsrqType ::= 						SEQUENCE{
	allSymbols							BOOLEAN,
	wideBand							BOOLEAN
}


SatData ::=							SEQUENCE{
	satID								SatID,
	iode								IODE
}

SatDataList ::=						SEQUENCE (SIZE (0..maxSat)) OF
										SatData

SatellitesListRelatedData ::=		SEQUENCE {
	satId								INTEGER (0..63),
	iod									INTEGER (0..1023)
}

SatellitesListRelatedDataList ::=	SEQUENCE (SIZE (1..maxGANSSSat)) OF
										SatellitesListRelatedData

SatelliteStatus ::=					ENUMERATED {
										ns-NN-U,
										es-SN,
										es-NN-U,
										rev2,
										rev }

Satellite-clock-model ::=			SEQUENCE {
	t-oc								BIT STRING (SIZE (14)),
	af2									BIT STRING (SIZE (6)),
	af1									BIT STRING (SIZE (21)),
	af0									BIT STRING (SIZE (31)),
	tgd									BIT STRING (SIZE (10))				OPTIONAL,
	sisa								BIT STRING (SIZE (8)),
	model-id							INTEGER (0..1) 						OPTIONAL
}

Satellite-clock-modelList ::=		SEQUENCE (SIZE (1..maxSatClockModels)) OF Satellite-clock-model

-- Identifies the satellite and is equal to (SV ID No - 1) where SV ID No is defined in [12].
SatID ::=							INTEGER (0..63)

SBASclockModel ::=					SEQUENCE {
	sbasTo								BIT STRING (SIZE (13)),
	sbasAgfo							BIT STRING (SIZE (12)),
	sbasAgf1							BIT STRING (SIZE (8))
}

S-DPCCH-Information ::=		SEQUENCE {
	s-DPCCH-DPCCH-PowerOffset				S-DPCCH-DPCCH-PowerOffset
}

S-DPCCH-DPCCH-PowerOffset ::=		INTEGER (0..6)

SFN-Offset-Validity ::=			ENUMERATED { false }

SFN-SFN-Drift ::= 					ENUMERATED {
										sfnsfndrift0, sfnsfndrift1, sfnsfndrift2,
										sfnsfndrift3, sfnsfndrift4, sfnsfndrift5,
										sfnsfndrift8, sfnsfndrift10, sfnsfndrift15,
										sfnsfndrift25, sfnsfndrift35, sfnsfndrift50,
										sfnsfndrift65, sfnsfndrift80, sfnsfndrift100,
										sfnsfndrift-1, sfnsfndrift-2, sfnsfndrift-3,
										sfnsfndrift-4, sfnsfndrift-5, sfnsfndrift-8,
										sfnsfndrift-10, sfnsfndrift-15, sfnsfndrift-25,
										sfnsfndrift-35, sfnsfndrift-50, sfnsfndrift-65,
										sfnsfndrift-80, sfnsfndrift-100}

SFN-SFN-ObsTimeDifference ::=		CHOICE {
	type1								SFN-SFN-ObsTimeDifference1,
	type2								SFN-SFN-ObsTimeDifference2
}

-- SPARE: SFN-SFN-ObsTimeDifference1, Max = 9830399
-- For 1.28Mcps TDD, Max value of SFN-SFN-ObsTimeDifference1 is 3276799.
-- Values above Max are spare
SFN-SFN-ObsTimeDifference1 ::=		INTEGER (0..16777215)

-- SPARE: SFN-SFN-ObsTimeDifference2, Max = 40961
-- For 1.28Mcps TDD, Max value of SFN-SFN-ObsTimeDifference2 is 27649.
-- Values above Max are spare
SFN-SFN-ObsTimeDifference2 ::=		INTEGER (0..65535)

SFN-SFN-OTD-Type ::=				ENUMERATED {
										noReport,
										type1,
										type2 }

SFN-SFN-RelTimeDifference1 ::=		SEQUENCE {
	sfn-Offset							INTEGER (0 .. 4095),
	sfn-sfn-Reltimedifference			INTEGER (0.. 38399)
}

SFN-TOW-Uncertainty ::=				ENUMERATED {
										lessThan10,
										moreThan10 }


SIR ::=								INTEGER (0..63)


SIR-MeasurementList ::=				SEQUENCE (SIZE (1..maxCCTrCH)) OF
										SIR-MeasurementResults


SIR-MeasurementResults ::=			SEQUENCE {
	tfcs-ID								TFCS-IdentityPlain,
	sir-TimeslotList					SIR-TimeslotList
}

SIR-TFCS ::=						TFCS-IdentityPlain


SIR-TFCS-List ::=					SEQUENCE (SIZE (1..maxCCTrCH)) OF
										SIR-TFCS

SIR-TimeslotList ::=				SEQUENCE (SIZE (1..maxTS)) OF
										SIR

-- SubFrame1Reserved, reserved bits in subframe 1 of the GPS navigation message
SubFrame1Reserved ::= 				SEQUENCE {
 	reserved1							BIT STRING (SIZE (23)),
	reserved2							BIT STRING (SIZE (24)),
	reserved3							BIT STRING (SIZE (24)),
	reserved4							BIT STRING (SIZE (16))
}

T-ADVinfo ::=						SEQUENCE {
				t-ADV					INTEGER(0..2047),
				sfn						INTEGER(0..4095)
}

T-ADVinfo-ext ::=					SEQUENCE {
	t-ADV								INTEGER (0..8191),
	sfn									INTEGER (0..4095)
}

T-CRMax ::=							CHOICE {
	notUsed								NULL,
	t30									N-CR-T-CRMaxHyst,
	t60									N-CR-T-CRMaxHyst,
	t120								N-CR-T-CRMaxHyst,
	t180								N-CR-T-CRMaxHyst,
	t240								N-CR-T-CRMaxHyst
}

T-CRMaxHyst ::=						ENUMERATED {
										notUsed, t10, t20, t30,
										t40, t50, t60, t70 }

TCE-Id ::=			SEQUENCE {
	tce-Id				OCTET STRING (SIZE (1))
}

TemporaryOffset1 ::=				ENUMERATED {
										to3, to6, to9, to12, to15,
										to18, to21, infinite }

TemporaryOffset2 ::=				ENUMERATED {
										to2, to3, to4, to6, to8,
										to10, to12, infinite }

TemporaryOffsetList ::=				SEQUENCE 	{
		temporaryOffset1 				TemporaryOffset1,
		temporaryOffset2 				TemporaryOffset2
}

Threshold ::=						INTEGER (-115..0)

Threshold-r12 ::=					INTEGER (-115..6)

Threshold-r6 ::=							INTEGER (-120..0)

-- The order of the list corresponds to the order of frequency defined in Inter-FreqEventCriteria
ThreholdNonUsedFrequency-deltaList ::= SEQUENCE (SIZE (1..maxFreq)) OF
											DeltaRSCPPerCell

ThresholdPositionChange ::=			ENUMERATED {
										pc10, pc20, pc30, pc40, pc50,
										pc100, pc200, pc300, pc500,
										pc1000, pc2000, pc5000, pc10000,
										pc20000, pc50000, pc100000 }

ThresholdSFN-GANSS-TOW ::=			ENUMERATED {
										us1, us2, us3, us5, us10,
										us20, us50, us100 }

ThresholdSFN-GPS-TOW ::=			ENUMERATED {
										ms1, ms2, ms3, ms5, ms10,
										ms20, ms50, ms100 }

ThresholdSFN-GPS-TOW-us ::=			ENUMERATED {
										us1, us2, us3, us5, us10,
										us20, us50, us100 }

ThresholdSFN-SFN-Change ::=			ENUMERATED {
										c0-25, c0-5, c1, c2, c3, c4, c5,
										c10, c20, c50, c100, c200, c500,
										c1000, c2000, c5000 }

ThresholdUsedFrequency ::=			INTEGER (-115..165)

ThresholdUsedFrequency-r6 ::=		INTEGER (-120..165)

-- Actual value TimeInterval = IE value * 20.
TimeInterval ::=					INTEGER (1..13)


TimeslotInfo ::=					SEQUENCE {
	timeslotNumber						TimeslotNumber,
	burstType							BurstType
}

TimeslotInfo-LCR-r4 ::=				SEQUENCE {
	timeslotNumber						TimeslotNumber-LCR-r4
}

TimeslotInfoList ::=				SEQUENCE (SIZE (1..maxTS)) OF
										TimeslotInfo

TimeslotInfoList-LCR-r4 ::=			SEQUENCE (SIZE (1..maxTS-LCR)) OF
										TimeslotInfo-LCR-r4

TimeslotInfoList-r4 ::=				CHOICE {
	-- the choice for 7.68 Mcps TDD is the same as for 3.84 Mcps TDD --
	tdd384								SEQUENCE (SIZE (1..maxTS)) OF
											TimeslotInfo,
	tdd128								SEQUENCE (SIZE (1..maxTS-LCR)) OF
											TimeslotInfo-LCR-r4
}

-- SPARE: TimeslotISCP, Max = 91
-- Values above Max are spare
TimeslotISCP ::=					INTEGER (0..127)


-- TimeslotISCP-List shall not include more than 6 elements in 1.28Mcps TDD mode.
TimeslotISCP-List ::=				SEQUENCE (SIZE (1..maxTS)) OF
										TimeslotISCP

TimeslotListWithISCP ::=			SEQUENCE (SIZE (1..maxTS)) OF
										TimeslotWithISCP

TimeslotWithISCP ::=				SEQUENCE {
	timeslot							TimeslotNumber,
	timeslotISCP						TimeslotISCP
}

TimeToTrigger ::=					ENUMERATED {
										ttt0, ttt10, ttt20, ttt40, ttt60,
										ttt80, ttt100, ttt120, ttt160,
										ttt200, ttt240, tt320, ttt640,
										ttt1280, ttt2560, ttt5000 }

TraceReference ::=					SEQUENCE {
	plmn-Identity						PLMN-Identity,
	traceId								OCTET STRING (SIZE (3))
}

TraceRecordingSession ::=			SEQUENCE {
	traceRecordingSession				OCTET STRING (SIZE (2))
}

TrafficVolumeEventParam ::=			SEQUENCE {
	eventID								TrafficVolumeEventType,
	reportingThreshold					TrafficVolumeThreshold,
	timeToTrigger						TimeToTrigger						OPTIONAL,
	pendingTimeAfterTrigger				PendingTimeAfterTrigger				OPTIONAL,
	tx-InterruptionAfterTrigger			TX-InterruptionAfterTrigger			OPTIONAL
}

TrafficVolumeEventResults ::=		SEQUENCE {
	ul-transportChannelCausingEvent		UL-TrCH-Identity,
	trafficVolumeEventIdentity			TrafficVolumeEventType
}

TrafficVolumeEventType ::=			ENUMERATED {
										e4a,
										e4b }

TrafficVolumeMeasQuantity ::=		CHOICE {
	rlc-BufferPayload					NULL,
	averageRLC-BufferPayload			TimeInterval,
	varianceOfRLC-BufferPayload			TimeInterval
}

TrafficVolumeMeasSysInfo ::=		SEQUENCE {
	trafficVolumeMeasurementID			MeasurementIdentity			DEFAULT 4,
	trafficVolumeMeasurementObjectList	TrafficVolumeMeasurementObjectList	OPTIONAL,
	trafficVolumeMeasQuantity			TrafficVolumeMeasQuantity			OPTIONAL,
	trafficVolumeReportingQuantity		TrafficVolumeReportingQuantity		OPTIONAL,
	-- dummy is not used in this version of specification, it should
	-- not be sent and if received it should be ignored.
	dummy								TrafficVolumeReportingCriteria		OPTIONAL,
	measurementValidity					MeasurementValidity					OPTIONAL,
	measurementReportingMode			MeasurementReportingMode,
	reportCriteriaSysInf				TrafficVolumeReportCriteriaSysInfo

}

TrafficVolumeMeasuredResults ::=	SEQUENCE {
	rb-Identity							RB-Identity,
	rlc-BuffersPayload					RLC-BuffersPayload					OPTIONAL,
	averageRLC-BufferPayload			AverageRLC-BufferPayload			OPTIONAL,
	varianceOfRLC-BufferPayload			VarianceOfRLC-BufferPayload			OPTIONAL
}

TrafficVolumeMeasuredResultsList ::= SEQUENCE (SIZE (1..maxRB)) OF
										TrafficVolumeMeasuredResults

TrafficVolumeMeasurement ::= 		SEQUENCE {
	trafficVolumeMeasurementObjectList	TrafficVolumeMeasurementObjectList	OPTIONAL,
	trafficVolumeMeasQuantity			TrafficVolumeMeasQuantity			OPTIONAL,
	trafficVolumeReportingQuantity		TrafficVolumeReportingQuantity		OPTIONAL,
	measurementValidity					MeasurementValidity					OPTIONAL,
	reportCriteria						TrafficVolumeReportCriteria
}

TrafficVolumeMeasurementObjectList ::= SEQUENCE (SIZE (1..maxTrCH)) OF
											UL-TrCH-Identity

TrafficVolumeReportCriteria ::=		CHOICE {
	trafficVolumeReportingCriteria		TrafficVolumeReportingCriteria,
	periodicalReportingCriteria			PeriodicalReportingCriteria,
	noReporting							NULL
}

TrafficVolumeReportCriteriaSysInfo ::=	CHOICE {
	trafficVolumeReportingCriteria		TrafficVolumeReportingCriteria,
	periodicalReportingCriteria			PeriodicalReportingCriteria
}

TrafficVolumeReportingCriteria ::= SEQUENCE {
	-- NOTE: transChCriteriaList should be mandatory in later versions of this message
	transChCriteriaList					TransChCriteriaList					OPTIONAL
}

TrafficVolumeReportingQuantity ::= SEQUENCE {
	rlc-RB-BufferPayload				BOOLEAN,
	rlc-RB-BufferPayloadAverage			BOOLEAN,
	rlc-RB-BufferPayloadVariance		BOOLEAN
}

TrafficVolumeThreshold ::=			ENUMERATED {
										th8, th16, th32, th64, th128,
										th256, th512, th1024, th2k, th3k,
										th4k, th6k, th8k, th12k, th16k,
										th24k, th32k, th48k, th64k, th96k,
										th128k, th192k, th256k, th384k,
										th512k, th768k }

TransChCriteria ::=					SEQUENCE {
	ul-transportChannelID				UL-TrCH-Identity					OPTIONAL,
	eventSpecificParameters				SEQUENCE (SIZE (1..maxMeasParEvent)) OF
											TrafficVolumeEventParam			OPTIONAL
}

TransChCriteriaList ::=			SEQUENCE (SIZE (1..maxTrCH)) OF
										TransChCriteria

TransferMode ::=					ENUMERATED {
										acknowledgedModeRLC,
										unacknowledgedModeRLC }

TransmittedPowerThreshold ::=		INTEGER (-50..33)

TriggeringCondition1 ::=			ENUMERATED {
										activeSetCellsOnly,
										monitoredSetCellsOnly,
										activeSetAndMonitoredSetCells }

TriggeringCondition2 ::=			ENUMERATED {
										activeSetCellsOnly,
										monitoredSetCellsOnly,
										activeSetAndMonitoredSetCells,
										detectedSetCellsOnly,
										detectedSetAndMonitoredSetCells }

Tutran-Ganss-DriftRate ::=			ENUMERATED {
										ugdr0, ugdr1, ugdr2, ugdr5, ugdr10, ugdr15 , ugdr25,
										ugdr50, ugdr-1, ugdr-2, ugdr-5, ugdr-10, ugdr-15,
										ugdr-25, ugdr-50, spare }

TX-InterruptionAfterTrigger ::=		ENUMERATED {
										txiat0-25, txiat0-5, txiat1,
										txiat2, txiat4, txiat8, txiat16 }

UDRE ::=							ENUMERATED {
										lessThan1,
										between1-and-4,
										between4-and-8,
										over8 }

UDREGrowthRate ::=					ENUMERATED {
										growth-1-5,
										growth-2,
										growth-4,
										growth-6,
										growth-8,
										growth-10,
										growth-12,
										growth-16 }

UDREValidityTime	::=					ENUMERATED {
											val-20sec,
											val-40sec,
											val-80sec,
											val-160sec,
											val-320sec,
											val-640sec,
											val-1280sec,
											val-2560sec }

UE-6AB-Event ::=					SEQUENCE {
	timeToTrigger						TimeToTrigger,
	transmittedPowerThreshold			TransmittedPowerThreshold
}

UE-6FG-Event ::=					SEQUENCE {
	timeToTrigger						TimeToTrigger,
	-- in 1.28 Mcps TDD ue-RX-TX-TimeDifferenceThreshold corresponds to TADV Threshold
	ue-RX-TX-TimeDifferenceThreshold	UE-RX-TX-TimeDifferenceThreshold
}

UE-6HI-Event ::=					SEQUENCE {
	timeToTrigger						TimeToTrigger,
	hysteresis							Hysteresis,
	ue-powerheadroomthreshold			UE-PowerHeadroomThreshold,
	filtercoefficient					FilterCoefficient,
	pendingtimeaftertrigger				PendingTimeAfterTrigger			OPTIONAL
}

-- dummy and dummy2 are not used in this version of the specification, they should
-- not be sent and if received the UE behaviour is not specified.
UE-AutonomousUpdateMode ::=			CHOICE {
	dummy								NULL,
	onWithNoReporting					NULL,
	dummy2								RL-InformationLists
}

UE-InternalEventParam ::=			CHOICE {
	event6a								UE-6AB-Event,
	event6b								UE-6AB-Event,
	event6c								TimeToTrigger,
	event6d								TimeToTrigger,
	event6e								TimeToTrigger,
	event6f								UE-6FG-Event,
	event6g								UE-6FG-Event
}

UE-InternalEventParam-r14::=		CHOICE {
	event6a								UE-6AB-Event,
	event6b								UE-6AB-Event,
	event6c								TimeToTrigger,
	event6d								TimeToTrigger,
	event6e								TimeToTrigger,
	event6f								UE-6FG-Event,
	event6g								UE-6FG-Event,
	event6h								UE-6HI-Event,
	event6i								UE-6HI-Event,
	spare7								NULL,
	spare6								NULL,
	spare5								NULL,
	spare4								NULL,
	spare3								NULL,
	spare2								NULL,
	spare1								NULL
}


UE-InternalEventParamList ::=		SEQUENCE (SIZE (1..maxMeasEvent)) OF
										UE-InternalEventParam

UE-InternalEventParamList-r14 ::=	SEQUENCE (SIZE (1..maxMeasEvent)) OF
										UE-InternalEventParam-r14

UE-InternalEventResults ::=			CHOICE {
	event6a								NULL,
	event6b								NULL,
	event6c								NULL,
	event6d								NULL,
	event6e								NULL,
	event6f								PrimaryCPICH-Info,
	event6g								PrimaryCPICH-Info,
	ue-InternalEventResults-v30ext				UE-InternalEventResults-v30ext-IEs
}

UE-InternalEventResults-v30ext-IEs ::=	CHOICE {
	event6h								NULL,
	event6i								NULL,
	spare6								NULL,
	spare5								NULL,
	spare4								NULL,
	spare3								NULL,
    spare2								NULL,
	spare1								NULL
}

UE-InternalMeasQuantity ::=			SEQUENCE {
	measurementQuantity					UE-MeasurementQuantity,
	filterCoefficient					FilterCoefficient					DEFAULT fc0
}

UE-InternalMeasQuantity-r14 ::=		SEQUENCE {
	measurementQuantity					UE-MeasurementQuantity-r14,
	filterCoefficient					FilterCoefficient					DEFAULT fc0
}

UE-InternalMeasuredResults ::=		SEQUENCE {
	modeSpecificInfo					CHOICE {
		fdd									SEQUENCE {
			ue-TransmittedPowerFDD				UE-TransmittedPower			OPTIONAL,
			ue-RX-TX-ReportEntryList			UE-RX-TX-ReportEntryList	OPTIONAL
		},
		tdd									SEQUENCE {
			ue-TransmittedPowerTDD-List			UE-TransmittedPowerTDD-List	OPTIONAL,
			appliedTA							UL-TimingAdvance			OPTIONAL
		}
	}
}

UE-InternalMeasuredResults-ve30ext ::=	SEQUENCE {
	modeSpecificInfo					CHOICE {
		fdd									SEQUENCE {
			ue-powerheadroom					UE-PowerHeadroom			OPTIONAL
		},
		tdd								NULL
	}
}

UE-InternalMeasuredResults-LCR-r4 ::=	SEQUENCE {
		ue-TransmittedPowerTDD-List			UE-TransmittedPowerTDD-List		OPTIONAL,
		-- If TA value is not greater than 2047, then use this IE to report.
		t-ADVinfo							T-ADVinfo						OPTIONAL
}

UE-InternalMeasuredResults-v770ext ::= SEQUENCE {
	modeSpecificInfo					CHOICE {
		tdd384-768							SEQUENCE {
			appliedTA							EXT-UL-TimingAdvance		OPTIONAL
		},
		tdd128								SEQUENCE {
			-- If TA value is greater than 2047, then use this IE to report
			t-ADVinfo							T-ADVinfo-ext				OPTIONAL
		}
	}
}

UE-InternalMeasurement ::=			SEQUENCE {
	ue-InternalMeasQuantity				UE-InternalMeasQuantity				OPTIONAL,
	ue-InternalReportingQuantity		UE-InternalReportingQuantity		OPTIONAL,
	reportCriteria						UE-InternalReportCriteria
}

UE-InternalMeasurement-r4 ::=		SEQUENCE {
	ue-InternalMeasQuantity				UE-InternalMeasQuantity				OPTIONAL,
	ue-InternalReportingQuantity		UE-InternalReportingQuantity-r4		OPTIONAL,
	reportCriteria						UE-InternalReportCriteria
}

UE-InternalMeasurement-r14 ::=		SEQUENCE {
	ue-InternalMeasQuantity				UE-InternalMeasQuantity-r14			OPTIONAL,
	ue-InternalReportingQuantity		UE-InternalReportingQuantity-r14	OPTIONAL,
	reportCriteria						UE-InternalReportCriteria-r14
}

UE-InternalMeasurementSysInfo ::= 	SEQUENCE {
	ue-InternalMeasurementID			MeasurementIdentity			DEFAULT 5,
	ue-InternalMeasQuantity				UE-InternalMeasQuantity
}

UE-InternalReportCriteria ::=		CHOICE {
	ue-InternalReportingCriteria		UE-InternalReportingCriteria,
	periodicalReportingCriteria			PeriodicalReportingCriteria,
	noReporting							NULL
}

UE-InternalReportCriteria-r14 ::=	CHOICE {
	ue-InternalReportingCriteria		UE-InternalReportingCriteria-r14,
	periodicalReportingCriteria			PeriodicalReportingCriteria,
	noReporting							NULL
}

UE-InternalReportingCriteria ::=	SEQUENCE {
	ue-InternalEventParamList			UE-InternalEventParamList			OPTIONAL
}

UE-InternalReportingCriteria-r14 ::=	SEQUENCE {
	ue-InternalEventParamList				UE-InternalEventParamList-r14			OPTIONAL
}

UE-InternalReportingQuantity ::=	SEQUENCE {
	ue-TransmittedPower					BOOLEAN,
	modeSpecificInfo					CHOICE {
		fdd									SEQUENCE {
			ue-RX-TX-TimeDifference				BOOLEAN
		},
		tdd									SEQUENCE {
			appliedTA							BOOLEAN
		}
	}
}

UE-InternalReportingQuantity-r4 ::=	SEQUENCE {
	ue-TransmittedPower					BOOLEAN,
	modeSpecificInfo					CHOICE {
		fdd									SEQUENCE {
			ue-RX-TX-TimeDifference				BOOLEAN
		},
		tdd									SEQUENCE {
			tddOption							CHOICE {
			-- appliedTA applies to both 3.84 Mcps TDD and to 7.68 Mcps TDD.
			-- Therefore, no additional choice of TDD mode is necessary
				tdd384								SEQUENCE {
					appliedTA							BOOLEAN
				},
				tdd128								SEQUENCE {
					t-ADVinfo							BOOLEAN
				}
			}
		}
	}
}

UE-InternalReportingQuantity-r14 ::=	SEQUENCE {
	ue-TransmittedPower					BOOLEAN,
	modeSpecificInfo					CHOICE {
		fdd									SEQUENCE {
			ue-RX-TX-TimeDifference				BOOLEAN,
			ue-powerheadroom					BOOLEAN
		},
		tdd									SEQUENCE {
			tddOption							CHOICE {
			-- appliedTA applies to both 3.84 Mcps TDD and to 7.68 Mcps TDD.
			-- Therefore, no additional choice of TDD mode is necessary
				tdd384								SEQUENCE {
					appliedTA							BOOLEAN
				},
				tdd128								SEQUENCE {
					t-ADVinfo							BOOLEAN
				}
			}
		}
	}
}

-- TABULAR: UE-MeasurementQuantity, for 3.84 Mcps TDD only the first two values
-- ue-TransmittedPower and utra-Carrier-RSSI are used.
-- For 1.28 Mcps TDD ue-RX-TX-TimeDifference corresponds to T-ADV in the tabular
UE-MeasurementQuantity ::=			ENUMERATED {
										ue-TransmittedPower,
										utra-Carrier-RSSI,
										ue-RX-TX-TimeDifference }

UE-MeasurementQuantity-r14 ::=		ENUMERATED {
										ue-TransmittedPower,
										utra-Carrier-RSSI,
										ue-RX-TX-TimeDifference,
										ue-powerheadroom }

UE-PowerHeadroom ::=				INTEGER (0..31)

UE-PowerHeadroomThreshold ::=		INTEGER (-50..33)

UE-RX-TX-ReportEntry ::=			SEQUENCE {
	primaryCPICH-Info					PrimaryCPICH-Info,
	ue-RX-TX-TimeDifferenceType1		UE-RX-TX-TimeDifferenceType1
}

UE-RX-TX-ReportEntryList ::=		SEQUENCE (SIZE (1..maxRL)) OF
										UE-RX-TX-ReportEntry

-- SPARE: UE-RX-TX-TimeDifferenceType1, Max = 1280
-- Values above Max are spare
UE-RX-TX-TimeDifferenceType1 ::=			INTEGER (768..1791)


UE-RX-TX-TimeDifferenceType2 ::=	INTEGER (0..8191)

UE-RX-TX-TimeDifferenceType2Info ::=	SEQUENCE {
	ue-RX-TX-TimeDifferenceType2			UE-RX-TX-TimeDifferenceType2,
	neighbourQuality						NeighbourQuality
}

-- In 1.28 Mcps TDD, actual value for
-- T-ADV Threshold = (UE-RX-TX-TimeDifferenceThreshold - 768) * 0.125
UE-RX-TX-TimeDifferenceThreshold ::= INTEGER (768..1280)

UE-TransmittedPower ::=				INTEGER (0..104)

UE-TransmittedPowerTDD-List ::=		SEQUENCE (SIZE (1..maxTS)) OF
										UE-TransmittedPower

UL-TrCH-Identity ::=					CHOICE{
	dch									TransportChannelIdentity,
	-- Note: the reference to CPCH in the element name below is incorrect. The name is not changed
	-- to keep it aligned with R99.
	rachorcpch							NULL,
	usch								TransportChannelIdentity
}

UE-Positioning-Accuracy ::=					BIT STRING (SIZE (7))

UE-Positioning-DBDSCorrections ::= SEQUENCE {
	bds-RefTime				INTEGER (0..119),
	bds-DBDS-InfoList		DBDS-InfoList
}

UE-Positioning-CipherParameters ::=			SEQUENCE {
	cipheringKeyFlag					BIT STRING (SIZE (1)),
	cipheringSerialNumber				INTEGER (0..65535)
}

UE-Positioning-DGANSSCorrections ::= SEQUENCE {
	dganssreferencetime					INTEGER (0..119),			-- scale factor 30s
	dganssInfoList						DGANSSInfoList
}

UE-Positioning-DGANSSCorrections-r9 ::= SEQUENCE {
	dganssreferencetime					INTEGER (0..119),			-- scale factor 30s
	dganssInfoList						DGANSSInfoList-r9
}

UE-Positioning-DGANSSCorrections-v920ext ::= SEQUENCE {
	dganssInfoList						DGANSSInfoList-v920ext
}

UE-Positioning-Error ::=			SEQUENCE {
	errorReason							UE-Positioning-ErrorCause,
	ue-positioning-GPS-additionalAssistanceDataRequest
										UE-Positioning-GPS-AdditionalAssistanceDataRequest	OPTIONAL
}

UE-Positioning-Error-r7 ::=			SEQUENCE {
	errorReason							UE-Positioning-ErrorCause-r7,
	ue-positioning-GPS-additionalAssistanceDataRequest
								UE-Positioning-GPS-AdditionalAssistanceDataRequest		OPTIONAL,
	ue-positioning-GANSS-additionalAssistanceDataRequest
								UE-Positioning-GANSS-AdditionalAssistanceDataRequest	OPTIONAL
}

UE-Positioning-Error-v860ext ::=	SEQUENCE {
	ue-positioning-GANSS-additionalAssistanceDataRequest
						UE-Positioning-GANSS-AdditionalAssistanceDataRequest-v860ext	OPTIONAL
}

UE-Positioning-Error-vc50ext ::=	SEQUENCE {
	ue-positioning-GANSS-additionalAssistanceDataRequest
						UE-Positioning-GANSS-AdditionalAssistanceDataRequest-vc50ext	OPTIONAL
}

UE-Positioning-ErrorCause ::=		ENUMERATED {
										notEnoughOTDOA-Cells,
										notEnoughGPS-Satellites,
										assistanceDataMissing,
										notAccomplishedGPS-TimingOfCellFrames,
										undefinedError,
										requestDeniedByUser,
										notProcessedAndTimeout,
										referenceCellNotServingCell }

UE-Positioning-ErrorCause-r7 ::=	ENUMERATED {
										notEnoughOTDOA-Cells,
										notEnoughGPS-Satellites,
										assistanceDataMissing,
										notAccomplishedGPS-TimingOfCellFrames,
										undefinedError,
										requestDeniedByUser,
										notProcessedAndTimeout,
										referenceCellNotServingCell,
										notEnoughGANSS-Satellites,
										notAccomplishedGANSS-TimingOfCellFrames,
										spare6, spare5, spare4, spare3, spare2, spare1 }

UE-Positioning-EventParam ::=					SEQUENCE {
	reportingAmount						ReportingAmount,
	reportFirstFix						BOOLEAN,
	measurementInterval					UE-Positioning-MeasurementInterval,
	eventSpecificInfo					UE-Positioning-EventSpecificInfo
}

UE-Positioning-EventParam-r7 ::=	SEQUENCE {
	reportingAmount						ReportingAmount,
	reportFirstFix						BOOLEAN,
	measurementInterval					UE-Positioning-MeasurementInterval,
	eventSpecificInfo					UE-Positioning-EventSpecificInfo-r7
}

UE-Positioning-EventParamList ::=				SEQUENCE (SIZE (1..maxMeasEvent)) OF
										UE-Positioning-EventParam

UE-Positioning-EventParamList-r7 ::= SEQUENCE (SIZE (1..maxMeasEvent)) OF
										UE-Positioning-EventParam-r7

UE-Positioning-EventSpecificInfo ::=			CHOICE {
	e7a									ThresholdPositionChange,
	e7b									ThresholdSFN-SFN-Change,
	e7c									ThresholdSFN-GPS-TOW
}

UE-Positioning-EventSpecificInfo-r7 ::= CHOICE {
	e7a									ThresholdPositionChange,
	e7b									ThresholdSFN-SFN-Change,
	e7c									ThresholdSFN-GPS-TOW-us,
	e7d									ThresholdSFN-GANSS-TOW
}

-- This IE, if included,  shall contain exactly one of the optional elements
UE-Positioning-GANSS-AddUTCModels ::= SEQUENCE {
	utcModel1							UTCmodelSet1							OPTIONAL,
	utcModel2							UTCmodelSet2							OPTIONAL,
	utcModel3							UTCmodelSet3							OPTIONAL
}

-- This IE, if included,  shall contain exactly one of the optional elements
UE-Positioning-GANSS-AddUTCModels-r12 ::= SEQUENCE {
	utcModel1							UTCmodelSet1							OPTIONAL,
	utcModel2							UTCmodelSet2							OPTIONAL,
	utcModel3							UTCmodelSet3							OPTIONAL,
	utcModel4							UTCmodelSet4							OPTIONAL
}

UE-Positioning-GANSS-AddUTCModels-vc50ext ::= SEQUENCE {
	utcModel4							UTCmodelSet4			OPTIONAL
}

UE-Positioning-GANSS-Almanac ::=	SEQUENCE{
	ganss-wk-number						INTEGER (0..255),
	alm-keplerianParameters				ALM-keplerianParameters					OPTIONAL
}

-- This IE, if included,  shall contain exactly one of the optional elements
UE-Positioning-GANSS-Almanac-v860ext ::= SEQUENCE {
	alm-keplerianNAVAlmanac	 			ALM-NAVKeplerianSet						OPTIONAL,
	alm-keplerianReducedAlmanac			ALM-ReducedKeplerianSet					OPTIONAL,
	alm-keplerianMidiAlmanac			ALM-MidiAlmanacSet						OPTIONAL,
	alm-keplerianGLONASS				ALM-GlonassAlmanacSet					OPTIONAL,
	alm-ecefSBASAlmanac					ALM-ECEFsbasAlmanacSet					OPTIONAL
}

UE-Positioning-GANSS-Almanac-r8 ::=	SEQUENCE{
	ganss-wk-number						INTEGER (0..255),
	alm-keplerianParameters				ALM-keplerianParameters					OPTIONAL,
	alm-keplerianNAVAlmanac	 			ALM-NAVKeplerianSet						OPTIONAL,
	alm-keplerianReducedAlmanac			ALM-ReducedKeplerianSet					OPTIONAL,
	alm-keplerianMidiAlmanac			ALM-MidiAlmanacSet						OPTIONAL,
	alm-keplerianGLONASS				ALM-GlonassAlmanacSet					OPTIONAL,
	alm-ecefSBASAlmanac					ALM-ECEFsbasAlmanacSet					OPTIONAL
}

UE-Positioning-GANSS-Almanac-va40ext ::= SEQUENCE {
	complete-Almanac-Provided			BOOLEAN									OPTIONAL
}

UE-Positioning-GANSS-Almanac-r10 ::=	SEQUENCE{
	ganss-wk-number						INTEGER (0..255),
	complete-Almanac-Provided			BOOLEAN									OPTIONAL,
	alm-keplerianParameters				ALM-keplerianParameters					OPTIONAL,
	alm-keplerianNAVAlmanac	 			ALM-NAVKeplerianSet						OPTIONAL,
	alm-keplerianReducedAlmanac			ALM-ReducedKeplerianSet					OPTIONAL,
	alm-keplerianMidiAlmanac			ALM-MidiAlmanacSet						OPTIONAL,
	alm-keplerianGLONASS				ALM-GlonassAlmanacSet					OPTIONAL,
	alm-ecefSBASAlmanac					ALM-ECEFsbasAlmanacSet					OPTIONAL
}

UE-Positioning-GANSS-Almanac-r12 ::=	SEQUENCE{
	ganss-wk-number						INTEGER (0..255),
	complete-Almanac-Provided			BOOLEAN									OPTIONAL,
	alm-keplerianParameters				ALM-keplerianParameters					OPTIONAL,
	alm-keplerianNAVAlmanac	 			ALM-NAVKeplerianSet						OPTIONAL,
	alm-keplerianReducedAlmanac			ALM-ReducedKeplerianSet					OPTIONAL,
	alm-keplerianMidiAlmanac				ALM-MidiAlmanacSet						OPTIONAL,
	alm-keplerianGLONASS					ALM-GlonassAlmanacSet					OPTIONAL,
	alm-ecefSBASAlmanac					ALM-ECEFsbasAlmanacSet					OPTIONAL,
	alm-keplerianBDSAlmanac				ALM-BDSKeplerianSet						OPTIONAL
}

UE-Positioning-GANSS-Almanac-vc50ext ::= SEQUENCE {
	alm-keplerianBDSAlmanac				ALM-BDSKeplerianSet			OPTIONAL
}

UE-Positioning-GANSS-AdditionalAssistanceDataRequest ::= SEQUENCE {
	ganssReferenceTime					BOOLEAN,
	ganssreferenceLocation				BOOLEAN,
	ganssIonosphericModel				BOOLEAN,
	ganssRequestedGenericAssistanceDataList	GanssRequestedGenericAssistanceDataList
}

UE-Positioning-GANSS-AdditionalAssistanceDataRequest-v860ext ::= SEQUENCE {
	ganssAddIonoModelReq				BIT STRING (SIZE (2))					OPTIONAL,
	ganssEOPreq							ENUMERATED { true }						OPTIONAL,
	ganssRequestedGenericAssistanceDataList
										GanssRequestedGenericAssistanceDataList-v860ext
}

UE-Positioning-GANSS-AdditionalAssistanceDataRequest-vc50ext ::= SEQUENCE {
	ganssRequestedGenericAssistanceDataList
										GanssRequestedGenericAssistanceDataList-vc50ext
}

UE-Positioning-GANSS-AddIonoModel ::= SEQUENCE {
	dataID								BIT STRING (SIZE (2)),
	alpha-beta-parameters				UE-Positioning-GPS-IonosphericModel
}

UE-Positioning-GANSS-AddNavigationModels ::= SEQUENCE {
	non-broadcastIndication				ENUMERATED { true }						OPTIONAL,
	ganssSatInfoNavList					Ganss-Sat-Info-AddNavList
}

UE-Positioning-GANSS-AddNavigationModels-r12 ::= SEQUENCE {
	non-broadcastIndication				ENUMERATED { true }						OPTIONAL,
	ganssSatInfoNavList					Ganss-Sat-Info-AddNavList-r12
}

UE-Positioning-GANSS-AddNavigationModels-vc50ext ::= SEQUENCE {
	ganssSatInfoNavList					Ganss-Sat-Info-AddNavList-vc50ext
}

UE-Positioning-GANSS-AssistanceData ::= SEQUENCE {
	ue-positioning-GANSS-ReferenceTime	UE-Positioning-GANSS-ReferenceTime		OPTIONAL,
	uePositioningGanssReferencePosition	ReferenceLocationGANSS					OPTIONAL,
	uePositioningGanssIonosphericModel	UE-Positioning-GANSS-IonosphericModel	OPTIONAL,
	ganssGenericDataList				GANSSGenericDataList					OPTIONAL
}

UE-Positioning-GANSS-AssistanceData-v860ext ::= SEQUENCE {
	uePositioningGanssAddIonoModel			UE-Positioning-GANSS-AddIonoModel		OPTIONAL,
	uePositioningGanssEarthOrientationPara	UE-Positioning-GANSS-EarthOrientPara	OPTIONAL,
	ganssGenericDataList					GANSSGenericDataList-v860ext			OPTIONAL
}

UE-Positioning-GANSS-AssistanceData-r8 ::= SEQUENCE {
	ue-positioning-GANSS-ReferenceTime	UE-Positioning-GANSS-ReferenceTime		OPTIONAL,
	uePositioningGanssReferencePosition	ReferenceLocationGANSS					OPTIONAL,
	uePositioningGanssIonosphericModel	UE-Positioning-GANSS-IonosphericModel	OPTIONAL,
	uePositioningGanssAddIonoModel		UE-Positioning-GANSS-AddIonoModel		OPTIONAL,
	uePositioningGanssEarthOrientationPara
										UE-Positioning-GANSS-EarthOrientPara	OPTIONAL,
	ganssGenericDataList				GANSSGenericDataList-r8					OPTIONAL
}

UE-Positioning-GANSS-AssistanceData-r9 ::= SEQUENCE {
	ue-positioning-GANSS-ReferenceTime	UE-Positioning-GANSS-ReferenceTime		OPTIONAL,
	uePositioningGanssReferencePosition	ReferenceLocationGANSS					OPTIONAL,
	uePositioningGanssIonosphericModel	UE-Positioning-GANSS-IonosphericModel	OPTIONAL,
	uePositioningGanssAddIonoModel		UE-Positioning-GANSS-AddIonoModel		OPTIONAL,
	uePositioningGanssEarthOrientationPara
										UE-Positioning-GANSS-EarthOrientPara	OPTIONAL,
	ganssGenericDataList				GANSSGenericDataList-r9					OPTIONAL
}

UE-Positioning-GANSS-AssistanceData-v920ext ::= SEQUENCE {
	ganssGenericDataList				GANSSGenericDataList-v920ext			OPTIONAL
}

UE-Positioning-GANSS-AssistanceData-va40ext ::= SEQUENCE {
	ue-positioning-GANSS-ReferenceTime	UE-Positioning-GANSS-ReferenceTime-va40ext	OPTIONAL,
	ganssGenericDataList				GANSSGenericDataList-va40ext				OPTIONAL
}

UE-Positioning-GANSS-AssistanceData-vc50ext ::= SEQUENCE {
	ganssGenericDataList				GANSSGenericDataList-vc50ext				OPTIONAL
}

UE-Positioning-GANSS-AssistanceData-r10 ::= SEQUENCE {
	ue-positioning-GANSS-ReferenceTime	UE-Positioning-GANSS-ReferenceTime-r10	OPTIONAL,
	uePositioningGanssReferencePosition	ReferenceLocationGANSS					OPTIONAL,
	uePositioningGanssIonosphericModel	UE-Positioning-GANSS-IonosphericModel	OPTIONAL,
	uePositioningGanssAddIonoModel		UE-Positioning-GANSS-AddIonoModel		OPTIONAL,
	uePositioningGanssEarthOrientationPara
										UE-Positioning-GANSS-EarthOrientPara	OPTIONAL,
	ganssGenericDataList				GANSSGenericDataList-r10				OPTIONAL
}

UE-Positioning-GANSS-AssistanceData-r12 ::= SEQUENCE {
	ue-positioning-GANSS-ReferenceTime		UE-Positioning-GANSS-ReferenceTime-r10	OPTIONAL,
	uePositioningGanssReferencePosition		ReferenceLocationGANSS					OPTIONAL,
	uePositioningGanssIonosphericModel		UE-Positioning-GANSS-IonosphericModel	OPTIONAL,
	uePositioningGanssAddIonoModel			UE-Positioning-GANSS-AddIonoModel		OPTIONAL,
	uePositioningGanssEarthOrientationPara	UE-Positioning-GANSS-EarthOrientPara	OPTIONAL,
	ganssGenericDataList					GANSSGenericDataList-r12				OPTIONAL
}

UE-Positioning-GANSS-AuxiliaryInfo ::= CHOICE {
	-- This choice may only be present if GANSS ID indicates Modernized GPS
	ganssID1	AuxInfoGANSS-ID1,
	-- This choice may only be present if GANSS ID indicates GLONASS
	ganssID3	AuxInfoGANSS-ID3
}

UE-Positioning-GANSS-ClockModel ::=	SEQUENCE {
	satellite-clock-modelList			Satellite-clock-modelList
}

-- This IE, if included,  shall contain exactly one of the optional elements
UE-Positioning-GANSS-AddClockModels ::= SEQUENCE {
	navClockModel			 			NAVclockModel							OPTIONAL,
	cnavClockModel			 			CNAVclockModel							OPTIONAL,
	glonassClockModel		 			GLONASSclockModel						OPTIONAL,
	sbasClockModel			 			SBASclockModel							OPTIONAL
}

-- This IE, if included,  shall contain exactly one of the optional elements
UE-Positioning-GANSS-AddClockModels-r12 ::= SEQUENCE {
	navClockModel			 			NAVclockModel							OPTIONAL,
	cnavClockModel			 			CNAVclockModel							OPTIONAL,
	glonassClockModel		 			GLONASSclockModel						OPTIONAL,
	sbasClockModel			 			SBASclockModel							OPTIONAL,
	bdsClockModel			 			BDSclockModel							OPTIONAL
}

UE-Positioning-GANSS-AddClockModels-vc50ext ::= SEQUENCE {
	bdsClockModel			 			BDSclockModel							OPTIONAL
}

-- This IE, if included, shall contain exactly one of the optional elements
UE-Positioning-GANSS-AddOrbitModels ::= SEQUENCE {
	navKeplerianSet	 					NavModel-NAVKeplerianSet				OPTIONAL,
	cnavKeplerianSet					NavModel-CNAVKeplerianSet				OPTIONAL,
	glonassECEF							NavModel-GLONASSecef					OPTIONAL,
	sbasECEF							NavModel-SBASecef						OPTIONAL
}

UE-Positioning-GANSS-AddOrbitModels-r12 ::= SEQUENCE {
	navKeplerianSet	 				NavModel-NAVKeplerianSet					OPTIONAL,
	cnavKeplerianSet				NavModel-CNAVKeplerianSet					OPTIONAL,
	glonassECEF						NavModel-GLONASSecef						OPTIONAL,
	sbasECEF						NavModel-SBASecef							OPTIONAL,
	bdsKeplerianSet					NavModel-BDSKeplerianSet					OPTIONAL
}

UE-Positioning-GANSS-AddOrbitModels-vc50ext ::= SEQUENCE {
	bdsKeplerianSet					NavModel-BDSKeplerianSet					OPTIONAL
}

UE-Positioning-GANSS-Data ::=		SEQUENCE {
	ganssDataCipheringInfo				UE-Positioning-CipherParameters			OPTIONAL,
	ganssDecipheringKeys				GANSSDecipheringKeys					OPTIONAL,
	uePositioningGanssReferenceTime		UE-Positioning-GANSS-ReferenceTime		OPTIONAL,
	uePositioningGanssReferencePosition	ReferenceLocationGANSS					OPTIONAL,
	uePositioningGanssIonosphericModel	UE-Positioning-GANSS-IonosphericModel	OPTIONAL,
	ganssGenericDataList				GANSSGenericDataList					OPTIONAL
}

UE-Positioning-GANSS-Data-Bit-Assistance ::= SEQUENCE {
	ganss-tod							INTEGER (0..59),
	dataBitAssistanceList				DataBitAssistanceList
}

UE-Positioning-GANSS-EarthOrientPara ::= SEQUENCE {
	teop								BIT STRING (SIZE (16)),
	pmX									BIT STRING (SIZE (21)),
	pmXdot								BIT STRING (SIZE (15)),
	pmY									BIT STRING (SIZE (21)),
	pmYdot								BIT STRING (SIZE (15)),
	deltaUT1							BIT STRING (SIZE (31)),
	deltaUT1dot							BIT STRING (SIZE (19))
}

UE-Positioning-GANSS-IonosphericModel ::= SEQUENCE {
	alpha-zero-ionos					BIT STRING (SIZE (11)),
	alpha-one-ionos						BIT STRING (SIZE (11)),
	alpha-two-ionos						BIT STRING (SIZE (14)),
	gANSS-storm-flags					GANSS-Storm-Flag					OPTIONAL
}

UE-Positioning-BDS-IonoGridModel ::= SEQUENCE {
-- Actual value bds-RefTime = ((30..3600) / 30) - 1.
	bds-RefTime					INTEGER (0..119),
	bds-IGPInfoList				BDS-IGPInfoList
}

UE-Positioning-GANSS-MeasuredResults ::= SEQUENCE {
	referenceTime						CHOICE {
		utran-GANSSReferenceTimeResult		UTRAN-GANSSReferenceTime,
		ganssReferenceTimeOnly				GANSSReferenceTimeOnly
	},
	ganssGenericMeasurementInfo			GANSSGenericMeasurementInfo
}

UE-Positioning-GANSS-MeasuredResults-v860ext ::= SEQUENCE {
	ganssGenericMeasurementInfo			GANSSGenericMeasurementInfo-v860ext
}

UE-Positioning-GANSS-NavigationModel ::= SEQUENCE {
	non-broadcastIndication				ENUMERATED { true }					OPTIONAL,
	ganssSatInfoNavList					Ganss-Sat-Info-NavList
}

UE-Positioning-GANSS-OrbitModel ::=	SEQUENCE {
	keplerianParameters					KeplerianParameters					OPTIONAL
}

UE-Positioning-GANSS-RealTimeIntegrity ::= SEQUENCE (SIZE (1..maxGANSSSat)) OF SEQUENCE {
	bad-ganss-satId						INTEGER (0..63),
	bad-ganss-signalId					BIT STRING (SIZE (8))				OPTIONAL
}

UE-Positioning-GANSS-ReferenceMeasurementInfo ::= SEQUENCE {
	ganssSignalId						GANSS-Signal-Id						OPTIONAL,
	satelliteInformationList			GANSSSatelliteInformationList
}

UE-Positioning-GANSS-ReferenceMeasurementInfo-va40ext ::= SEQUENCE {
	satelliteInformationList			GANSSSatelliteInformationList-va40ext
}

UE-Positioning-GANSS-ReferenceMeasurementInfo-r10 ::= SEQUENCE {
	ganssSignalId						GANSS-Signal-Id						OPTIONAL,
	satelliteInformationList			GANSSSatelliteInformationList-r10
}

UE-Positioning-GANSS-ReferenceMeasurementInfo-vc50ext ::= SEQUENCE {
	confidence							INTEGER (0..100)					OPTIONAL,
	satelliteInformationList			GANSSSatelliteInformationList-vc50ext
}

UE-Positioning-GANSS-ReferenceMeasurementInfo-r12 ::= SEQUENCE {
	ganssSignalId						GANSS-Signal-Id						OPTIONAL,
	confidence							INTEGER (0..100)					OPTIONAL,
	satelliteInformationList			GANSSSatelliteInformationList-r12
}

UE-Positioning-GANSS-ReferenceTime ::= SEQUENCE {
	ganssDay							INTEGER (0..8191)					OPTIONAL,
	ganssTod							INTEGER (0..86399),
	ganssTodUncertainty					INTEGER (0..127)					OPTIONAL,
	ganssTimeId							INTEGER (0..7)						OPTIONAL,
	utran-ganssreferenceTime			SEQUENCE {
		timingOfCellFrames					INTEGER (0..3999999),
		mode									CHOICE {
			fdd										SEQUENCE {
				primary-CPICH-Info						PrimaryCPICH-Info
			},
			tdd										SEQUENCE {
				cellParameters							CellParametersID
			}
		},
		referenceSfn						INTEGER (0..4095)
	}		OPTIONAL,
	tutran-ganss-driftRate				Tutran-Ganss-DriftRate				OPTIONAL
}

UE-Positioning-GANSS-ReferenceTime-va40ext ::= SEQUENCE {
	ganss-Day-Cycle-Number				INTEGER (0..7)						OPTIONAL
}

UE-Positioning-GANSS-ReferenceTime-r10 ::= SEQUENCE {
	ganssDay							INTEGER (0..8191)					OPTIONAL,
	ganss-Day-Cycle-Number				INTEGER (0..7)						OPTIONAL,
	ganssTod							INTEGER (0..86399),
	ganssTodUncertainty					INTEGER (0..127)					OPTIONAL,
	ganssTimeId							INTEGER (0..7)						OPTIONAL,
	utran-ganssreferenceTime			SEQUENCE {
		timingOfCellFrames					INTEGER (0..3999999),
		mode									CHOICE {
			fdd										SEQUENCE {
				primary-CPICH-Info						PrimaryCPICH-Info
			},
			tdd										SEQUENCE {
				cellParameters							CellParametersID
			}
		},
		referenceSfn						INTEGER (0..4095)
	}		OPTIONAL,
	tutran-ganss-driftRate				Tutran-Ganss-DriftRate				OPTIONAL
}

UE-Positioning-GANSS-SBAS-ID ::=	ENUMERATED {
										waas,
										egnos,
										msas,
										gagan,
										spare4,
										spare3,
										spare2,
										spare1 }

UE-Positioning-GANSS-TimeModel ::=	SEQUENCE {
	ganss-timeModelreferenceTime		INTEGER (0..37799),						-- scale factor 16s
	ganss-t-a0							INTEGER (-2147483648..2147483647),		-- scale factor 2-35
	-- 'ganss-t-al' scale factor 2-51
	ganss-t-a1							INTEGER (-8388608..8388607)			OPTIONAL,
	-- 'ganss-t-a2' scale factor 2-68
	ganss-t-a2							INTEGER (-64..63)					OPTIONAL,
	gnss-to-id							ENUMERATED { gps, galileo, qzss,
											glonass, spare4, spare3, spare2, spare1 },
	ganss-wk-number						INTEGER (0..8191)					OPTIONAL
}

UE-Positioning-GANSS-TimeModel-va40ext ::= SEQUENCE {
	deltaT								INTEGER (-128..127)					OPTIONAL
}

UE-Positioning-GANSS-TimeModel-r10 ::=	SEQUENCE {
	ganss-timeModelreferenceTime		INTEGER (0..37799),						-- scale factor 16s
	ganss-t-a0							INTEGER (-2147483648..2147483647),		-- scale factor 2-35
	-- 'ganss-t-al' scale factor 2-51
	ganss-t-a1							INTEGER (-8388608..8388607)			OPTIONAL,
	-- 'ganss-t-a2' scale factor 2-68
	ganss-t-a2							INTEGER (-64..63)					OPTIONAL,
	gnss-to-id							ENUMERATED { gps, galileo, qzss,
											glonass, bds, spare3, spare2, spare1 },
	ganss-wk-number						INTEGER (0..8191)					OPTIONAL,
	deltaT								INTEGER (-128..127)					OPTIONAL
}

UE-Positioning-GANSS-TimeModels ::= SEQUENCE (SIZE (1..maxGANSS-1)) OF
										UE-Positioning-GANSS-TimeModel

UE-Positioning-GANSS-TimeModels-va40ext ::= SEQUENCE (SIZE (1..maxGANSS-1)) OF
										UE-Positioning-GANSS-TimeModel-va40ext

UE-Positioning-GANSS-UTCModel ::=	SEQUENCE {
	a-one-utc							BIT STRING (SIZE (24)),
	a-zero-utc							BIT STRING (SIZE (32)),
	t-ot-utc							BIT STRING (SIZE (8)),
	delta-t-ls-utc						BIT STRING (SIZE (8)),
	w-n-t-utc							BIT STRING (SIZE (8)),
	w-n-lsf-utc							BIT STRING (SIZE (8)),
	dn-utc								BIT STRING (SIZE (8)),
	delta-t-lsf-utc						BIT STRING (SIZE (8))
}

UE-Positioning-GPS-AcquisitionAssistance ::=	SEQUENCE {
	gps-ReferenceTime					GPS-TOW-1msec,
	utran-GPSReferenceTime				UTRAN-GPSReferenceTime			OPTIONAL,
	satelliteInformationList			AcquisitionSatInfoList
}

UE-Positioning-GPS-AcquisitionAssistance-v770ext ::= SEQUENCE {
	ue-Positioning-GPS-ReferenceTimeUncertainty
										UE-Positioning-GPS-ReferenceTimeUncertainty		OPTIONAL
}

UE-Positioning-GPS-AcquisitionAssistance-r7 ::= SEQUENCE {
	gps-ReferenceTime					GPS-TOW-1msec,
	utran-GPSReferenceTime				UTRAN-GPSReferenceTime			OPTIONAL,
	ue-Positioning-GPS-ReferenceTimeUncertainty
										UE-Positioning-GPS-ReferenceTimeUncertainty		OPTIONAL,
	satelliteInformationList			AcquisitionSatInfoList
}

UE-Positioning-GPS-AcquisitionAssistance-va40ext ::=	SEQUENCE {
	satelliteInformationList			AcquisitionSatInfoList-va40ext
}

UE-Positioning-GPS-AcquisitionAssistance-r10 ::= SEQUENCE {
	gps-ReferenceTime					GPS-TOW-1msec,
	utran-GPSReferenceTime				UTRAN-GPSReferenceTime			OPTIONAL,
	ue-Positioning-GPS-ReferenceTimeUncertainty
										UE-Positioning-GPS-ReferenceTimeUncertainty
																		OPTIONAL,
	satelliteInformationList			AcquisitionSatInfoList-r10
}

UE-Positioning-GPS-AcquisitionAssistance-vc50ext ::=	SEQUENCE {
	confidence							INTEGER (0..100)					OPTIONAL,
	satelliteInformationList			AcquisitionSatInfoList-vc50ext
}

UE-Positioning-GPS-AcquisitionAssistance-r12 ::= SEQUENCE {
	gps-ReferenceTime					GPS-TOW-1msec,
	utran-GPSReferenceTime				UTRAN-GPSReferenceTime			OPTIONAL,
	ue-Positioning-GPS-ReferenceTimeUncertainty
										UE-Positioning-GPS-ReferenceTimeUncertainty
																		OPTIONAL,
	confidence							INTEGER (0..100)				OPTIONAL,
	satelliteInformationList			AcquisitionSatInfoList-r12
}

UE-Positioning-GPS-AdditionalAssistanceDataRequest ::=		SEQUENCE {
	almanacRequest						BOOLEAN,
	utcModelRequest						BOOLEAN,
	ionosphericModelRequest				BOOLEAN,
	navigationModelRequest				BOOLEAN,
	dgpsCorrectionsRequest				BOOLEAN,
	referenceLocationRequest			BOOLEAN,
	referenceTimeRequest				BOOLEAN,
	aquisitionAssistanceRequest			BOOLEAN,
	realTimeIntegrityRequest			BOOLEAN,
	navModelAddDataRequest				UE-Positioning-GPS-NavModelAddDataReq		OPTIONAL
}

UE-Positioning-GPS-Almanac ::=					SEQUENCE {
	wn-a								BIT STRING (SIZE (8)),
	almanacSatInfoList					AlmanacSatInfoList,
	sv-GlobalHealth						BIT STRING (SIZE (364))				OPTIONAL
}

UE-Positioning-GPS-Almanac-va40ext ::=	SEQUENCE {
	complete-Almanac-Provided				BOOLEAN							OPTIONAL
}

UE-Positioning-GPS-Almanac-r10 ::= SEQUENCE {
	wn-a								BIT STRING (SIZE (8)),
	complete-Almanac-Provided			BOOLEAN								OPTIONAL,
	almanacSatInfoList					AlmanacSatInfoList,
	sv-GlobalHealth						BIT STRING (SIZE (364))				OPTIONAL
}

UE-Positioning-GPS-AssistanceData ::=	SEQUENCE {
	ue-positioning-GPS-ReferenceTime		UE-Positioning-GPS-ReferenceTime			OPTIONAL,
	ue-positioning-GPS-ReferenceLocation	ReferenceLocation							OPTIONAL,
	ue-positioning-GPS-DGPS-Corrections		UE-Positioning-GPS-DGPS-Corrections			OPTIONAL,
	ue-positioning-GPS-NavigationModel		UE-Positioning-GPS-NavigationModel			OPTIONAL,
	ue-positioning-GPS-IonosphericModel		UE-Positioning-GPS-IonosphericModel			OPTIONAL,
	ue-positioning-GPS-UTC-Model			UE-Positioning-GPS-UTC-Model				OPTIONAL,
	ue-positioning-GPS-Almanac				UE-Positioning-GPS-Almanac					OPTIONAL,
	ue-positioning-GPS-AcquisitionAssistance
											UE-Positioning-GPS-AcquisitionAssistance	OPTIONAL,
	ue-positioning-GPS-Real-timeIntegrity	BadSatList									OPTIONAL,
	-- dummy is not used in this version of the specification, it should
	-- not be sent and if received it should be ignored.
	dummy			UE-Positioning-GPS-ReferenceCellInfo		OPTIONAL
}

UE-Positioning-GPS-AssistanceData-v770ext ::= SEQUENCE {
	ue-positioning-GPS-ReferenceTime		UE-Positioning-GPS-ReferenceTime-v770ext	OPTIONAL,
	ue-positioning-GPS-AcquisitionAssistance
									UE-Positioning-GPS-AcquisitionAssistance-v770ext	OPTIONAL
}

UE-Positioning-GPS-AssistanceData-r7 ::= SEQUENCE {
	ue-positioning-GPS-ReferenceTime		UE-Positioning-GPS-ReferenceTime-r7			OPTIONAL,
	ue-positioning-GPS-ReferenceLocation	ReferenceLocation							OPTIONAL,
	ue-positioning-GPS-DGPS-Corrections		UE-Positioning-GPS-DGPS-Corrections			OPTIONAL,
	ue-positioning-GPS-NavigationModel		UE-Positioning-GPS-NavigationModel			OPTIONAL,
	ue-positioning-GPS-IonosphericModel		UE-Positioning-GPS-IonosphericModel			OPTIONAL,
	ue-positioning-GPS-UTC-Model			UE-Positioning-GPS-UTC-Model				OPTIONAL,
	ue-positioning-GPS-Almanac				UE-Positioning-GPS-Almanac					OPTIONAL,
	ue-positioning-GPS-AcquisitionAssistance
											UE-Positioning-GPS-AcquisitionAssistance-r7	OPTIONAL,
	ue-positioning-GPS-Real-timeIntegrity	BadSatList									OPTIONAL
}

UE-Positioning-GPS-AssistanceData-r9 ::= SEQUENCE {
	ue-positioning-GPS-ReferenceTime		UE-Positioning-GPS-ReferenceTime-r7			OPTIONAL,
	ue-positioning-GPS-ReferenceLocation	ReferenceLocation							OPTIONAL,
	ue-positioning-GPS-DGPS-Corrections		UE-Positioning-GPS-DGPS-Corrections-r9		OPTIONAL,
	ue-positioning-GPS-NavigationModel		UE-Positioning-GPS-NavigationModel			OPTIONAL,
	ue-positioning-GPS-IonosphericModel		UE-Positioning-GPS-IonosphericModel			OPTIONAL,
	ue-positioning-GPS-UTC-Model			UE-Positioning-GPS-UTC-Model				OPTIONAL,
	ue-positioning-GPS-Almanac				UE-Positioning-GPS-Almanac					OPTIONAL,
	ue-positioning-GPS-AcquisitionAssistance
											UE-Positioning-GPS-AcquisitionAssistance-r7	OPTIONAL,
	ue-positioning-GPS-Real-timeIntegrity	BadSatList									OPTIONAL
}

UE-Positioning-GPS-AssistanceData-v920ext ::= SEQUENCE {
	ue-positioning-GPS-DGPS-Corrections		UE-Positioning-GPS-DGPS-Corrections-v920ext	OPTIONAL
}

UE-Positioning-GPS-AssistanceData-va40ext ::= SEQUENCE {
	ue-positioning-GPS-ReferenceTime		UE-Positioning-GPS-ReferenceTime-va40ext	OPTIONAL,
	ue-positioning-GPS-Almanac				UE-Positioning-GPS-Almanac-va40ext			OPTIONAL,
	ue-positioning-GPS-AcquisitionAssistance
											UE-Positioning-GPS-AcquisitionAssistance-va40ext
																						OPTIONAL
}

UE-Positioning-GPS-AssistanceData-r10 ::=	SEQUENCE {
	ue-positioning-GPS-ReferenceTime		UE-Positioning-GPS-ReferenceTime-r10		OPTIONAL,
	ue-positioning-GPS-ReferenceLocation	ReferenceLocation							OPTIONAL,
	ue-positioning-GPS-DGPS-Corrections		UE-Positioning-GPS-DGPS-Corrections-r9		OPTIONAL,
	ue-positioning-GPS-NavigationModel		UE-Positioning-GPS-NavigationModel			OPTIONAL,
	ue-positioning-GPS-IonosphericModel		UE-Positioning-GPS-IonosphericModel			OPTIONAL,
	ue-positioning-GPS-UTC-Model			UE-Positioning-GPS-UTC-Model				OPTIONAL,
	ue-positioning-GPS-Almanac				UE-Positioning-GPS-Almanac-r10				OPTIONAL,
	ue-positioning-GPS-AcquisitionAssistance
											UE-Positioning-GPS-AcquisitionAssistance-r10
																						OPTIONAL,
	ue-positioning-GPS-Real-timeIntegrity	BadSatList									OPTIONAL
}

UE-Positioning-GPS-AssistanceData-vc50ext ::= SEQUENCE {
	ue-positioning-GPS-AcquisitionAssistance
											UE-Positioning-GPS-AcquisitionAssistance-vc50ext
																						OPTIONAL
}

UE-Positioning-GPS-AssistanceData-r12 ::=	SEQUENCE {
	ue-positioning-GPS-ReferenceTime		UE-Positioning-GPS-ReferenceTime-r10		OPTIONAL,
	ue-positioning-GPS-ReferenceLocation	ReferenceLocation							OPTIONAL,
	ue-positioning-GPS-DGPS-Corrections		UE-Positioning-GPS-DGPS-Corrections-r9		OPTIONAL,
	ue-positioning-GPS-NavigationModel		UE-Positioning-GPS-NavigationModel			OPTIONAL,
	ue-positioning-GPS-IonosphericModel		UE-Positioning-GPS-IonosphericModel			OPTIONAL,
	ue-positioning-GPS-UTC-Model			UE-Positioning-GPS-UTC-Model				OPTIONAL,
	ue-positioning-GPS-Almanac				UE-Positioning-GPS-Almanac-r10				OPTIONAL,
	ue-positioning-GPS-AcquisitionAssistance
											UE-Positioning-GPS-AcquisitionAssistance-r12
																						OPTIONAL,
	ue-positioning-GPS-Real-timeIntegrity	BadSatList									OPTIONAL
}

UE-Positioning-GPS-DGPS-Corrections ::=		SEQUENCE {
	gps-TOW								GPS-TOW-1sec,
	statusHealth						DiffCorrectionStatus,
	dgps-CorrectionSatInfoList			DGPS-CorrectionSatInfoList
}

UE-Positioning-GPS-DGPS-Corrections-r9 ::=		SEQUENCE {
	gps-TOW								GPS-TOW-1sec,
	statusHealth						DiffCorrectionStatus,
	dgps-CorrectionSatInfoList			DGPS-CorrectionSatInfoList-r9
}

UE-Positioning-GPS-DGPS-Corrections-v920ext ::=	SEQUENCE {
	dgps-CorrectionSatInfoList			DGPS-CorrectionSatInfoList-v920ext
}

UE-Positioning-GPS-IonosphericModel ::=		SEQUENCE {
	alpha0								BIT STRING (SIZE (8)),
	alpha1								BIT STRING (SIZE (8)),
	alpha2								BIT STRING (SIZE (8)),
	alpha3								BIT STRING (SIZE (8)),
	beta0								BIT STRING (SIZE (8)),
	beta1								BIT STRING (SIZE (8)),
	beta2								BIT STRING (SIZE (8)),
	beta3								BIT STRING (SIZE (8))
}

UE-Positioning-GPS-MeasurementResults ::=		SEQUENCE {
	referenceTime						CHOICE {
		utran-GPSReferenceTimeResult		UTRAN-GPSReferenceTimeResult,
		gps-ReferenceTimeOnly				GPS-TOW-1msec
	},
	gps-MeasurementParamList			GPS-MeasurementParamList
}

UE-Positioning-GPS-MeasurementResults-v770ext ::= SEQUENCE {
	ue-Positioning-GPS-ReferenceTimeUncertainty
										UE-Positioning-GPS-ReferenceTimeUncertainty		OPTIONAL
}

UE-Positioning-GPS-NavigationModel ::=			SEQUENCE {
	navigationModelSatInfoList			NavigationModelSatInfoList
}

UE-Positioning-GPS-NavModelAddDataReq ::=		SEQUENCE {
	gps-Week							INTEGER (0..1023),
	-- SPARE: gps-Toe, Max = 167
	-- Values above Max are spare
	gps-Toe								INTEGER (0..255),
	-- SPARE: tToeLimit, Max = 10
	-- Values above Max are spare
	tToeLimit							INTEGER (0..15),
	satDataList							SatDataList
}

UE-Positioning-GPS-ReferenceCellInfo ::=		SEQUENCE{
	modeSpecificInfo				CHOICE {
		fdd								SEQUENCE {
			referenceIdentity				PrimaryCPICH-Info
		},
		tdd								SEQUENCE {
			referenceIdentity				CellParametersID
		}
	}
}

UE-Positioning-GPS-ReferenceTime ::= SEQUENCE {
	gps-Week							INTEGER (0..1023),
	gps-tow-1msec						GPS-TOW-1msec,
	utran-GPSReferenceTime				UTRAN-GPSReferenceTime				OPTIONAL,
	sfn-tow-Uncertainty					SFN-TOW-Uncertainty					OPTIONAL,
	utran-GPS-DriftRate					UTRAN-GPS-DriftRate					OPTIONAL,
	gps-TOW-AssistList					GPS-TOW-AssistList					OPTIONAL
}

UE-Positioning-GPS-ReferenceTime-v770ext ::= SEQUENCE {
	ue-Positioning-GPS-ReferenceTimeUncertainty
										UE-Positioning-GPS-ReferenceTimeUncertainty		OPTIONAL
}

UE-Positioning-GPS-ReferenceTime-r7 ::= SEQUENCE {
	gps-Week							INTEGER (0..1023),
	gps-tow-1msec						GPS-TOW-1msec,
	utran-GPSReferenceTime				UTRAN-GPSReferenceTime				OPTIONAL,
	ue-Positioning-GPS-ReferenceTimeUncertainty
										UE-Positioning-GPS-ReferenceTimeUncertainty		OPTIONAL,
	sfn-tow-Uncertainty					SFN-TOW-Uncertainty					OPTIONAL,
	utran-GPS-DriftRate					UTRAN-GPS-DriftRate					OPTIONAL,
	gps-TOW-AssistList					GPS-TOW-AssistList					OPTIONAL
}

UE-Positioning-GPS-ReferenceTime-va40ext ::= SEQUENCE {
	gps-Week-Cycle-Number				INTEGER (0..7)						OPTIONAL
}

UE-Positioning-GPS-ReferenceTime-r10 ::= SEQUENCE {
	gps-Week							INTEGER (0..1023),
	gps-Week-Cycle-Number				INTEGER (0..7)						OPTIONAL,
	gps-tow-1msec						GPS-TOW-1msec,
	utran-GPSReferenceTime				UTRAN-GPSReferenceTime				OPTIONAL,
	ue-Positioning-GPS-ReferenceTimeUncertainty
										UE-Positioning-GPS-ReferenceTimeUncertainty
																			OPTIONAL,
	sfn-tow-Uncertainty					SFN-TOW-Uncertainty					OPTIONAL,
	utran-GPS-DriftRate					UTRAN-GPS-DriftRate					OPTIONAL,
	gps-TOW-AssistList					GPS-TOW-AssistList					OPTIONAL
}

UE-Positioning-GPS-ReferenceTimeUncertainty ::= INTEGER (0..127)

UE-Positioning-GPS-UTC-Model ::=				SEQUENCE {
	a1									BIT STRING (SIZE (24)),
	a0									BIT STRING (SIZE (32)),
	t-ot								BIT STRING (SIZE (8)),
	wn-t								BIT STRING (SIZE (8)),
	delta-t-LS							BIT STRING (SIZE (8)),
	wn-lsf								BIT STRING (SIZE (8)),
	dn									BIT STRING (SIZE (8)),
	delta-t-LSF							BIT STRING (SIZE (8))
}

UE-Positioning-IPDL-Parameters ::=				SEQUENCE {
	ip-Spacing							IP-Spacing,
	ip-Length							IP-Length,
	ip-Offset							INTEGER (0..9),
	seed								INTEGER (0..63),
	burstModeParameters					BurstModeParameters 		OPTIONAL
}

UE-Positioning-IPDL-Parameters-r4 ::=			SEQUENCE {
	modeSpecificInfo					CHOICE {
		fdd									SEQUENCE {
			ip-Spacing							IP-Spacing,
			ip-Length							IP-Length,
			ip-Offset							INTEGER (0..9),
			seed								INTEGER (0..63)
		},
		tdd									SEQUENCE {
			ip-Spacing-TDD						IP-Spacing-TDD,
			ip-slot								INTEGER (0..14),
			ip-Start							INTEGER (0..4095),
			ip-PCCPCG							IP-PCCPCH-r4			OPTIONAL
		}
	},
	burstModeParameters					BurstModeParameters				OPTIONAL
}

UE-Positioning-IPDL-Parameters-TDD-r4-ext ::=	SEQUENCE {
	ip-Spacing							IP-Spacing-TDD,
	ip-slot								INTEGER (0..14),
	ip-Start							INTEGER (0..4095),
	ip-PCCPCG							IP-PCCPCH-r4					OPTIONAL,
	burstModeParameters					BurstModeParameters
}

UE-Positioning-MeasuredResults ::=		SEQUENCE {
	ue-positioning-OTDOA-Measurement		UE-Positioning-OTDOA-Measurement			OPTIONAL,
	-- Extended 'ue-positioning-PositionEstimateInfo' information may be provided using IE
	-- 'UE-Positioning-PositionEstimateInfo-v770ext' in IE 'UE-Positioning-MeasuredResults-v770ext'.
	ue-positioning-PositionEstimateInfo		UE-Positioning-PositionEstimateInfo			OPTIONAL,
	ue-positioning-GPS-Measurement			UE-Positioning-GPS-MeasurementResults		OPTIONAL,
	-- The 'ue-positioning-Error' information may be provided using IE 'UE-Positioning-Error-r7' in
	-- IE 'UE-Positioning-MeasuredResults-v770ext'.
	-- If IE 'UE-Positioning-Error-r7' is present, the corresponding IE 'UE-Positioning-Error' shall
	-- be excluded.
	ue-positioning-Error					UE-Positioning-Error						OPTIONAL
}

UE-Positioning-MeasuredResults-v770ext ::= SEQUENCE {
	ue-positioning-PositionEstimateInfo		UE-Positioning-PositionEstimateInfo-v770ext	OPTIONAL,
	ue-positioning-GPS-Measurement			UE-Positioning-GPS-MeasurementResults-v770ext
																						OPTIONAL,
	ue-positioning-Error					UE-Positioning-Error-r7						OPTIONAL,
	ue-positioning-Ganss-MeasuredResults	UE-Positioning-GANSS-MeasuredResults		OPTIONAL
}

UE-Positioning-MeasuredResults-v390ext ::=		SEQUENCE {
	ue-Positioning-OTDOA-Measurement-v390ext		UE-Positioning-OTDOA-Measurement-v390ext
}

UE-Positioning-MeasuredResults-v860ext ::= SEQUENCE {
	ue-positioning-Error					UE-Positioning-Error-v860ext				OPTIONAL,
	ue-positioning-Ganss-MeasurementResults	UE-Positioning-GANSS-MeasuredResults-v860ext	OPTIONAL
}

UE-Positioning-MeasuredResults-vc50ext ::= SEQUENCE {
	ue-positioning-Error					UE-Positioning-Error-vc50ext				OPTIONAL
}

UE-Positioning-MeasuredResults-vd20ext ::= SEQUENCE {
	ue-positioning-AddPos-MeasurementResults	UE-Positioning-AddPos-MeasuredResults	OPTIONAL,
	ue-positioning-PositionEstimateInfo		UE-Positioning-PositionEstimateInfo-vd20ext
																						OPTIONAL
}

UE-Positioning-Measurement ::=			SEQUENCE {
	ue-positioning-ReportingQuantity		UE-Positioning-ReportingQuantity,
	reportCriteria							UE-Positioning-ReportCriteria,
	ue-positioning-OTDOA-AssistanceData		UE-Positioning-OTDOA-AssistanceData			OPTIONAL,
	ue-positioning-GPS-AssistanceData		UE-Positioning-GPS-AssistanceData				OPTIONAL
}

UE-Positioning-Measurement-v390ext ::=	SEQUENCE {
	ue-positioning-ReportingQuantity-v390ext
											UE-Positioning-ReportingQuantity-v390ext	OPTIONAL,
	measurementValidity						MeasurementValidity							OPTIONAL,
	ue-positioning-OTDOA-AssistanceData-UEB	UE-Positioning-OTDOA-AssistanceData-UEB		OPTIONAL
}

UE-Positioning-Measurement-r4 ::=		SEQUENCE {
	ue-positioning-ReportingQuantity		UE-Positioning-ReportingQuantity-r4,
	measurementValidity						MeasurementValidity						OPTIONAL,
	reportCriteria							UE-Positioning-ReportCriteria,
	ue-positioning-OTDOA-AssistanceData		UE-Positioning-OTDOA-AssistanceData-r4	OPTIONAL,
	ue-positioning-GPS-AssistanceData		UE-Positioning-GPS-AssistanceData		OPTIONAL
}

UE-Positioning-Measurement-r7 ::=		SEQUENCE {
	ue-positioning-ReportingQuantity		UE-Positioning-ReportingQuantity-r7,
	measurementValidity						MeasurementValidity						OPTIONAL,
	reportCriteria							UE-Positioning-ReportCriteria-r7,
	ue-positioning-OTDOA-AssistanceData		UE-Positioning-OTDOA-AssistanceData-r7	OPTIONAL,
	ue-positioning-GPS-AssistanceData		UE-Positioning-GPS-AssistanceData-r7	OPTIONAL,
	ue-positioning-GANSS-AssistanceData		UE-Positioning-GANSS-AssistanceData		OPTIONAL
}

UE-Positioning-Measurement-r8 ::=		SEQUENCE {
	ue-positioning-ReportingQuantity		UE-Positioning-ReportingQuantity-r8,
	measurementValidity						MeasurementValidity						OPTIONAL,
	reportCriteria							UE-Positioning-ReportCriteria-r7,
	ue-positioning-OTDOA-AssistanceData		UE-Positioning-OTDOA-AssistanceData-r7	OPTIONAL,
	ue-positioning-GPS-AssistanceData		UE-Positioning-GPS-AssistanceData-r7	OPTIONAL,
	ue-positioning-GANSS-AssistanceData		UE-Positioning-GANSS-AssistanceData-r8	OPTIONAL
}

UE-Positioning-Measurement-r9 ::=		SEQUENCE {
	ue-positioning-ReportingQuantity		UE-Positioning-ReportingQuantity-r8,
	measurementValidity						MeasurementValidity						OPTIONAL,
	reportCriteria							UE-Positioning-ReportCriteria-r7,
	ue-positioning-OTDOA-AssistanceData		UE-Positioning-OTDOA-AssistanceData-r7	OPTIONAL,
	ue-positioning-GPS-AssistanceData		UE-Positioning-GPS-AssistanceData-r9	OPTIONAL,
	ue-positioning-GANSS-AssistanceData		UE-Positioning-GANSS-AssistanceData-r9	OPTIONAL
}

UE-Positioning-Measurement-r10 ::=		SEQUENCE {
	ue-positioning-ReportingQuantity		UE-Positioning-ReportingQuantity-r8,
	measurementValidity						MeasurementValidity						OPTIONAL,
	reportCriteria							UE-Positioning-ReportCriteria-r7,
	ue-positioning-OTDOA-AssistanceData		UE-Positioning-OTDOA-AssistanceData-r7	OPTIONAL,
	ue-positioning-GPS-AssistanceData		UE-Positioning-GPS-AssistanceData-r10	OPTIONAL,
	ue-positioning-GANSS-AssistanceData		UE-Positioning-GANSS-AssistanceData-r10	OPTIONAL
}

UE-Positioning-Measurement-r12 ::=		SEQUENCE {
	ue-positioning-ReportingQuantity		UE-Positioning-ReportingQuantity-r8,
	measurementValidity						MeasurementValidity						OPTIONAL,
	reportCriteria							UE-Positioning-ReportCriteria-r7,
	ue-positioning-OTDOA-AssistanceData		UE-Positioning-OTDOA-AssistanceData-r7	OPTIONAL,
	ue-positioning-GPS-AssistanceData		UE-Positioning-GPS-AssistanceData-r12	OPTIONAL,
	ue-positioning-GANSS-AssistanceData		UE-Positioning-GANSS-AssistanceData-r12	OPTIONAL
}

UE-Positioning-Measurement-r13 ::=	SEQUENCE {
	ue-positioning-ReportingQuantity		UE-Positioning-ReportingQuantity-r13,
	measurementValidity					MeasurementValidity						OPTIONAL,
	reportCriteria							UE-Positioning-ReportCriteria-r7,
	ue-positioning-OTDOA-AssistanceData	UE-Positioning-OTDOA-AssistanceData-r7	OPTIONAL,
	ue-positioning-GPS-AssistanceData	UE-Positioning-GPS-AssistanceData-r12	OPTIONAL,
	ue-positioning-GANSS-AssistanceData	UE-Positioning-GANSS-AssistanceData-r12	OPTIONAL
}

UE-Positioning-MeasurementEventResults ::= CHOICE {
	-- In case of 'event7a' reporting, if IE 'UE-Positioning-PositionEstimateInfo' is not needed,
	-- CHOICE shall be set to 'additionalOrReplacedPosMeasEvent'and the 'event7a' shall be included
	-- in IE 'UE-Positioning-MeasurementEventResults-v770ext'.
	event7a								UE-Positioning-PositionEstimateInfo,
	event7b								UE-Positioning-OTDOA-Measurement,
	event7c								UE-Positioning-GPS-MeasurementResults,
	-- If CHOICE is set to 'additionalOrReplacedPosMeasEvent',
	-- IE 'UE-Positioning-MeasurementEventResults-v770ext' shall be present.
	additionalOrReplacedPosMeasEvent	NULL
}

UE-Positioning-MeasurementEventResults-v770ext ::= CHOICE {
	event7a								UE-Positioning-PositionEstimateInfo-v770ext,
	event7c								UE-Positioning-GPS-MeasurementResults-v770ext,
	event7d								UE-Positioning-GANSS-MeasuredResults,
	spare								NULL
}

UE-Positioning-MeasurementEventResults-v860ext ::= CHOICE {
	event7d								UE-Positioning-GANSS-MeasuredResults-v860ext
}

UE-Positioning-MeasurementInterval ::=			ENUMERATED {
										e5, e15, e60, e300,
										e900, e1800, e3600, e7200 }

UE-Positioning-MethodType ::=					ENUMERATED {
										ue-Assisted,
										ue-Based,
										ue-BasedPreferred,
										ue-AssistedPreferred }

UE-Positioning-OTDOA-AssistanceData ::=	SEQUENCE {
	ue-positioning-OTDOA-ReferenceCellInfo
										UE-Positioning-OTDOA-ReferenceCellInfo			OPTIONAL,
	ue-positioning-OTDOA-NeighbourCellList
										UE-Positioning-OTDOA-NeighbourCellList			OPTIONAL
}

UE-Positioning-OTDOA-AssistanceData-r4 ::= SEQUENCE {
	ue-positioning-OTDOA-ReferenceCellInfo
										UE-Positioning-OTDOA-ReferenceCellInfo-r4		OPTIONAL,
	ue-positioning-OTDOA-NeighbourCellList
										UE-Positioning-OTDOA-NeighbourCellList-r4		OPTIONAL
}

UE-Positioning-OTDOA-AssistanceData-r4ext ::= SEQUENCE {
	-- In case of TDD these IPDL parameters shall be used for the reference cell instead of
	-- IPDL Parameters in IE UE-Positioning-OTDOA-ReferenceCellInfo
	ue-Positioning-IPDL-Parameters-TDD-r4-ext
										UE-Positioning-IPDL-Parameters-TDD-r4-ext		OPTIONAL,
	-- These IPDL parameters shall be used for the neighbour cells in case of TDD instead of
	-- IPDL Parameters in IE UE-Positioning-OTDOA-NeighbourCellInfoList. The cells shall be
	-- listed in the same order as in IE UE-Positioning-OTDOA-NeighbourCellInfoList
	ue-Positioning-IPDL-Parameters-TDDList-r4-ext
										UE-Positioning-IPDL-Parameters-TDDList-r4-ext	OPTIONAL
}

UE-Positioning-OTDOA-AssistanceData-UEB ::=		SEQUENCE {
	ue-positioning-OTDOA-ReferenceCellInfo-UEB
										UE-Positioning-OTDOA-ReferenceCellInfo-UEB		OPTIONAL,
	ue-positioning-OTDOA-NeighbourCellList-UEB
										UE-Positioning-OTDOA-NeighbourCellList-UEB		OPTIONAL
}

UE-Positioning-OTDOA-AssistanceData-UEB-ext ::=	SEQUENCE {
	ue-positioning-OTDOA-ReferenceCellInfo-UEB-ext
										UE-Positioning-OTDOA-ReferenceCellInfo-UEB-ext	OPTIONAL,
	ue-positioning-OTDOA-NeighbourCellList-UEB-ext
										UE-Positioning-OTDOA-NeighbourCellList-UEB-ext	OPTIONAL
}

UE-Positioning-OTDOA-AssistanceData-r7 ::= SEQUENCE {
	ue-positioning-OTDOA-ReferenceCellInfo	UE-Positioning-OTDOA-ReferenceCellInfo-r7	OPTIONAL,
	ue-positioning-OTDOA-NeighbourCellList	UE-Positioning-OTDOA-NeighbourCellList-r7	OPTIONAL
}

UE-Positioning-IPDL-Parameters-TDDList-r4-ext ::=	SEQUENCE (SIZE (1..maxCellMeas)) OF
											UE-Positioning-IPDL-Parameters-TDD-r4-ext

UE-Positioning-OTDOA-MeasuredResultsTDD-ext ::= SEQUENCE {
	neighbourList						NeighbourList-TDD-r7					OPTIONAL
}

UE-Positioning-OTDOA-Measurement ::=			SEQUENCE {
	sfn									INTEGER (0..4095),
	modeSpecificInfo				CHOICE {
		fdd								SEQUENCE {
			referenceCellIDentity				PrimaryCPICH-Info,
			ue-RX-TX-TimeDifferenceType2Info	UE-RX-TX-TimeDifferenceType2Info
		},
		tdd									SEQUENCE {
			referenceCellIdentity			CellParametersID
		}
	},
	neighbourList						NeighbourList						OPTIONAL
}

UE-Positioning-OTDOA-Measurement-v390ext ::=			SEQUENCE {
	neighbourList-v390ext						NeighbourList-v390ext
}

UE-Positioning-OTDOA-NeighbourCellInfo ::= SEQUENCE {
	modeSpecificInfo	CHOICE	{
		fdd								SEQUENCE {
			primaryCPICH-Info					PrimaryCPICH-Info
		},
		tdd								SEQUENCE{
			cellAndChannelIdentity				CellAndChannelIdentity
		}
	},
	frequencyInfo						FrequencyInfo						OPTIONAL,
	ue-positioning-IPDL-Paremeters		UE-Positioning-IPDL-Parameters		OPTIONAL,
	sfn-SFN-RelTimeDifference			SFN-SFN-RelTimeDifference1,
	sfn-SFN-Drift						SFN-SFN-Drift						OPTIONAL,
	searchWindowSize					OTDOA-SearchWindowSize,
	positioningMode 	CHOICE{
		ueBased									SEQUENCE {},
		ueAssisted								SEQUENCE {}
	}
}

UE-Positioning-OTDOA-NeighbourCellInfo-r4 ::= SEQUENCE {
	modeSpecificInfo	CHOICE	{
		fdd								SEQUENCE {
			primaryCPICH-Info					PrimaryCPICH-Info
		},
		tdd								SEQUENCE{
			cellAndChannelIdentity				CellAndChannelIdentity
		}
	},
	frequencyInfo						FrequencyInfo						OPTIONAL,
	ue-positioning-IPDL-Paremeters		UE-Positioning-IPDL-Parameters-r4	OPTIONAL,
	sfn-SFN-RelTimeDifference			SFN-SFN-RelTimeDifference1,
	sfn-Offset-Validity					SFN-Offset-Validity					OPTIONAL,
	sfn-SFN-Drift						SFN-SFN-Drift						OPTIONAL,
	searchWindowSize					OTDOA-SearchWindowSize,
	positioningMode 	CHOICE {
		ueBased									SEQUENCE {
			relativeNorth						INTEGER (-20000..20000)				OPTIONAL,
			relativeEast						INTEGER (-20000..20000)				OPTIONAL,
			relativeAltitude					INTEGER (-4000..4000)				OPTIONAL,
			fineSFN-SFN							FineSFN-SFN							OPTIONAL,
			-- actual value roundTripTime = (IE value * 0.0625) + 876
			roundTripTime						INTEGER (0.. 32766)					OPTIONAL
		},
		ueAssisted								SEQUENCE {}
	}
}

UE-Positioning-OTDOA-NeighbourCellInfo-UEB ::= SEQUENCE {
	modeSpecificInfo	CHOICE	{
		fdd								SEQUENCE {
			primaryCPICH-Info					PrimaryCPICH-Info
		},
		tdd								SEQUENCE{
			cellAndChannelIdentity				CellAndChannelIdentity
		}
	},
	frequencyInfo						FrequencyInfo						OPTIONAL,
	ue-positioning-IPDL-Paremeters		UE-Positioning-IPDL-Parameters		OPTIONAL,
	sfn-SFN-RelTimeDifference			SFN-SFN-RelTimeDifference1,
	sfn-SFN-Drift						SFN-SFN-Drift						OPTIONAL,
	searchWindowSize					OTDOA-SearchWindowSize,
	relativeNorth						INTEGER (-20000..20000)				OPTIONAL,
	relativeEast						INTEGER (-20000..20000)				OPTIONAL,
	relativeAltitude					INTEGER (-4000..4000)				OPTIONAL,
	fineSFN-SFN							FineSFN-SFN,
	-- actual value roundTripTime = (IE value * 0.0625) + 876
	roundTripTime						INTEGER (0..32766)					OPTIONAL
}

UE-Positioning-OTDOA-NeighbourCellInfo-UEB-ext ::= SEQUENCE {
	-- actual value roundTripTimeExtension = (IE value * 0.0625)
	roundTripTimeExtension				INTEGER (0..70274)					OPTIONAL
}

UE-Positioning-OTDOA-NeighbourCellInfo-r7 ::= SEQUENCE {
	modeSpecificInfo					CHOICE {
		fdd									SEQUENCE {
			primaryCPICH-Info					PrimaryCPICH-Info
		},
		tdd									SEQUENCE{
			cellAndChannelIdentity				CellAndChannelIdentity
		}
	},
	frequencyInfo						FrequencyInfo						OPTIONAL,
	ue-positioning-IPDL-Paremeters		UE-Positioning-IPDL-Parameters-r4	OPTIONAL,
	sfn-SFN-RelTimeDifference			SFN-SFN-RelTimeDifference1,
	sfn-Offset-Validity					SFN-Offset-Validity					OPTIONAL,
	sfn-SFN-Drift						SFN-SFN-Drift						OPTIONAL,
	searchWindowSize					OTDOA-SearchWindowSize,
	positioningMode						CHOICE {
		ueBased								SEQUENCE {
			relativeNorth						INTEGER (-20000..20000)				OPTIONAL,
			relativeEast						INTEGER (-20000..20000)				OPTIONAL,
			relativeAltitude					INTEGER (-4000..4000)				OPTIONAL,
			fineSFN-SFN							FineSFN-SFN							OPTIONAL,
			-- actual value roundTripTime = (IE value * 0.0625) + 876
			roundTripTime						INTEGER (0.. 32766)					OPTIONAL,
			-- actual value roundTripTimeExtension = (IE value * 0.0625)
			roundTripTimeExtension				INTEGER (0..70274)					OPTIONAL
		},
		ueAssisted							SEQUENCE {}
	}
}

UE-Positioning-OTDOA-NeighbourCellList ::= SEQUENCE (SIZE (1..maxCellMeas)) OF
											UE-Positioning-OTDOA-NeighbourCellInfo

UE-Positioning-OTDOA-NeighbourCellList-r4 ::= SEQUENCE (SIZE (1..maxCellMeas)) OF
												UE-Positioning-OTDOA-NeighbourCellInfo-r4

UE-Positioning-OTDOA-NeighbourCellList-UEB ::= SEQUENCE (SIZE (1..maxCellMeas)) OF
											UE-Positioning-OTDOA-NeighbourCellInfo-UEB

-- The order of the list corresponds to the order of UE-Positioning-OTDOA-NeighbourCellInfo-UEB
-- in UE-Positioning-OTDOA-NeighbourCellList-UEB
UE-Positioning-OTDOA-NeighbourCellList-UEB-ext ::= SEQUENCE (SIZE (1..maxCellMeas)) OF
										UE-Positioning-OTDOA-NeighbourCellInfo-UEB-ext

UE-Positioning-OTDOA-NeighbourCellList-r7 ::= SEQUENCE (SIZE (1..maxCellMeas)) OF
												UE-Positioning-OTDOA-NeighbourCellInfo-r7

UE-Positioning-OTDOA-Quality ::=			SEQUENCE {
	stdResolution						BIT STRING (SIZE (2)),
	numberOfOTDOA-Measurements			BIT STRING (SIZE (3)),
	stdOfOTDOA-Measurements				BIT STRING (SIZE (5))
}

UE-Positioning-OTDOA-ReferenceCellInfo ::=	SEQUENCE {
	sfn									INTEGER (0..4095)					OPTIONAL,
	modeSpecificInfo CHOICE {
		fdd										SEQUENCE {
			primaryCPICH-Info					PrimaryCPICH-Info
		},
		tdd										SEQUENCE{
			cellAndChannelIdentity				CellAndChannelIdentity
		}
	},
	frequencyInfo						FrequencyInfo						OPTIONAL,
	positioningMode CHOICE {
		ueBased									SEQUENCE {},
		ueAssisted								SEQUENCE {}
	},
	ue-positioning-IPDL-Paremeters				UE-Positioning-IPDL-Parameters	OPTIONAL
}

UE-Positioning-OTDOA-ReferenceCellInfo-r4 ::=	SEQUENCE {
	sfn									INTEGER (0..4095)					OPTIONAL,
	modeSpecificInfo CHOICE {
		fdd										SEQUENCE {
			primaryCPICH-Info					PrimaryCPICH-Info
		},
		tdd										SEQUENCE{
			cellAndChannelIdentity				CellAndChannelIdentity
		}
	},
	frequencyInfo						FrequencyInfo						OPTIONAL,
	positioningMode CHOICE {
		ueBased									SEQUENCE {
			cellPosition								ReferenceCellPosition	OPTIONAL,
			-- actual value roundTripTime = (IE value * 0.0625) + 876
			roundTripTime						INTEGER (0..32766)				OPTIONAL
		},
		ueAssisted								SEQUENCE {}
	},
	ue-positioning-IPDL-Paremeters				UE-Positioning-IPDL-Parameters-r4	OPTIONAL
}

UE-Positioning-OTDOA-ReferenceCellInfo-UEB ::=			SEQUENCE {
	sfn									INTEGER (0..4095)					OPTIONAL,
	modeSpecificInfo CHOICE {
		fdd										SEQUENCE {
			primaryCPICH-Info					PrimaryCPICH-Info
		},
		tdd										SEQUENCE{
			cellAndChannelIdentity				CellAndChannelIdentity
		}
	},
	frequencyInfo						FrequencyInfo						OPTIONAL,
	cellPosition						ReferenceCellPosition				OPTIONAL,
	-- actual value roundTripTime = (IE value * 0.0625) + 876
	roundTripTime						INTEGER (0..32766)					OPTIONAL,
	ue-positioning-IPDL-Paremeters		UE-Positioning-IPDL-Parameters		OPTIONAL
}

UE-Positioning-OTDOA-ReferenceCellInfo-UEB-ext ::= SEQUENCE {
	-- actual value roundTripTimeExtension = (IE value * 0.0625)
	roundTripTimeExtension				INTEGER (0..70274)					OPTIONAL
}

UE-Positioning-OTDOA-ReferenceCellInfo-r7 ::= SEQUENCE {
	sfn									INTEGER (0..4095)					OPTIONAL,
	modeSpecificInfo					CHOICE {
		fdd									SEQUENCE {
			primaryCPICH-Info					PrimaryCPICH-Info
		},
		tdd									SEQUENCE{
			cellAndChannelIdentity				CellAndChannelIdentity
		}
	},
	frequencyInfo						FrequencyInfo						OPTIONAL,
	positioningMode						CHOICE {
		ueBased								SEQUENCE {
			cellPosition						ReferenceCellPosition			OPTIONAL,
			-- actual value roundTripTime = (IE value * 0.0625) + 876
			roundTripTime						INTEGER (0..32766)				OPTIONAL,
			-- actual value roundTripTimeExtension = (IE value * 0.0625)
			roundTripTimeExtension				INTEGER (0..70274)				OPTIONAL
		},
		ueAssisted							SEQUENCE {}
	},
	ue-positioning-IPDL-Paremeters		UE-Positioning-IPDL-Parameters-r4	OPTIONAL
}

UE-Positioning-PositionEstimateInfo ::= SEQUENCE {
	referenceTime						CHOICE {
		utran-GPSReferenceTimeResult		UTRAN-GPSReferenceTimeResult,
		gps-ReferenceTimeOnly				GPS-TOW-1msec,
		cell-Timing							SEQUENCE {
			sfn											INTEGER (0..4095),
			modeSpecificInfo 				CHOICE {
				fdd									SEQUENCE {
					primaryCPICH-Info					PrimaryCPICH-Info
				},
				tdd									SEQUENCE{
					cellAndChannelIdentity				CellAndChannelIdentity
				}
			}
		}
	},
	positionEstimate					PositionEstimate
}

UE-Positioning-PositionEstimateInfo-v770ext ::= SEQUENCE {
	referenceTimeOptions				CHOICE {
		-- If 'earlier-than-r7', IE 'UE-Positioning-PositionEstimateInfo' shall be included.
		earlier-than-r7						NULL,
		-- If 'r7', the corresponding IE 'UE-Positioning-PositionEstimateInfo' shall be excluded.
		r7									SEQUENCE {
			referenceTime						CHOICE {
				utran-GANSSReferenceTimeResult		UTRAN-GANSSReferenceTime,
				ganssReferenceTimeOnly				GANSSReferenceTimeOnly
			},
			positionEstimate					PositionEstimate
		}
	},
	positionData						BIT STRING (SIZE (16)),
	velocityEstimate					VelocityEstimate					OPTIONAL,
	ue-Positioning-GPS-ReferenceTimeUncertainty
								UE-Positioning-GPS-ReferenceTimeUncertainty	OPTIONAL
}

UE-Positioning-PositionEstimateInfo-vd20ext ::= SEQUENCE {
	locationTimeStamp					UTCTime OPTIONAL
}

UE-Positioning-ReportCriteria ::=				CHOICE {
	ue-positioning-ReportingCriteria				UE-Positioning-EventParamList,
	periodicalReportingCriteria			PeriodicalReportingCriteria,
	noReporting							NULL
}

UE-Positioning-ReportCriteria-r7 ::=	CHOICE {
	ue-positioning-ReportingCriteria		UE-Positioning-EventParamList-r7,
	periodicalReportingCriteria				PeriodicalReportingCriteria,
	noReporting								NULL
}

UE-Positioning-ReportingQuantity ::=			SEQUENCE {
	methodType							UE-Positioning-MethodType,
	positioningMethod					PositioningMethod,
	-- dummy1 is not used in this version of specification and it should
	-- be ignored.
	dummy1								UE-Positioning-ResponseTime,
	horizontal-Accuracy					UE-Positioning-Accuracy				OPTIONAL,
	gps-TimingOfCellWanted				BOOLEAN,
	-- dummy2 is not used in this version of specification and it should
	-- be ignored.
	dummy2								BOOLEAN,
	additionalAssistanceDataRequest		BOOLEAN,
	environmentCharacterisation			EnvironmentCharacterisation			OPTIONAL
}

UE-Positioning-ReportingQuantity-v390ext ::=		SEQUENCE {
	vertical-Accuracy							UE-Positioning-Accuracy
}

UE-Positioning-ReportingQuantity-r4 ::=			SEQUENCE {
	methodType							UE-Positioning-MethodType,
	positioningMethod					PositioningMethod,
	horizontalAccuracy					UE-Positioning-Accuracy				OPTIONAL,
	verticalAccuracy					UE-Positioning-Accuracy				OPTIONAL,
	gps-TimingOfCellWanted				BOOLEAN,
	additionalAssistanceDataReq			BOOLEAN,
	environmentCharacterisation			EnvironmentCharacterisation			OPTIONAL
}

UE-Positioning-ReportingQuantity-r7 ::= SEQUENCE {
	methodType							UE-Positioning-MethodType,
	positioningMethod					PositioningMethod,
	horizontalAccuracy					UE-Positioning-Accuracy				OPTIONAL,
	verticalAccuracy					UE-Positioning-Accuracy				OPTIONAL,
	gps-TimingOfCellWanted				BOOLEAN,
	additionalAssistanceDataReq			BOOLEAN,
	environmentCharacterisation			EnvironmentCharacterisation			OPTIONAL,
	velocityRequested					ENUMERATED { true }					OPTIONAL,
	gANSSPositioningMethods				BIT STRING (SIZE (16))				OPTIONAL,
	gANSSTimingOfCellWanted				BIT STRING (SIZE (8))				OPTIONAL,
	gANSSCarrierPhaseMeasurementRequested
										BIT STRING (SIZE (8))				OPTIONAL
}

UE-Positioning-ReportingQuantity-r8 ::= SEQUENCE {
	methodType							UE-Positioning-MethodType,
	positioningMethod					PositioningMethod,
	horizontalAccuracy					UE-Positioning-Accuracy				OPTIONAL,
	verticalAccuracy					UE-Positioning-Accuracy				OPTIONAL,
	gps-TimingOfCellWanted				BOOLEAN,
	additionalAssistanceDataReq			BOOLEAN,
	environmentCharacterisation			EnvironmentCharacterisation			OPTIONAL,
	velocityRequested					ENUMERATED { true }					OPTIONAL,
	gANSSPositioningMethods				BIT STRING (SIZE (16))				OPTIONAL,
	gANSSTimingOfCellWanted				BIT STRING (SIZE (8))				OPTIONAL,
	gANSSCarrierPhaseMeasurementRequested
										BIT STRING (SIZE (8))				OPTIONAL,
	gANSSMultiFreqMeasurementRequested	BIT STRING (SIZE (8))				OPTIONAL
}

UE-Positioning-ReportingQuantity-r13 ::= SEQUENCE {
	methodType								UE-Positioning-MethodType,
	positioningMethod						PositioningMethod,
	horizontalAccuracy						UE-Positioning-Accuracy				OPTIONAL,
	verticalAccuracy						UE-Positioning-Accuracy				OPTIONAL,
	gps-TimingOfCellWanted				BOOLEAN,
	additionalAssistanceDataReq			BOOLEAN,
	environmentCharacterisation			EnvironmentCharacterisation			OPTIONAL,
	velocityRequested						ENUMERATED { true }					OPTIONAL,
	gANSSPositioningMethods				BIT STRING (SIZE (16))				OPTIONAL,
	gANSSTimingOfCellWanted				BIT STRING (SIZE (8))					OPTIONAL,
	gANSSCarrierPhaseMeasurementRequested
											BIT STRING (SIZE (8))					OPTIONAL,
	gANSSMultiFreqMeasurementRequested	BIT STRING (SIZE (8))					OPTIONAL,
	additionalPositioningMethods			BIT STRING (SIZE (8))					OPTIONAL
}

UE-Positioning-ResponseTime ::=				ENUMERATED {
										s1, s2, s4, s8, s16,
										s32, s64, s128 }

UE-Positioning-AddPos-MeasuredResults ::= SEQUENCE (SIZE (1..maxAddPos)) OF
												UE-Positioning-AddPos-MeasuredResults-element

UE-Positioning-AddPos-MeasuredResults-element ::=SEQUENCE {
	timestamp							UTCTime OPTIONAL,
	addPos-ID							CHOICE {
	barometricPressure						UE-Positioning-BarometricPressureMeasurement,
	wlan									UE-Positioning-WLANMeasurementList,
	bt										UE-Positioning-BTMeasurementList,
	mbs										UE-Positioning-MBSMeasurementList,
	spare4									NULL,
	spare3									NULL,
	spare2									NULL,
	spare1									NULL
	}
}

UE-Positioning-BarometricPressureMeasurement ::= SEQUENCE {
	ubpMeasurement		 				INTEGER (30000..115000)
}

UE-Positioning-WLANMeasurementList ::=  SEQUENCE (SIZE (1..maxWLANs))OF
											UE-Positioning-WLANMeasurementList-element

UE-Positioning-WLANMeasurementList-element ::=	SEQUENCE {
	wlanBSSID								OCTET STRING (SIZE (6)),
	wlanSSID								OCTET STRING (SIZE(1..32)) 				OPTIONAL,
	wlanRSSI								INTEGER(-127..128) OPTIONAL,
	wlanRTTvalue							INTEGER(0..16777215) OPTIONAL,
	wlanRTTunits							ENUMERATED { microseconds,hundredsofnanoseconds,
															tensofnanoseconds,nanoseconds,
															tenthsofnanosecond,
															spare3, spare2, spare1}	OPTIONAL,
	wlanRTTaccuracy						INTEGER(0..255) 							OPTIONAL,
	wlanAPChannelFrequency				INTEGER(0..256) 							OPTIONAL,
	wlanServingFlag						BOOLEAN 									OPTIONAL
}

UE-Positioning-BTMeasurementList ::= SEQUENCE (SIZE (1..maxBTs)) OF
											UE-Positioning-BTMeasurementList-element

UE-Positioning-BTMeasurementList-element ::= SEQUENCE {
	btAddr									OCTET STRING (SIZE(6)),
	-- Actual value = IE value - 1
	btRSSI									INTEGER(-127..128) OPTIONAL
}

UE-Positioning-MBSMeasurementList ::=	SEQUENCE (SIZE (1..maxBeacons)) OF
											UE-Positioning-MBSMeasurementList-element

UE-Positioning-MBSMeasurementList-element ::= SEQUENCE {
	transmitterId							INTEGER (0..32767),
	codePhase								INTEGER (0..2097151),
	codePhaseRmsError						INTEGER (0..63)
}

UTCmodelSet1 ::=						SEQUENCE {
	utcA0									BIT STRING (SIZE (16)),
	utcA1									BIT STRING (SIZE (13)),
	utcA2									BIT STRING (SIZE (7)),
	utcDeltaTls								BIT STRING (SIZE (8)),
	utcTot									BIT STRING (SIZE (16)),
	utcWNot									BIT STRING (SIZE (13)),
	utcWNlsf								BIT STRING (SIZE (8)),
	utcDN									BIT STRING (SIZE (4)),
	utcDeltaTlsf							BIT STRING (SIZE (8))
}

UTCmodelSet2 ::=						SEQUENCE {
	nA										BIT STRING (SIZE (11)),
	tauC									BIT STRING (SIZE (32)),
	deltaUT1								DeltaUT1							OPTIONAL,
	kp										BIT STRING (SIZE (2))				OPTIONAL
}

UTCmodelSet3 ::=						SEQUENCE {
	utcA1wnt								BIT STRING (SIZE (24)),
	utcA0wnt								BIT STRING (SIZE (32)),
	utcTot									BIT STRING (SIZE (8)),
	utcWNt									BIT STRING (SIZE (8)),
	utcDeltaTls								BIT STRING (SIZE (8)),
	utcWNlsf								BIT STRING (SIZE (8)),
	utcDN									BIT STRING (SIZE (8)),
	utcDeltaTlsf							BIT STRING (SIZE (8)),
	utcStandardID							BIT STRING (SIZE (3))
}

UTCmodelSet4 ::=		SEQUENCE {
	utcA0			BIT STRING (SIZE (32)),
	utcA1			BIT STRING (SIZE (24)),
	utcDeltaTls		BIT STRING (SIZE (8)),
	utcWNlsf		BIT STRING (SIZE (8)),
	utcDN			BIT STRING (SIZE (8)),
	utcDeltaTlsf	BIT STRING (SIZE (8))
}

-- SPARE: UTRA-CarrierRSSI, Max = 76
-- Values above Max are spare
UTRA-CarrierRSSI ::=				INTEGER (0..127)

UTRAN-GANSSReferenceTime ::=		SEQUENCE {
	ue-GANSSTimingOfCellFrames			SEQUENCE {
		-- Actual value [ns] = (ms-Part * 4294967296 + ls-Part) * 250
		-- Actual values [ns] > 86399999999750 are reserved and are considered a protocol error
		ms-Part								INTEGER (0..80),
		ls-Part								INTEGER (0..4294967295)
	},
	gANSS-TimeId						INTEGER (0..7)						OPTIONAL,
	gANSS-TimeUncertainty				INTEGER (0..127)					OPTIONAL,
	mode								CHOICE {
		fdd									SEQUENCE {
			primary-CPICH-Info					PrimaryCPICH-Info
		},
		tdd									SEQUENCE {
			cellParameters						CellParametersID
		}
	},
	referenceSfn						INTEGER (0..4095)
}

UTRAN-FDD-FrequencyList ::=			SEQUENCE (SIZE(1..maxNumFDDFreqs)) OF
										UTRAN-FDD-Frequency

UTRAN-FDD-Frequency ::=				SEQUENCE {
	uarfcn								UARFCN,
	priority							INTEGER (0..maxPrio-1),
	-- Actual value = IE value * 2
	threshXhigh							INTEGER (0..31),
	-- Actual value = IE value * 2
	threshXlow							INTEGER (0..31),
	qQualMinFDD							INTEGER (-24..0)					OPTIONAL,
	-- Actual value = IE value * 2 + 1
	qRxLevMinFDD						INTEGER (-60..-13) 					OPTIONAL
}

UTRAN-TDD-FrequencyList ::=			SEQUENCE (SIZE(1..maxNumTDDFreqs)) OF
										UTRAN-TDD-Frequency

UTRAN-TDD-Frequency ::=				SEQUENCE {
	uarfcn								UARFCN,
	priority							INTEGER (0..maxPrio-1),
	-- Actual value = IE value * 2
	threshXhigh							INTEGER (0..31),
	-- Actual value = IE value * 2
	threshXlow							INTEGER (0..31),
	-- Actual value = IE value * 2 + 1
	qRxLevMinTDD						INTEGER (-60..-13) 					OPTIONAL
}

UTRAN-GPS-DriftRate ::=				ENUMERATED {
									utran-GPSDrift0, utran-GPSDrift1, utran-GPSDrift2,
									utran-GPSDrift5, utran-GPSDrift10, utran-GPSDrift15,
									utran-GPSDrift25, utran-GPSDrift50, utran-GPSDrift-1,
									utran-GPSDrift-2, utran-GPSDrift-5, utran-GPSDrift-10,
									utran-GPSDrift-15, utran-GPSDrift-25, utran-GPSDrift-50}

UTRAN-GPSReferenceTime ::=				SEQUENCE {
	-- For utran-GPSTimingOfCell values above 2322431999999 are not
	-- used in this version of the specification
	-- Actual value utran-GPSTimingOfCell = (ms-part * 4294967296) + ls-part
	utran-GPSTimingOfCell			SEQUENCE {
		ms-part 						INTEGER (0..1023),
		ls-part							INTEGER (0..4294967295)
	},
	modeSpecificInfo				CHOICE {
		fdd								SEQUENCE {
			referenceIdentity				PrimaryCPICH-Info
		},
		tdd								SEQUENCE {
			referenceIdentity				CellParametersID
		}
	} 				OPTIONAL,
	sfn									INTEGER (0..4095)
}

UTRAN-GPSReferenceTimeResult ::=				SEQUENCE {
	-- For ue-GPSTimingOfCell values above 37158911999999 are not
	-- used in this version of the specification
	-- Actual value ue-GPSTimingOfCell = (ms-part * 4294967296) + ls-part
	ue-GPSTimingOfCell			SEQUENCE {
		ms-part 						INTEGER (0.. 16383),
		ls-part							INTEGER (0..4294967295)
	},
	modeSpecificInfo				CHOICE {
		fdd								SEQUENCE {
			referenceIdentity				PrimaryCPICH-Info
		},
		tdd								SEQUENCE {
			referenceIdentity				CellParametersID
		}
	},
	sfn									INTEGER (0..4095)
}

UTRA-PriorityInfoList ::=			SEQUENCE {
	utra-ServingCell					SEQUENCE {
		priority							INTEGER (0..maxPrio-1),
		-- Actual value = IE value * 2
		s-PrioritySearch1					INTEGER (0..31),
		-- Actual value = IE value, default value is 0
		s-PrioritySearch2					INTEGER (0..7)						OPTIONAL,
		-- Actual value = IE value * 2
		threshServingLow					INTEGER (0..31)
	},
	utran-FDD-FrequencyList				UTRAN-FDD-FrequencyList			OPTIONAL,
	utran-TDD-FrequencyList				UTRAN-TDD-FrequencyList			OPTIONAL
}

UTRA-PriorityInfoList-v920ext ::=	SEQUENCE {
	threshServingLow2						INTEGER (0..31) 					OPTIONAL
}

VarianceOfRLC-BufferPayload ::=	ENUMERATED {
										plv0, plv4, plv8, plv16, plv32, plv64,
										plv128, plv256, plv512, plv1024,
										plv2k, plv4k, plv8k, plv16k, spare2, spare1 }

VelocityEstimate ::=				CHOICE {
	horizontalVelocity									HorizontalVelocity,
	horizontalWithVerticalVelocity					HorizontalWithVerticalVelocity,
	horizontalVelocityWithUncertainty				HorizontalVelocityWithUncertainty,
	horizontalWithVerticalVelocityAndUncertainty	HorizontalWithVerticalVelocityAndUncertainty
}

-- Actual value W = IE value * 0.1
W ::=								INTEGER (0..20)

-- ***************************************************
--
--     OTHER INFORMATION ELEMENTS (10.3.8)
--
-- ***************************************************

ACDC-Barring ::= 					CHOICE {
	acdc-Barred						ENUMERATED {true, false},
	acdc-acb-barringBitmap			BIT STRING (SIZE (10))
}

ACDC-Parameters ::= 				SEQUENCE {
	barringRepresentation				CHOICE {
		acdc-ParametersPerPLMN-List		ACDC-ParametersPerPLMN-List,
		acdc-ParametersForAll				ACDC-ParametersForAll
	}
}

ACDC-ParametersForAll ::=			SEQUENCE {
	acdc-Information					SpecificACDC-BarringInformation			OPTIONAL,
	acdcApplicableForRoamer			ENUMERATED { true }						OPTIONAL
}

ACDC-ParametersPerPLMN-List ::= 	SEQUENCE (SIZE (1..6)) OF
										SEQUENCE {
	plmnSpecificACDC-Parameters			SpecificACDC-BarringInformation		OPTIONAL,
	acdcApplicableForRoamer				ENUMERATED { true }					OPTIONAL
}

BCC ::=								INTEGER (0..7)

BCCH-ModificationInfo ::=			SEQUENCE {
	mib-ValueTag						MIB-ValueTag,
	bcch-ModificationTime				BCCH-ModificationTime						OPTIONAL
}

BCCH-ModificationInfo-vc50ext ::= 	SEQUENCE {
	mib-ValueTagExt						MIB-ValueTagExt						OPTIONAL,
	sb3-ValueTag							CellValueTag2							OPTIONAL
}

-- Actual value BCCH-ModificationTime = IE value * 8
BCCH-ModificationTime ::=			INTEGER (0..511)

BSIC ::=							SEQUENCE {
	ncc									NCC,
	bcc									BCC
}

CBS-DRX-Level1Information ::=		SEQUENCE {
	ctch-AllocationPeriod				INTEGER (1..256),
	cbs-FrameOffset					INTEGER (0..255)
}

CBS-DRX-Level1Information-extension-r6 ::=	ENUMERATED {p8, p16, p32, p64, p128, p256}

CDMA2000-Message ::=				SEQUENCE {
	msg-Type							BIT STRING (SIZE (8)),
	payload								BIT STRING (SIZE (1..512))
}

CDMA2000-MessageList ::=				SEQUENCE (SIZE (1..maxInterSysMessages)) OF
											CDMA2000-Message

CDMA2000-UMTS-Frequency-List ::=		SEQUENCE (SIZE (1..maxNumCDMA2000Freqs)) OF
											FrequencyInfoCDMA2000

CellValueTag ::=						INTEGER (1..4)

CellValueTag2 ::=						INTEGER (1..16)

CellValueTagExt ::=					INTEGER (0..3)

CellValueTag3 ::=					SEQUENCE {
	cellValueTag						CellValueTag,
	cellValueTagExt					CellValueTagExt							OPTIONAL
}

DataTransmFrequency ::=			SEQUENCE {
	dataTransmFreqGranularity			ENUMERATED { ms100, ms250, ms500, ms1000,
											ms2000, ms5000, ms10000, ms60000 },
	numberOfDataTransmOcc				INTEGER (1..610)
}

DataVolumeHistory ::=				SEQUENCE {
	dataVolumeMontoringWindow			INTEGER (1..120),
	dataTransmFrequency				DataTransmFrequency						OPTIONAL,
	dataVolumePerRB					DataVolumePerRB-List						OPTIONAL
}

DataVolumePerRB ::=				SEQUENCE {
	rb-Identity						RB-Identity,
	dataVolume							INTEGER (0..4294967295)
}

DataVolumePerRB-List ::=			SEQUENCE (SIZE (1..maxRB)) OF DataVolumePerRB

DeferredMeasurementControlReadingSupport ::= SEQUENCE {
	-- If modeSpecificInfo is not present, deferred SIB11, SIB11bis and SIB12 reading
	-- with default measurement quantities applies
	modeSpecificInfo					CHOICE {
		fdd									SEQUENCE {
			intraFreqMeasQuantity-FDD			IntraFreqMeasQuantity-FDD-sib3
		},
		tdd									SEQUENCE {
			intraFreqMeasQuantity-TDDList		IntraFreqMeasQuantity-TDD-sib3List
		}
	}		OPTIONAL
}

ETWS-Information ::=				SEQUENCE {
	warningType						OCTET STRING (SIZE (1..2)),
	messageIdentifier					OCTET STRING (SIZE (2)),
	serialNumber						OCTET STRING (SIZE (2))
}

-- This IE is not used in the specification.
ETWS-WarningSecurityInfo ::=		OCTET STRING

EUTRA-Exclude-listedCell ::=			SEQUENCE {
	physicalCellIdentity				EUTRA-PhysicalCellIdentity
}

EUTRA-Exclude-listedCellPerFreqList ::= SEQUENCE (SIZE (1..maxEUTRACellPerFreq)) OF
											EUTRA-Exclude-listedCell

EUTRA-PhysicalCellIdentity ::=		INTEGER (0..503)

EUTRA-RadioAccessCapability ::=		SEQUENCE {
	ue-EUTRA-Capability					OCTET STRING
}

EUTRA-TargetFreqInfoList ::=		SEQUENCE (SIZE (1..maxEUTRATargetFreqs)) OF
										EUTRA-TargetFreqInfo

EUTRA-TargetFreqInfoList-vb50ext ::=	SEQUENCE (SIZE (1..maxEUTRATargetFreqs)) OF
											EUTRA-TargetFreqInfo-vb50ext

EUTRA-TargetFreqInfo ::=			SEQUENCE {
	dlEUTRACarrierFreq					EARFCN,
	eutraExclude-listedCellPerFreqList		EUTRA-Exclude-listedCellPerFreqList	OPTIONAL
}

EUTRA-TargetFreqInfo-vb50ext ::=	SEQUENCE {
	earfcn								EARFCNExtension						OPTIONAL
}

--Actual value = 2^(IE value)
ExpirationTimeFactor ::=			INTEGER (1..8)

ExpirationTimeFactor2 ::=			INTEGER (0..15)


ExtGANSS-SchedulingInfo ::=		SEQUENCE {
	extensionGANSS-SIBType			SIB-TypeExtGANSS,
	schedulingInfo						SchedulingInformation,
	valueTagInfo						ValueTagInfo
}

-- For each extended GANSS SIB type the value tag information is added at the end
ExtGANSS-SIBTypeInfoSchedulingInfoList ::= SEQUENCE (SIZE (1..maxGANSS)) OF
										ExtGANSS-SIBTypeInfoSchedulingInfo

ExtGANSS-SIBTypeInfoSchedulingInfo ::= SEQUENCE {
	ganssID										INTEGER (0..7)							OPTIONAL,
	sbasID										UE-Positioning-GANSS-SBAS-ID			OPTIONAL,
	ganssScheduling							SEQUENCE (SIZE (1..maxSIB)) OF
													ExtGANSS-SchedulingInfo
}

-- For each extended SIB type the value tag information is added at the end
ExtSIBTypeInfoSchedulingInfo-List ::=	SEQUENCE (SIZE (1..maxSIB)) OF
												ExtSIBTypeInfoSchedulingInfo

ExtSIBTypeInfoSchedulingInfo ::=	SEQUENCE {
	extensionSIB-Type					SIB-TypeExt,
	schedulingInfo						SchedulingInformation,
	valueTagInfo						ValueTagInfo
}

-- For each extended SIB type the value tag information is added at the end
ExtSIBTypeInfoSchedulingInfo-List2 ::=	SEQUENCE (SIZE (1..maxSIB)) OF
												ExtSIBTypeInfoSchedulingInfo2

ExtSIBTypeInfoSchedulingInfo-List3 ::=	SEQUENCE (SIZE (1..maxSIB)) OF
												ExtSIBTypeInfoSchedulingInfo3

ExtSIBTypeInfoSchedulingInfo2 ::=	SEQUENCE {
	extensionSIB-Type2						SIB-TypeExt2,
	schedulingInfo							SchedulingInformation,
	valueTagInfo							ValueTagInfo
}

ExtSIBTypeInfoSchedulingInfo3 ::=	SEQUENCE {
	extensionSIB-Type3						SIB-TypeExt3,
	schedulingInfo							SchedulingInformation2,
	valueTagInfo							ValueTagInfoExtValueTag
}

FDD-UMTS-Frequency-List ::=			SEQUENCE (SIZE (1..maxNumFDDFreqs)) OF
											-- NOTE1: The IE "UARFCN (Nlow)" corresponds to
											-- "uarfcn-DL" in FrequencyInfoFDD.
											-- NOTE2: The IE "UARFCN (Nupper)" corresponds to
											-- "uarfcn-UL" in FrequencyInfoFDD.
											FrequencyInfoFDD

FrequencyInfoCDMA2000 ::=				SEQUENCE {
											band-Class		BIT STRING (SIZE (5)),
											cdma-Freq		BIT STRING (SIZE(11))
}

GERAN-SystemInfoBlock ::=				OCTET STRING (SIZE (1..23))

GERAN-SystemInformation ::=			SEQUENCE (SIZE (1..maxGERAN-SI)) OF GERAN-SystemInfoBlock

GSM-BA-Range ::= 						SEQUENCE {
											gsmLowRangeUARFCN		UARFCN,
											gsmUpRangeUARFCN		UARFCN
}

GSM-BA-Range-List ::= 				SEQUENCE (SIZE (1..maxNumGSMFreqRanges)) OF
											GSM-BA-Range


-- This IE is formatted as 'TLV' and is coded in the same way as the Mobile Station Classmark 2
-- information element in [5]. The first octet is the Mobile station classmark 2 IEI and its value
-- shall be set to 33H. The second octet is the Length of mobile station classmark 2 and its value
-- shall be set to 3. The octet 3 contains the first octet of the value part of the Mobile Station
-- Classmark 2 information element, the octet 4 contains the second octet of the value part of the
-- Mobile Station Classmark 2 information element and so on. For each of these octets, the first/
-- leftmost/ most significant bit of the octet contains b8 of the corresponding octet of the Mobile
-- Station Classmark 2.
GSM-Classmark2 ::=					OCTET STRING (SIZE (5))

-- This IE is formatted as 'V' and is coded in the same way as the value part in the Mobile station
-- classmark 3 information element in [5]
-- The value part is specified by means of CSN.1, which encoding results in a bit string, to which
-- final padding may be appended upto the next octet boundary [5]. The first/ leftmost bit of the
-- CSN.1 bit string is placed in the first/ leftmost/ most significant bit of the first
-- octet. This continues until the last bit of the CSN.1 bit string, which is placed in the last/
-- rightmost/ least significant bit of the last octet.
GSM-Classmark3 ::=					OCTET STRING (SIZE (1..32))

GSM-MessageList ::=				SEQUENCE (SIZE (1..maxInterSysMessages)) OF
										BIT STRING (SIZE (1..512))

GSM-MS-RadioAccessCapability ::=	OCTET STRING (SIZE (1..64))

GsmSecurityCapability ::=			BIT STRING {
										-- For each bit value "0" means false/ not supported
										a5-7(0),
										a5-6(1),
									 	a5-5(2),
									 	a5-4(3),
									 	a5-3(4),
									 	a5-2(5),
									 	a5-1(6)
										}	(SIZE (7))

GSM-TargetCellInfoList ::=		SEQUENCE (SIZE (1..maxGSMTargetCells)) OF
										GSM-TargetCellInfo


GSM-TargetCellInfo ::= 			SEQUENCE {
	bcch-ARFCN							BCCH-ARFCN,
	frequency-band						Frequency-Band,
	bsic								BSIC			OPTIONAL
}

HNBName ::=						OCTET STRING (SIZE(1..maxHNBNameSize))

IdentificationOfReceivedMessage ::=	SEQUENCE {
		rrc-TransactionIdentifier			RRC-TransactionIdentifier,
		receivedMessageType				ReceivedMessageType
}

InterRAT-ChangeFailureCause ::=	CHOICE {
	configurationUnacceptable			NULL,
	physicalChannelFailure			NULL,
	protocolError						ProtocolErrorInformation,
	unspecified						NULL,
	spare4								NULL,
	spare3								NULL,
	spare2								NULL,
	spare1								NULL
}

GERANIu-MessageList ::=			SEQUENCE (SIZE (1..maxInterSysMessages)) OF
										BIT STRING (SIZE (1..32768))

GERANIu-RadioAccessCapability ::=	BIT STRING (SIZE (1..170))

InterRAT-UE-RadioAccessCapability ::= CHOICE {
	gsm										SEQUENCE {
		gsm-Classmark2							GSM-Classmark2,
		gsm-Classmark3							GSM-Classmark3
	},
	cdma2000								SEQUENCE {
		cdma2000-MessageList					CDMA2000-MessageList
	}
}

InterRAT-UE-RadioAccessCapabilityList ::= 	SEQUENCE (SIZE(1..maxInterSysMessages)) OF
											InterRAT-UE-RadioAccessCapability

InterRAT-UE-RadioAccessCapability-v590ext ::= SEQUENCE {
	geranIu-RadioAccessCapability		GERANIu-RadioAccessCapability
}

InterRAT-UE-RadioAccessCapability-v690ext ::= SEQUENCE {
	supportOfInter-RAT-PS-Handover		ENUMERATED { doesSupporInter-RAT-PS-Handover }	OPTIONAL,
	gsm-MS-RadioAccessCapability			GSM-MS-RadioAccessCapability
}

InterRAT-UE-RadioAccessCapability-v860ext ::= SEQUENCE {
	eutra-RadioAccessCapability			EUTRA-RadioAccessCapability				OPTIONAL
}

InterRAT-UE-SecurityCapability ::= CHOICE {
	gsm									SEQUENCE {
		gsmSecurityCapability			GsmSecurityCapability
	}
}

InterRAT-UE-SecurityCapList ::= 	SEQUENCE (SIZE(1..maxInterSysMessages)) OF
										InterRAT-UE-SecurityCapability

InterRAT-HO-FailureCause ::=		CHOICE {
	configurationUnacceptable			NULL,
	physicalChannelFailure			NULL,
	protocolError						ProtocolErrorInformation,
	interRAT-ProtocolError			NULL,
	unspecified						NULL,
	spare11								NULL,
	spare10								NULL,
	spare9								NULL,
	spare8								NULL,
	spare7								NULL,
	spare6								NULL,
	spare5								NULL,
	spare4								NULL,
	spare3								NULL,
	spare2								NULL,
	spare1								NULL
}

MasterInformationBlock ::=		SEQUENCE {
		mib-ValueTag					MIB-ValueTag,
		-- TABULAR: The PLMN identity and ANSI-41 core network information
		-- are included in PLMN-Type.
		plmn-Type						PLMN-Type,
		sibSb-ReferenceList			SIBSb-ReferenceList,
	-- Extension mechanism for non- release99 information
		v690NonCriticalExtensions			SEQUENCE {
			masterInformationBlock-v690ext		MasterInformationBlock-v690ext,
			v6b0NonCriticalExtensions			SEQUENCE {
				masterInformationBlock-v6b0ext		MasterInformationBlock-v6b0ext-IEs,
				v860NonCriticalExtensions			SEQUENCE {
					masterInformationBlock-v860ext		MasterInformationBlock-v860ext-IEs,
					vc50NonCriticalExtensions			SEQUENCE {
						masterInformationBlock-vc50ext		MasterInformationBlock-vc50ext-IEs,
						nonCriticalExtensions				SEQUENCE {}							OPTIONAL
					}	OPTIONAL
				}	OPTIONAL
			}	OPTIONAL
		}	OPTIONAL
}

MasterInformationBlock-v690ext ::=	SEQUENCE {
	multiplePLMN-List						MultiplePLMN-List-r6						OPTIONAL
}

MasterInformationBlock-v6b0ext-IEs ::=	SEQUENCE {
	extSIBTypeInfoSchedulingInfo-List		ExtSIBTypeInfoSchedulingInfo-List	OPTIONAL
}

MasterInformationBlock-v860ext-IEs ::=	SEQUENCE {
	extSIBTypeInfoSchedulingInfo-List		ExtSIBTypeInfoSchedulingInfo-List2	OPTIONAL,
	extGANSS-SIBTypeInfoSchedulingInfoList
										ExtGANSS-SIBTypeInfoSchedulingInfoList		OPTIONAL,
	csg-Indicator								ENUMERATED { true }					OPTIONAL
}

MasterInformationBlock-vc50ext-IEs ::=	SEQUENCE {
	mib-ValueTagExt							MIB-ValueTagExt						OPTIONAL,
	sibSb-ReferenceList						SIBSb-ReferenceList2					OPTIONAL,
	extSIBTypeInfoSchedulingInfo-List		ExtSIBTypeInfoSchedulingInfo-List3	OPTIONAL,
	sb3-Information							SB3-Information						OPTIONAL
}

SB3-Information ::=	SEQUENCE {
	sb3-SegCount						SegCount										DEFAULT 1,
	sb3-Sib-Rep						SIB-Rep,
	second-BCH-Channelizationcode	BCH-Channelizationcode
}

MIB-ValueTag ::=					INTEGER (1..8)

MIB-ValueTagExt ::=				INTEGER (0..1)

NCC ::=								INTEGER (0..7)

PLMN-ValueTag ::=					INTEGER (1..256)


PredefinedConfigIdentityAndValueTag ::=	SEQUENCE {
	predefinedConfigIdentity					PredefinedConfigIdentity,
	predefinedConfigValueTag					PredefinedConfigValueTag
}

ProtocolErrorInformation ::=		SEQUENCE {
	diagnosticsType					CHOICE {
		type1								SEQUENCE {
			protocolErrorCause					ProtocolErrorCause
		},
		spare								NULL
	}
}

ReceivedMessageType ::=			ENUMERATED {
										activeSetUpdate,
										cellChangeOrderFromUTRAN,
										cellUpdateConfirm,
										counterCheck,
										downlinkDirectTransfer,
										interRATHandoverCommand,
										measurementControl,
										pagingType2,
										physicalChannelReconfiguration,
										physicalSharedChannelAllocation,
										radioBearerReconfiguration,
										radioBearerRelease,
										radioBearerSetup,
										rrcConnectionRelease,
										rrcConnectionReject,
										rrcConnectionSetup,
										securityModeCommand,
										signallingConnectionRelease,
										transportChannelReconfiguration,
										transportFormatCombinationControl,
										ueCapabilityEnquiry,
										ueCapabilityInformationConfirm,
										uplinkPhysicalChannelControl,
										uraUpdateConfirm,
										utranMobilityInformation,
										assistanceDataDelivery,
										spare6, spare5, spare4, spare3, spare2,
										spare1
}

Rplmn-Information ::=			SEQUENCE {
	gsm-BA-Range-List				GSM-BA-Range-List						OPTIONAL,
	fdd-UMTS-Frequency-List		FDD-UMTS-Frequency-List				OPTIONAL,
	tdd-UMTS-Frequency-List		TDD-UMTS-Frequency-List				OPTIONAL,
	cdma2000-UMTS-Frequency-List	CDMA2000-UMTS-Frequency-List			OPTIONAL
}

Rplmn-Information-r4 ::=		SEQUENCE {
	gsm-BA-Range-List				GSM-BA-Range-List						OPTIONAL,
	fdd-UMTS-Frequency-List		FDD-UMTS-Frequency-List				OPTIONAL,
	-- the option is the same for 7.68 Mcps TDD as for 3.84 Mcps TDD
	-- i.e. TDD-UMTS-Frequency-List applies
	tdd384-UMTS-Frequency-List	TDD-UMTS-Frequency-List				OPTIONAL,
	tdd128-UMTS-Frequency-List	TDD-UMTS-Frequency-List				OPTIONAL,
	cdma2000-UMTS-Frequency-List	CDMA2000-UMTS-Frequency-List			OPTIONAL
}

SIB-Rep::=			ENUMERATED {
						frame-8,
						frame-16,
						frame-32,
						frame-64
}

BCH-Channelizationcode ::=			INTEGER (2..33)

SchedulingInformation ::=			SEQUENCE {
	scheduling							SEQUENCE {
		segCount							SegCount				 		 DEFAULT 1,
		sib-Pos								CHOICE {
			-- The element name indicates the repetition period and the value
			-- (multiplied by two) indicates the position of the first segment.
			rep4								INTEGER (0..1),
			rep8								INTEGER (0..3),
			rep16								INTEGER (0..7),
			rep32								INTEGER (0..15),
			rep64								INTEGER (0..31),
			rep128								INTEGER (0..63),
			rep256								INTEGER (0..127),
			rep512								INTEGER (0..255),
			rep1024								INTEGER (0..511),
			rep2048								INTEGER (0..1023),
			rep4096								INTEGER (0..2047)
		},
		sib-PosOffsetInfo					SibOFF-List						OPTIONAL
	}
}

SchedulingInformation2 ::=	CHOICE {
	scheduling						SEQUENCE {
		segCount						SegCount						OPTIONAL,
		sib-Pos							CHOICE {
			-- The element name indicates the repetition period and the value
			-- (multiplied by two) indicates the position of the first segment.
			rep4								INTEGER (0..1),
			rep8								INTEGER (0..3),
			rep16								INTEGER (0..7),
			rep32								INTEGER (0..15),
			rep64								INTEGER (0..31),
			rep128								INTEGER (0..63),
			rep256								INTEGER (0..127),
			rep512								INTEGER (0..255),
			rep1024								INTEGER (0..511),
			rep2048								INTEGER (0..1023),
			rep4096								INTEGER (0..2047)
		},
		sib-PosOffsetInfo					SibOFF-List2					OPTIONAL
	}
}

SchedulingInformationSIB ::=		SEQUENCE {
	sib-Type							SIB-TypeAndTag,
	scheduling							SchedulingInformation
}

SchedulingInformationSIB2 ::=		SEQUENCE {
	sib-Type							SIB-TypeAndTag2,
	scheduling							SchedulingInformation2
}

SchedulingInformationSIBSb ::=	SEQUENCE {
	sibSb-Type							SIBSb-TypeAndTag,
	scheduling							SchedulingInformation
}

SchedulingInformationSIBSb2 ::=	SEQUENCE {
	sibSb-Type							SIBSb-TypeAndTagExtValueTag
}

SegCount ::=						INTEGER (1..16)

SegmentIndex ::=					INTEGER (1..15)

-- Actual value SFN-Prime = 2 * IE value
SFN-Prime ::=						INTEGER (0..2047)


SIB-Data-fixed ::=					BIT STRING (SIZE (222))

SIB-Data2-fixed ::=				BIT STRING (SIZE (232))

SIB-Data-variable ::=				BIT STRING (SIZE (1..214))

SIB-Data2-variable ::=			BIT STRING (SIZE (1..224))

SIBOccurIdentity ::=				INTEGER (0..15)

SIBOccurrenceIdentityAndValueTag ::=	SEQUENCE {
	sibOccurIdentity						SIBOccurIdentity,
	sibOccurValueTag						SIBOccurValueTag
}

SIBOccurValueTag ::=			INTEGER (0..15)

SIB-ReferenceList ::=				SEQUENCE (SIZE (1..maxSIB)) OF
										SchedulingInformationSIB

SIB-ReferenceList2 ::=			SEQUENCE (SIZE (1..maxSIB2)) OF
										SchedulingInformationSIB2

SIBSb-ReferenceList ::=			SEQUENCE (SIZE (1..maxSIB)) OF
										SchedulingInformationSIBSb

SIBSb-ReferenceList2 ::=			SEQUENCE (SIZE (1..maxSIB)) OF
										SchedulingInformationSIBSb2

SIB-ReferenceListFACH ::=			SEQUENCE (SIZE (1..maxSIB-FACH)) OF
										SchedulingInformationSIB

SIB-Type ::=						ENUMERATED {
										masterInformationBlock,
										systemInformationBlockType1,
										systemInformationBlockType2,
										systemInformationBlockType3,
										systemInformationBlockType4,
										systemInformationBlockType5,
										systemInformationBlockType6,
										systemInformationBlockType7,
		-- dummy, dummy2 and dummy3 are not used in this version of the specification,
		-- they should not be sent. If they are received they should be ignored
										dummy,
										dummy2,
										dummy3,
										systemInformationBlockType11,
										systemInformationBlockType12,
										systemInformationBlockType13,
										systemInformationBlockType13-1,
										systemInformationBlockType13-2,
										systemInformationBlockType13-3,
										systemInformationBlockType13-4,
										systemInformationBlockType14,
										systemInformationBlockType15,
										systemInformationBlockType15-1,
										systemInformationBlockType15-2,
										systemInformationBlockType15-3,
										systemInformationBlockType16,
										systemInformationBlockType17,
										systemInformationBlockType15-4,
										systemInformationBlockType18,
										schedulingBlock1,
										schedulingBlock2,
										systemInformationBlockType15-5,
										systemInformationBlockType5bis,
										extensionType }

SIB-Type2 ::=						ENUMERATED {
										schedulingBlock3,
										systemInformationBlockType1,
										systemInformationBlockType2,
										systemInformationBlockType3,
										systemInformationBlockType4,
										systemInformationBlockType5,
										systemInformationBlockType5bis,
										systemInformationBlockType6,
										systemInformationBlockType7,
										systemInformationBlockType11,
										systemInformationBlockType11bis,
										systemInformationBlockType12,
										systemInformationBlockType13,
										systemInformationBlockType13-1,
										systemInformationBlockType13-2,
										systemInformationBlockType13-3,
										systemInformationBlockType13-4,
										systemInformationBlockType14,
										systemInformationBlockType15,
										systemInformationBlockType15bis,
										systemInformationBlockType15-1,
										systemInformationBlockType15-1bis,
										systemInformationBlockType15-1ter,
										systemInformationBlockType15-2,
										systemInformationBlockType15-2bis,
										systemInformationBlockType15-2ter,
										systemInformationBlockType15-3,
										systemInformationBlockType15-3bis,
										systemInformationBlockType15-4,
										systemInformationBlockType15-5,
										systemInformationBlockType15-6,
										systemInformationBlockType15-7,
										systemInformationBlockType15-8,
										systemInformationBlockType16,
										systemInformationBlockType17,
										systemInformationBlockType18,
										systemInformationBlockType19,
										systemInformationBlockType20,
										systemInformationBlockType21,
										systemInformationBlockType22,
										systemInformationBlockType23,
										systemInformationBlockType24,
										systemInformationBlockType11ter,
										systemInformationBlockType25,
										spare20, spare19, spare18,
										spare17, spare16, spare15, spare14, spare13, spare12,
										spare11, spare10, spare9, spare8, spare7, spare6,
										spare5,
										spare4, spare3, spare2, spare1 }

SIB-TypeAndTag ::=					CHOICE {
	sysInfoType1						PLMN-ValueTag,
	sysInfoType2						CellValueTag,
	sysInfoType3						CellValueTag,
	sysInfoType4						CellValueTag,
	sysInfoType5						CellValueTag,
	sysInfoType6						CellValueTag,
	sysInfoType7						NULL,
	-- dummy, dummy2 and dummy3 are not used in this version of the specification,
	-- they should not be sent. If they are received the UE behaviour is not specified.
	dummy								CellValueTag,
	dummy2								NULL,
	dummy3								NULL,
	sysInfoType11						CellValueTag,
	sysInfoType12 						CellValueTag,
	sysInfoType13						CellValueTag,
	sysInfoType13-1					CellValueTag,
	sysInfoType13-2					CellValueTag,
	sysInfoType13-3					CellValueTag,
	sysInfoType13-4					CellValueTag,
	sysInfoType14						NULL,
	sysInfoType15						CellValueTag,
	sysInfoType16						PredefinedConfigIdentityAndValueTag,
	sysInfoType17						NULL,
	sysInfoType15-1					CellValueTag,
	sysInfoType15-2					SIBOccurrenceIdentityAndValueTag,
	sysInfoType15-3					SIBOccurrenceIdentityAndValueTag,
	sysInfoType15-4					CellValueTag,
	sysInfoType18						CellValueTag,
	sysInfoType15-5					CellValueTag,
	sysInfoType5bis					CellValueTag,
	spare4								NULL,
	spare3								NULL,
	spare2								NULL,
	spare1								NULL
}

SIB-TypeAndTag2 ::=				CHOICE {
	sysInfoType1						PLMN-ValueTag,
	sysInfoType2						CellValueTag,
	sysInfoType3						CellValueTag3,
	sysInfoType4						CellValueTag,
	sysInfoType5						CellValueTag3,
	sysInfoType5bis					CellValueTag3,
	sysInfoType6						CellValueTag,
	sysInfoType7						NULL,
	sysInfoType11						CellValueTag,
	sysInfoType11bis					CellValueTag,
	sysInfoType12 						CellValueTag,
	sysInfoType13						CellValueTag,
	sysInfoType13-1					CellValueTag,
	sysInfoType13-2					CellValueTag,
	sysInfoType13-3					CellValueTag,
	sysInfoType13-4					CellValueTag,
	sysInfoType14						NULL,
	sysInfoType15						CellValueTag,
	sysInfoType15bis					CellValueTag,
	sysInfoType15-1					CellValueTag,
	sysInfoType15-1bis					CellValueTag,
	sysInfoType15-1ter					CellValueTag,
	sysInfoType15-2					SIBOccurrenceIdentityAndValueTag,
	sysInfoType15-2bis					SIBOccurrenceIdentityAndValueTag,
	sysInfoType15-2ter					SIBOccurrenceIdentityAndValueTag,
	sysInfoType15-3					SIBOccurrenceIdentityAndValueTag,
	sysInfoType15-3bis					SIBOccurrenceIdentityAndValueTag,
	sysInfoType15-4					CellValueTag,
	sysInfoType15-5					CellValueTag,
	sysInfoType15-6					CellValueTag,
	sysInfoType15-7					CellValueTag,
	sysInfoType15-8					CellValueTag,
	sysInfoType16						PredefinedConfigIdentityAndValueTag,
	sysInfoType17						NULL,
	sysInfoType18						CellValueTag,
	sysInfoType19						CellValueTag,
	sysInfoType20						CellValueTag,
	sysInfoType21						CellValueTag3,
	sysInfoType22						CellValueTag3,
	sysInfoType23						CellValueTag,
	sysInfoType24						NULL,
	sysInfoType11ter					CellValueTag3,
	sysInfoType25						NULL,
	spare21								NULL,
	spare20								NULL,
	spare19								NULL,
	spare18								NULL,
	spare17								NULL,
	spare16								NULL,
	spare15								NULL,
	spare14								NULL,
	spare13								NULL,
	spare12								NULL,
	spare11								NULL,
	spare10								NULL,
	spare9								NULL,
	spare8								NULL,
	spare7								NULL,
	spare6								NULL,
	spare5								NULL,
	spare4								NULL,
	spare3								NULL,
	spare2								NULL,
	spare1								NULL
}

SIBSb-TypeAndTag ::=				CHOICE {
	sysInfoType1						PLMN-ValueTag,
	sysInfoType2						CellValueTag,
	sysInfoType3						CellValueTag,
	sysInfoType4						CellValueTag,
	sysInfoType5						CellValueTag,
	sysInfoType6						CellValueTag,
	sysInfoType7						NULL,
	-- dummy, dummy2 and dummy3 are not used in this version of the specification,
	-- they should not be sent. If they are received the UE behaviour is not specified.
	dummy								CellValueTag,
	dummy2								NULL,
	dummy3								NULL,
	sysInfoType11						CellValueTag,
	sysInfoType12 						CellValueTag,
	sysInfoType13						CellValueTag,
	sysInfoType13-1					CellValueTag,
	sysInfoType13-2					CellValueTag,
	sysInfoType13-3					CellValueTag,
	sysInfoType13-4					CellValueTag,
	sysInfoType14						NULL,
	sysInfoType15						CellValueTag,
	sysInfoType16						PredefinedConfigIdentityAndValueTag,
	sysInfoType17						NULL,
	sysInfoTypeSB1						CellValueTag,
	sysInfoTypeSB2						CellValueTag,
	sysInfoType15-1					CellValueTag,
	sysInfoType15-2					SIBOccurrenceIdentityAndValueTag,
	sysInfoType15-3					SIBOccurrenceIdentityAndValueTag,
	sysInfoType15-4					CellValueTag,
	sysInfoType18						CellValueTag,
	sysInfoType15-5					CellValueTag,
	sysInfoType5bis					CellValueTag,
	spare2								NULL,
	spare1								NULL
}


SIBSb-TypeAndTagExtValueTag ::=	CHOICE {
	sysInfoType3						CellValueTagExt,
	sysInfoType5						CellValueTagExt,
	sysInfoType5bis					CellValueTagExt,
	sysInfoType21						CellValueTagExt,
	sysInfoType22						CellValueTagExt,
	spare3								NULL,
	spare2								NULL,
	spare1								NULL
}

SIB-TypeExt ::=					CHOICE {
	systemInfoType11bis				NULL,
	systemInfoType15bis				NULL,
	systemInfoType15-1bis				NULL,
	systemInfoType15-2bis				NULL,
	systemInfoType15-3bis				NULL,
	systemInfoType15-6					NULL,
	systemInfoType15-7					NULL,
	systemInfoType15-8					NULL
}

SIB-TypeExt2 ::=					CHOICE {
	systemInfoType19					NULL,
	systemInfoType15-2ter				NULL,
	systemInfoType20					NULL,
	systemInfoType21					NULL,
	systemInfoType22					NULL,
	systemInfoType15-1ter				NULL,
	systemInfoType23					NULL,
	systemInfoType24					NULL
}

SIB-TypeExt3 ::=					CHOICE {
	systemInfoType11ter				NULL,
	systemInfoType25					NULL,
	spare6								NULL,
	spare5								NULL,
	spare4								NULL,
	spare3								NULL,
	spare2								NULL,
	spare1								NULL
}

SIB-TypeExtGANSS ::=				CHOICE {
	systemInfoType15-1bis				NULL,
	systemInfoType15-2bis				NULL,
	systemInfoType15-2ter				NULL,
	systemInfoType15-3bis				NULL,
	systemInfoType15-6					NULL,
	systemInfoType15-7					NULL,
	systemInfoType15-8					NULL,
	spare9								NULL,
	spare8								NULL,
	spare7								NULL,
	spare6								NULL,
	spare5								NULL,
	spare4								NULL,
	spare3								NULL,
	spare2								NULL,
	spare1								NULL
}

SibOFF ::=							ENUMERATED {
										so2, so4, so6, so8, so10,
										so12, so14, so16, so18,
										so20, so22, so24, so26,
										so28, so30, so32 }

SibOFF-vc50ext ::=					SEQUENCE {
	sibOFF								SibOFF							OPTIONAL
}

SibOFF-List ::=					SEQUENCE (SIZE (1..15)) OF
										SibOFF

SibOFF-List2 ::=					SEQUENCE (SIZE (1..15)) OF
										SibOFF-vc50ext

SpecificACDC-BarringInformation ::=		SEQUENCE (SIZE (1.. maxNumAcdcCategory)) OF
												SEQUENCE {
	acdc-Barring									ACDC-Barring					OPTIONAL,
	expirationTimeFactor							ExpirationTimeFactor2			OPTIONAL
}

SysInfoType1 ::=					SEQUENCE {
	-- Core network IEs
		cn-CommonGSM-MAP-NAS-SysInfo	NAS-SystemInformationGSM-MAP,
		cn-DomainSysInfoList			CN-DomainSysInfoList,
	-- User equipment IEs
		ue-ConnTimersAndConstants		UE-ConnTimersAndConstants			OPTIONAL,
		ue-IdleTimersAndConstants		UE-IdleTimersAndConstants			OPTIONAL,
	-- Extension mechanism for non- release99 information
		v3a0NonCriticalExtensions		SEQUENCE {
			sysInfoType1-v3a0ext			SysInfoType1-v3a0ext-IEs,
			v860NonCriticalExtentions		SEQUENCE {
				sysInfoType1-v860ext			SysInfoType1-v860ext-IEs,
				nonCriticalExtensions			SEQUENCE {} OPTIONAL
			}							OPTIONAL
		}							OPTIONAL
}

SysInfoType1-v3a0ext-IEs ::=	SEQUENCE {
	ue-ConnTimersAndConstants-v3a0ext		UE-ConnTimersAndConstants-v3a0ext,
	ue-IdleTimersAndConstants-v3a0ext		UE-IdleTimersAndConstants-v3a0ext
}

SysInfoType1-v860ext-IEs ::=	SEQUENCE {
	ue-ConnTimersAndConstants				UE-ConnTimersAndConstants-v860ext
}

SysInfoType2 ::=				SEQUENCE {
	-- UTRAN mobility IEs
		ura-IdentityList				URA-IdentityList,
	-- Extension mechanism for non- release99 information
		nonCriticalExtensions			SEQUENCE {}							OPTIONAL
}

SysInfoType3 ::=				SEQUENCE {
		sib4indicator					BOOLEAN,
	-- UTRAN mobility IEs
		cellIdentity					CellIdentity,
		cellSelectReselectInfo			CellSelectReselectInfoSIB-3-4,
		cellAccessRestriction			CellAccessRestriction,
	-- Extension mechanism for non- release99 information
		v4b0NonCriticalExtensions		SEQUENCE {
			sysInfoType3-v4b0ext			SysInfoType3-v4b0ext-IEs,
			v590NonCriticalExtension		SEQUENCE {
				sysInfoType3-v590ext			SysInfoType3-v590ext,
				v5c0NoncriticalExtension		SEQUENCE {
					sysInfoType3-v5c0ext			SysInfoType3-v5c0ext-IEs,
					v670NonCriticalExtension			SEQUENCE {
						sysInfoType3-v670ext				SysInfoType3-v670ext,
						v770NonCriticalExtension			SEQUENCE {
							sysInfoType3-v770ext				SysInfoType3-v770ext-IEs,
							v830NonCriticalExtension			SEQUENCE {
								sysInfoType3-v830ext				SysInfoType3-v830ext-IEs,
								v860NonCriticalExtension			SEQUENCE {
									sysInfoType3-v860ext				SysInfoType3-v860ext-IEs,
									v870NonCriticalExtension			SEQUENCE {
										sysInfoType3-v870ext			SysInfoType3-v870ext-IEs,
										v900NonCriticalExtension		SEQUENCE {
											sysInfoType3-v920ext		SysInfoType3-v920ext-IEs,
											vc50NonCriticalExtension		SEQUENCE {
												sysInfoType3-vc50ext		SysInfoType3-vc50ext-IEs,
												nonCriticalExtensions	SEQUENCE {}	OPTIONAL
											}							OPTIONAL
										}							OPTIONAL
									}							OPTIONAL
								}							OPTIONAL
							}							OPTIONAL
						}							OPTIONAL
					}							OPTIONAL
				}							OPTIONAL
			}							OPTIONAL
		}							OPTIONAL
}

SysInfoType3-v4b0ext-IEs ::=	SEQUENCE {
	mapping-LCR					Mapping-LCR-r4							OPTIONAL
}

SysInfoType3-v590ext ::=	SEQUENCE {
	cellSelectReselectInfo-v590ext	CellSelectReselectInfo-v590ext 		OPTIONAL
}

SysInfoType3-v5c0ext-IEs ::=	SEQUENCE {
	cellSelectReselectInfoTreselectionScaling-v5c0ext
										CellSelectReselectInfoTreselectionScaling-v5c0ext	OPTIONAL
}

SysInfoType3-v670ext ::=	SEQUENCE {
	 	domainSpecificAccessRestrictionParametersForPLMNOfMIB
									DomainSpecificAccessRestrictionParam-v670ext	OPTIONAL,
		domainSpecificAccessRestictionForSharedNetwork
									DomainSpecificAccessRestrictionForSharedNetwork-v670ext	OPTIONAL
}

SysInfoType3-v770ext-IEs ::=		SEQUENCE {
	deferredMeasurementControlReadingSupport
											DeferredMeasurementControlReadingSupport	OPTIONAL,
	q-QualMin-Offset						Q-QualMin-Offset				OPTIONAL,
	q-RxlevMin-Offset						Q-RxlevMin-Offset				OPTIONAL,
	mbsfnOnlyService						MBSFNOnlyService				OPTIONAL
}

SysInfoType3-v830ext-IEs ::=		SEQUENCE {
	pagingPermissionWithAccessControlParametersForPLMNOfMIB
										PagingPermissionWithAccessControlParameters		OPTIONAL,
	pagingPermissionWithAccessControlParametersForSharedNetwork
										PagingPermissionWithAccessControlForSharedNetwork	OPTIONAL
}

SysInfoType3-v860ext-IEs ::=		SEQUENCE {
	csgIdentity						CSG-Identity							OPTIONAL,
	csg-PSCSplitInfo					CSG-PSCSplitInfo						OPTIONAL
}

SysInfoType3-v870ext-IEs ::=		SEQUENCE {
	cellAccessRestriction				CellAccessRestriction-v870ext		OPTIONAL
}

SysInfoType3-v920ext-IEs ::=		SEQUENCE {
	imsEmergencySupportIndicator		ENUMERATED { supported }			OPTIONAL
}

SysInfoType3-vc50ext-IEs ::=		SEQUENCE {
	txFailParams						TxFailParams						OPTIONAL
}

SysInfoType4 ::=					SEQUENCE {
	-- UTRAN mobility IEs
		cellIdentity					CellIdentity,
		cellSelectReselectInfo		CellSelectReselectInfoSIB-3-4,
		cellAccessRestriction			CellAccessRestriction,
	-- Extension mechanism for non- release99 information
		v4b0NonCriticalExtensions		SEQUENCE {
			sysInfoType4-v4b0ext			SysInfoType4-v4b0ext-IEs,
			v590NonCriticalExtension		SEQUENCE {
				sysInfoType4-v590ext			SysInfoType4-v590ext,
				v5b0NonCriticalExtension		SEQUENCE {
					sysInfoType4-v5b0ext			SysInfoType4-v5b0ext-IEs,
					v5c0NonCriticalExtension			SEQUENCE {
						sysInfoType4-v5c0ext				SysInfoType4-v5c0ext-IEs,
						nonCriticalExtensions			SEQUENCE {}		OPTIONAL
					}	OPTIONAL
				}	OPTIONAL
			}	OPTIONAL
		}	OPTIONAL
}

SysInfoType4-v4b0ext-IEs ::=	SEQUENCE {
	mapping-LCR					Mapping-LCR-r4							OPTIONAL
}


SysInfoType4-v590ext ::=	SEQUENCE {
	cellSelectReselectInfo-v590ext		CellSelectReselectInfo-v590ext		OPTIONAL
}

SysInfoType4-v5b0ext-IEs ::=	SEQUENCE {
	cellSelectReselectInfoPCHFACH-v5b0ext	CellSelectReselectInfoPCHFACH-v5b0ext		OPTIONAL
}

SysInfoType4-v5c0ext-IEs ::=	SEQUENCE {
	cellSelectReselectInfoTreselectionScaling-v5c0ext
										CellSelectReselectInfoTreselectionScaling-v5c0ext	OPTIONAL
}

SysInfoType5 ::=				SEQUENCE {
		sib6indicator				BOOLEAN,
	-- Physical channel IEs
		pich-PowerOffset			PICH-PowerOffset,
		modeSpecificInfo			CHOICE {
			fdd								SEQUENCE {
				aich-PowerOffset				AICH-PowerOffset
			},
			tdd								SEQUENCE {
	-- If PDSCH/PUSCH is configured for 1.28Mcps or 7.68Mcps TDD, the following IEs should be absent
	-- and the info included in the respective tdd128SpecificInfo or tdd768SpecificInfo instead.
	-- If PDSCH/PUSCH is configured for 3.84Mcps TDD in R5, HCR-r5-SpecificInfo should also be
	-- included.
				pusch-SysInfoList-SFN			PUSCH-SysInfoList-SFN		OPTIONAL,
				pdsch-SysInfoList-SFN			PDSCH-SysInfoList-SFN		OPTIONAL,
				openLoopPowerControl-TDD		OpenLoopPowerControl-TDD
			}
		},
		primaryCCPCH-Info				PrimaryCCPCH-Info					OPTIONAL,
		prach-SystemInformationList	PRACH-SystemInformationList,
		sCCPCH-SystemInformationList	SCCPCH-SystemInformationList,
		-- cbs-DRX-Level1Information is conditional on any of the CTCH indicator IEs in
		-- sCCPCH-SystemInformationList
		cbs-DRX-Level1Information		CBS-DRX-Level1Information			OPTIONAL,
	-- Extension mechanism for non- release99 information
		v4b0NonCriticalExtensions		SEQUENCE {
			sysInfoType5-v4b0ext			SysInfoType5-v4b0ext-IEs		OPTIONAL,
		-- Extension mechanism for non- rel-4 information
			v590NonCriticalExtensions		SEQUENCE {
				sysInfoType5-v590ext			SysInfoType5-v590ext-IEs		OPTIONAL,
				v650NonCriticalExtensions		SEQUENCE {
					sysInfoType5-v650ext			SysInfoType5-v650ext-IEs		OPTIONAL,
					v680NonCriticalExtensions		SEQUENCE {
						sysInfoType5-v680ext			SysInfoType5-v680ext-IEs		OPTIONAL,
						v690NonCriticalExtensions		SEQUENCE {
							sysInfoType5-v690ext			SysInfoType5-v690ext-IEs,
							v770NonCriticalExtensions		SEQUENCE {
								sysInfoType5-v770ext			SysInfoType5-v770ext-IEs,
								v860NonCriticalExtensions		SEQUENCE {
									sysInfoType5-v860ext			SysInfoType5-v860ext-IEs,
									v890NonCriticalExtensions		SEQUENCE {
										sysInfoType5-v890ext			SysInfoType5-v890ext-IEs,
										v8b0NonCriticalExtensions		SEQUENCE {
											sysInfoType5-v8b0ext
																		SysInfoType5-v8b0ext-IEs,
											v8d0NonCriticalExtensions		SEQUENCE {
												sysInfoType5-v8d0ext
																			SysInfoType5-v8d0ext-IEs,
												va40NonCriticalExtensions		SEQUENCE {
													sysInfoType5-va40ext
																			SysInfoType5-va40ext-IEs,
													va80NonCriticalExtensions		SEQUENCE {
														sysInfoType5-va80ext	SysInfoType5-va80ext-IEs,
														vb50NonCriticalExtensions
															SysInfoType5-NonCriticalExtensions-vb50-IEs
	OPTIONAL
													}		OPTIONAL
												}		OPTIONAL
											}		OPTIONAL
										}		OPTIONAL
									}		OPTIONAL
								}		OPTIONAL
							}		OPTIONAL
						}		OPTIONAL
					}		OPTIONAL
				}		OPTIONAL
			}		OPTIONAL
		}		OPTIONAL
}

SysInfoType5-v4b0ext-IEs ::=	SEQUENCE {
	--The following IE PNBSCH-Allocation-r4 shall be used for 3.84Mcps TDD only.
	pNBSCH-Allocation-r4 			PNBSCH-Allocation-r4			OPTIONAL,
	-- In case of TDD, the following IE is included instead of the
	-- IE up-IPDL-Parameter in up-OTDOA-AssistanceData.
	openLoopPowerControl-IPDL-TDD	OpenLoopPowerControl-IPDL-TDD-r4	OPTIONAL,
-- If SysInfoType5 is sent to describe a 1.28Mcps TDD cell, the IE PRACH-RACH-Info included in
-- PRACH-SystemInformationList shall be ignored, the IE PRACH-Partitioning and the
-- IE rach-TransportFormatSet shall be absent and the corresponding IE in the following
-- PRACH-SystemInformationList-LCR-r4 shall be used
	prach-SystemInformationList-LCR-r4	PRACH-SystemInformationList-LCR-r4	OPTIONAL,
	tdd128SpecificInfo				SEQUENCE {
		pusch-SysInfoList-SFN			PUSCH-SysInfoList-SFN-LCR-r4	OPTIONAL,
		pdsch-SysInfoList-SFN			PDSCH-SysInfoList-SFN-LCR-r4	OPTIONAL,
		pCCPCH-LCR-Extensions			PrimaryCCPCH-Info-LCR-r4-ext	OPTIONAL,
		sCCPCH-LCR-ExtensionsList		SCCPCH-SystemInformationList-LCR-r4-ext
	}																OPTIONAL,
	frequencyBandIndicator			RadioFrequencyBandFDD			OPTIONAL
}

SysInfoType5-v590ext-IEs ::=	SEQUENCE {
	hcr-r5-SpecificInfo				SEQUENCE {
		pusch-SysInfoList-SFN			PUSCH-SysInfoList-SFN-HCR-r5	OPTIONAL,
		pdsch-SysInfoList-SFN			PDSCH-SysInfoList-SFN-HCR-r5	OPTIONAL
	}																	OPTIONAL
}

SysInfoType5-v650ext-IEs ::=	SEQUENCE {
	frequencyBandIndicator2		RadioFrequencyBandFDD2
}

SysInfoType5-v680ext-IEs ::=	SEQUENCE {
	-- TABULAR: HSDPA Cell Indicator is MD in tabular description
	-- Default value is 'HSDPA Capability not indicated'
	hsdpa-CellIndicator			ENUMERATED { hsdpa-CapableCell }			OPTIONAL
}

SysInfoType5-v690ext-IEs ::=		SEQUENCE {
	-- TABULAR: E-DCH Cell Indicator is MD in tabular description
	-- Default value is 'E-DCH Capability not indicated'
	edch-CellIndicator					ENUMERATED { edch-CapableCell }		OPTIONAL,
	sccpch-SystemInformation-MBMS		CHOICE {
		mcchOnSCCPCHusedForNonMBMS			MBMS-MCCH-ConfigurationInfo-r6,
		mcchOnSCCPCHusedOnlyForMBMS			SCCPCH-SystemInformation-MBMS-r6
	}		OPTIONAL,
	additionalPRACH-TF-and-TFCS-CCCH-List	AdditionalPRACH-TF-and-TFCS-CCCH-List	OPTIONAL,
	cBS-DRX-Level1Information-extension		CBS-DRX-Level1Information-extension-r6	OPTIONAL
}

SysInfoType5-v770ext-IEs ::=		SEQUENCE {
	modeSpecificInfo					CHOICE {
		fdd									SEQUENCE {
			hs-dsch-CommonSystemInformation		HS-DSCH-CommonSystemInformation,
			hs-dsch-PagingSystemInformation		HS-DSCH-PagingSystemInformation		OPTIONAL
		},
		tdd768								SEQUENCE {
			pusch-SysInfoList-SFN				PUSCH-SysInfoList-SFN-VHCR			OPTIONAL,
			pdsch-SysInfoList-SFN				PDSCH-SysInfoList-VHCR-r7			OPTIONAL,
			-- If SysInfoType5 is sent to configure a 7.68Mcps TDD cell, the 'prach-RACH-Info' in
			-- IE PRACH-SystemInformationList shall be ignored, 'prach-Partitioning' shall be absent
			-- and the corresponding IE in the following IE PRACH-SystemInformationList-VHCR-r7
			-- shall be used instead.
			prach-SystemInformationList		PRACH-SystemInformationList-VHCR-r7	OPTIONAL
		},
		tdd128								SEQUENCE {
			prach-SystemInformationList		PRACH-SystemInformationList-LCR-v770ext	OPTIONAL
		}
	}		OPTIONAL,
	-- If SysInfoType5 is sent to configure a 7.68 Mcps TDD cell (in any mode) or a 3.84 Mcps TDD
	-- cell operating in MBSFN mode, IE SCCPCH-SystemInformationList-HCR-VHCR-r7 is used, otherwise
	-- IE SCCPCH-SystemInformationList-r6 is used.
	sccpch-SystemInformationList			SCCPCH-SystemInformationList-HCR-VHCR-r7	OPTIONAL,
	sccpch-SystemInformation-MBMS		CHOICE {
		-- If choice is 'mcchOnSCCPCHusedForNonMBMS', IE MBMS-MCCH-ConfigurationInfo-r6 is used.
		-- If choice is 'mcchOnSCCPCHusedOnlyForMBMS', IE MBMS-MCCH-ConfigurationInfo-r7 is used
		-- to configure a 7.68Mcps TDD cell or a cell operating in MBSFN mode, otherwise IE
		-- SCCPCH-SystemInformation-MBMS-r6 is used.
		mcchOnSCCPCHusedOnlyForMBMS			SCCPCH-SystemInformation-MBMS-r7
	}		OPTIONAL,
	tDD-MBSFNInformation				TDD-MBSFNInformation			OPTIONAL
}

SysInfoType5-v860ext-IEs ::=	SEQUENCE {
	-- The field 'dummy' shall be marked absent in SysInfoType5 and SysInfoType5bis. A failure to
	-- comply with this requirement may prevent the UE to receive any service in the cell. The UE
	-- may treat the cell as barred.
	dummy								SEQUENCE {}								OPTIONAL,
	modeSpecificInfo					CHOICE {
		fdd									SEQUENCE {
			hs-dsch-DrxCellfach-info			HS-DSCH-DrxCellfach-info				OPTIONAL
		},
		tdd128								SEQUENCE {
			hs-dsch-CommonSysInfo				SEQUENCE {
				hs-dsch-CommonSystemInformation	HS-DSCH-CommonSystemInformation-TDD128,
				hs-dsch-PagingSystemInformation	HS-DSCH-PagingSystemInformation-TDD128	OPTIONAL
			}		OPTIONAL,
			hs-dsch-DrxCellfach-info			HS-DSCH-DrxCellfach-info-TDD128			OPTIONAL
		}
	}
}

SysInfoType5-v890ext-IEs ::= SEQUENCE {
	secondFrequencyInfo			FrequencyInfoTDD						OPTIONAL,
	commonEDCHSystemInfo			CommonEDCHSystemInfo					OPTIONAL
}

SysInfoType5-v8b0ext-IEs ::= SEQUENCE {
	tresetUsageIndicator				ENUMERATED { true }				OPTIONAL,
	upPCHpositionInfo					UpPCHposition-LCR					OPTIONAL
}

SysInfoType5-v8d0ext-IEs ::=	SEQUENCE {
	commonEDCHSystemInfoFDD				CommonEDCHSystemInfoFDD		OPTIONAL
}

SysInfoType5-va40ext-IEs ::=	SEQUENCE {
	frequencyBandsIndicatorSupport		FrequencyBandsIndicatorSupport	OPTIONAL,
	frequencyBandIndicator3				RadioFrequencyBandFDD3			OPTIONAL
}

SysInfoType5-va80ext-IEs ::=	SEQUENCE {
	multipleFrequencyBandIndicatorListFDD		MultipleFrequencyBandIndicatorListFDD		OPTIONAL
}

SysInfoType5-NonCriticalExtensions-vb50-IEs::=	SEQUENCE {
	sysInfoType5-vb50ext				SysInfoType5-vb50ext-IEs,
	ve30NonCriticalExtensions			SysInfoType5-NonCriticalExtensions-ve30-IEs						OPTIONAL

}

SysInfoType5-NonCriticalExtensions-ve30-IEs::= SEQUENCE {
	sysInfoType5-ve30ext				SysInfoType5-ve30ext-IEs,
	nonCriticalExtensions				SEQUENCE {}						OPTIONAL

}

SysInfoType5-ve30ext-IEs ::= SEQUENCE {
	adjacentchannelinterferencelevel	ENUMERATED { moderate, high }		OPTIONAL
}

SysInfoType5-vb50ext-IEs ::=	SEQUENCE {
	sib22indicator					BOOLEAN,
	cellUpdateMessageOptimisedEncoding	ENUMERATED { true }		OPTIONAL
}

-- SysInfoType5bis uses the same structure as SysInfoType5
SysInfoType5bis ::= SysInfoType5

SysInfoType6 ::=					SEQUENCE {
	-- Physical channel IEs
		pich-PowerOffset				PICH-PowerOffset,
		modeSpecificInfo				CHOICE {
			fdd								SEQUENCE {
				aich-PowerOffset				AICH-PowerOffset,
				-- dummy is not used in this version of specification, it should
				-- not be sent and if received it should be ignored.
				dummy							CSICH-PowerOffset			OPTIONAL
			},
			tdd								SEQUENCE {
				-- If PDSCH/PUSCH is configured for 1.28Mcps TDD, pusch-SysInfoList-SFN,
				-- pdsch-SysInfoList-SFN and openLoopPowerControl-TDD should be absent
				-- and the info included in the tdd128SpecificInfo instead.
				-- If PDSCH/PUSCH is configured for 7.68Mcps TDD, pusch-SysInfoList-SFN
				-- and pdsch-SysInfoList-SFN should be absent and the info included in the
				-- tdd768SpecificInfo instead.
				-- If PDSCH/PUSCH is configured for 3.84Mcps TDD in R5, HCR-r5-SpecificInfo should
				-- also be included.
				pusch-SysInfoList-SFN			PUSCH-SysInfoList-SFN		OPTIONAL,
				pdsch-SysInfoList-SFN			PDSCH-SysInfoList-SFN		OPTIONAL,
				openLoopPowerControl-TDD		OpenLoopPowerControl-TDD
			}
		},
		primaryCCPCH-Info				PrimaryCCPCH-Info					OPTIONAL,
		prach-SystemInformationList	PRACH-SystemInformationList			OPTIONAL,
		sCCPCH-SystemInformationList	SCCPCH-SystemInformationList		OPTIONAL,
		cbs-DRX-Level1Information		CBS-DRX-Level1Information			OPTIONAL,
		-- Conditional on any of the CTCH indicator IEs in
		-- sCCPCH-SystemInformationList
	-- Extension mechanism for non- release99 information
		v4b0NonCriticalExtensions		SEQUENCE {
			sysInfoType6-v4b0ext			SysInfoType6-v4b0ext-IEs		OPTIONAL,
		-- Extension mechanism for non- rel-4 information
			v590NonCriticalExtensions	SEQUENCE {
				sysInfoType6-v590ext			SysInfoType6-v590ext-IEs		OPTIONAL,
				v650nonCriticalExtensions		SEQUENCE {
					sysInfoType6-v650ext			SysInfoType6-v650ext-IEs		OPTIONAL,
					v690nonCriticalExtensions		SEQUENCE {
						sysInfoType6-v690ext			SysInfoType6-v690ext-IEs,
						v770NonCriticalExtensions		SEQUENCE {
							sysInfoType6-v770ext			SysInfoType6-v770ext-IEs,
							va40NonCriticalExtensions			SEQUENCE {
								sysInfoType6-va40ext				SysInfoType6-va40ext-IEs,
								va80NonCriticalExtensions			SEQUENCE {
									sysInfoType6-va80ext				SysInfoType6-va80ext-IEs,
									ve30NonCriticalExtensions	SysInfoType6-NonCriticalExtensions-ve30-IEs	OPTIONAL
								}	OPTIONAL
							}	OPTIONAL
						}	OPTIONAL
					}	OPTIONAL
				}	OPTIONAL
			}	OPTIONAL
		}	OPTIONAL
}

SysInfoType6-NonCriticalExtensions-ve30-IEs::= SEQUENCE {
	sysInfoType6-ve30ext				SysInfoType6-ve30ext-IEs,
	nonCriticalExtensions				SEQUENCE {}			OPTIONAL
}

SysInfoType6-ve30ext-IEs ::= SEQUENCE {
	adjacentchannelinterferencelevel		ENUMERATED { moderate, high }	OPTIONAL
}

SysInfoType6-v4b0ext-IEs ::=	SEQUENCE {
	-- openLoopPowerControl-IPDL-TDD is present only if IPDLs are applied for TDD
	openLoopPowerControl-IPDL-TDD	OpenLoopPowerControl-IPDL-TDD-r4	OPTIONAL,
	-- If SysInfoType6 is sent to describe a 1.28Mcps TDD cell, the IE PRACH-RACH-Info included
	-- in PRACH-SystemInformationList shall be ignored, the IE PRACH-Partitioning and the
	-- IE rach-TransportFormatSet shall be absent and the corresponding IEs in the following
	-- PRACH-SystemInformationList-LCR-r4 shall be used
	prach-SystemInformationList-LCR-r4	PRACH-SystemInformationList-LCR-r4	OPTIONAL,
	tdd128SpecificInfo				SEQUENCE {
		pusch-SysInfoList-SFN			PUSCH-SysInfoList-SFN-LCR-r4	OPTIONAL,
		pdsch-SysInfoList-SFN			PDSCH-SysInfoList-SFN-LCR-r4	OPTIONAL,
		pCCPCH-LCR-Extensions			PrimaryCCPCH-Info-LCR-r4-ext	OPTIONAL,
		sCCPCH-LCR-ExtensionsList		SCCPCH-SystemInformationList-LCR-r4-ext	OPTIONAL
	}																OPTIONAL,
	frequencyBandIndicator			RadioFrequencyBandFDD			OPTIONAL
}

SysInfoType6-v590ext-IEs ::=	SEQUENCE {
	hcr-r5-SpecificInfo				SEQUENCE {
		pusch-SysInfoList-SFN			PUSCH-SysInfoList-SFN-HCR-r5	OPTIONAL,
		pdsch-SysInfoList-SFN			PDSCH-SysInfoList-SFN-HCR-r5	OPTIONAL
	}																	OPTIONAL
}

SysInfoType6-v650ext-IEs ::=	SEQUENCE {
	frequencyBandIndicator2			RadioFrequencyBandFDD2
}

SysInfoType6-v690ext-IEs ::=	SEQUENCE {
	additionalPRACH-TF-and-TFCS-CCCH-List	AdditionalPRACH-TF-and-TFCS-CCCH-List	OPTIONAL
}

SysInfoType6-v770ext-IEs ::=		SEQUENCE {
	tdd768SpecificInfo					SEQUENCE {
		pusch-SysInfoList-SFN				PUSCH-SysInfoList-SFN-VHCR			OPTIONAL,
		pdsch-SysInfoList-SFN				PDSCH-SysInfoList-VHCR-r7			OPTIONAL,
		-- If SysInfoType6 is sent to configure a 7.68Mcps TDD cell, the 'prach-RACH-Info' in
		-- IE PRACH-SystemInformationList shall be ignored, 'prach-Partitioning' shall be absent
		-- and the corresponding IE in the following IE PRACH-SystemInformationList-VHCR-r7
		-- shall be used instead.
		prach-SystemInformationList		PRACH-SystemInformationList-VHCR-r7	OPTIONAL
	}		OPTIONAL,
	-- If SysInfoType6 is sent to configure a 7.68 Mcps TDD cell,
	-- IE SCCPCH-SystemInformationList-HCR-VHCR-r7 is used, otherwise
	-- IE SCCPCH-SystemInformationList-r6 is used.
	sccpch-SystemInformationList		SCCPCH-SystemInformationList-HCR-VHCR-r7	OPTIONAL
}

SysInfoType6-va40ext-IEs ::= SEQUENCE {
	frequencyBandIndicator3			RadioFrequencyBandFDD3				OPTIONAL
}

SysInfoType6-va80ext-IEs ::= SEQUENCE {
	multipleFrequencyBandIndicatorListFDD		MultipleFrequencyBandIndicatorListFDD		OPTIONAL
}

SysInfoType7 ::=					SEQUENCE {
	-- Physical channel IEs
		modeSpecificInfo				CHOICE {
			fdd								SEQUENCE {
				ul-Interference				UL-Interference
			},
			tdd								NULL
		},
		prach-Information-SIB5-List	DynamicPersistenceLevelList,
		prach-Information-SIB6-List	DynamicPersistenceLevelList			OPTIONAL,
		expirationTimeFactor			ExpirationTimeFactor				OPTIONAL,
	-- Extension mechanism for non- release99 information
		nonCriticalExtensions			SEQUENCE {}							OPTIONAL
}

-- This IE is not used in this version of the specification.
-- It was kept only for backwards compatibility reasons
SysInfoType8 ::=					SEQUENCE {
	-- User equipment IEs
		-- dummy1, dummy2, dummy3 are not used in this version of the specification and
		-- they should be ignored by the receiver.
		dummy1							CPCH-Parameters,
	-- Physical channel IEs
		dummy2							CPCH-SetInfoList,
		dummy3							CSICH-PowerOffset,
	-- Extension mechanism for non- release99 information
		nonCriticalExtensions			SEQUENCE {}							OPTIONAL
}

-- This IE is not used in this version of the specification.
-- It was kept only for backwards compatibility reasons
SysInfoType9 ::=					SEQUENCE {
	-- Physical channel IEs
		-- dummy is not used in this version of the specification and
		-- it should be ignored by the receiver.
		dummy							CPCH-PersistenceLevelsList,
	-- Extension mechanism for non- release99 information
		nonCriticalExtensions			SEQUENCE {}							OPTIONAL
}

-- This IE is not used in this version of the specification.
-- It was kept only for backwards compatibility reasons
SysInfoType10 ::=					SEQUENCE {
	-- User equipment IEs
		-- dummy is not used in this version of the specification, it should
		-- not be sent and if received it should be ignored.
		dummy							DRAC-SysInfoList,
	-- Extension mechanism for non- release99 information
		nonCriticalExtensions			SEQUENCE {}							OPTIONAL
}

SysInfoType11 ::=					SEQUENCE {
		sib12indicator					BOOLEAN,
	-- Measurement IEs
		fach-MeasurementOccasionInfo	FACH-MeasurementOccasionInfo		OPTIONAL,
		measurementControlSysInfo		MeasurementControlSysInfo,
	-- Extension mechanism for non- release99 information
		v4b0NonCriticalExtensions		SEQUENCE {
			sysInfoType11-v4b0ext			SysInfoType11-v4b0ext-IEs		OPTIONAL,
			v590NonCriticalExtension		SEQUENCE {
				sysInfoType11-v590ext			SysInfoType11-v590ext-IEs,
				v690NonCriticalExtensions		SEQUENCE {
					sysInfoType11-v690ext			SysInfoType11-v690ext-IEs,
					v6b0NonCriticalExtensions		SEQUENCE {
						sysInfoType11-v6b0ext			SysInfoType11-v6b0ext-IEs,
						v770NonCriticalExtensions		SEQUENCE {
							sysInfoType11-v770ext			SysInfoType11-v770ext-IEs,
							v7b0NonCriticalExtensions		SEQUENCE {
								sysInfoType11-v7b0ext			SysInfoType11-v7b0ext-IEs,
								v860NonCriticalExtensions		SEQUENCE {
									sysInfoType11-v860ext			SysInfoType11-v860ext-IEs,
									va80NonCriticalExtensions		SEQUENCE {
										sysInfoType11-va80ext			SysInfoType11-va80ext-IEs,
										vc50NonCriticalExtensions		SEQUENCE {
											sysInfoType11-vc50ext			SysInfoType11-vc50ext-IEs,
											nonCriticalExtensions			SEQUENCE {}		OPTIONAL
										}		OPTIONAL
									}		OPTIONAL
								}		OPTIONAL
							}		OPTIONAL
						}		OPTIONAL
					}		OPTIONAL
				}		OPTIONAL
			}		OPTIONAL
		}		OPTIONAL
}

SysInfoType11-v4b0ext-IEs ::=	SEQUENCE {
	fach-MeasurementOccasionInfo-LCR-Ext	FACH-MeasurementOccasionInfo-LCR-r4-ext	OPTIONAL,
	measurementControlSysInfo-LCR			MeasurementControlSysInfo-LCR-r4-ext
}

SysInfoType11-v590ext-IEs ::=	SEQUENCE {
	--The order of the list corresponds to the order of cell in newIntraFrequencyCellInfoList
	newIntraFrequencyCellInfoList-v590ext	SEQUENCE (SIZE (1..maxCellMeas)) OF
													CellSelectReselectInfo-v590ext	OPTIONAL,
	--The order of the list corresponds to the order of cell in newInterFrequencyCellInfoList
	newInterFrequencyCellInfoList-v590ext	SEQUENCE (SIZE (1..maxCellMeas)) OF
													CellSelectReselectInfo-v590ext	OPTIONAL,
	--The order of the list corresponds to the order of cell in newInterRATCellInfoList
	newInterRATCellInfoList-v590ext			SEQUENCE (SIZE (1..maxCellMeas)) OF
													CellSelectReselectInfo-v590ext	OPTIONAL,
	intraFreqEventCriteriaList-v590ext		Intra-FreqEventCriteriaList-v590ext	OPTIONAL,
	intraFreqReportingCriteria-1b-r5			IntraFreqReportingCriteria-1b-r5		OPTIONAL,
	intraFreqEvent-1d-r5						IntraFreqEvent-1d-r5					OPTIONAL
}

SysInfoType11-v690ext-IEs ::=		SEQUENCE {
	-- dummy is not used in this version of the specification. If received, the UE behaviour
	-- is not specified.
	dummy								Dummy-InterFreqRACHReportingInfo	OPTIONAL
}

SysInfoType11-v6b0ext-IEs ::=		SEQUENCE {
	-- Measurement IEs
	interFreqRACHReportingInfo			InterFreqRACHReportingInfo			OPTIONAL
}

SysInfoType11-v770ext-IEs ::=		SEQUENCE {
	-- Measurement IEs
		mbsfnFrequencyList				MBSFNFrequencyList					OPTIONAL
}

SysInfoType11-v7b0ext-IEs ::=		SEQUENCE {
	-- Measurement IEs
		newInterFreqCellList			NewInterFreqCellList-v7b0ext		OPTIONAL
}

SysInfoType11-v860ext-IEs ::=		SEQUENCE {
	-- Measurement IEs
		mbsfnFrequencyList				MBSFNFrequencyList-v860ext			OPTIONAL
}

SysInfoType11-va80ext-IEs ::=		SEQUENCE {
	-- Measurement IEs
		multipleFrequencyInfoListFDD		MultipleFrequencyInfoListFDD	OPTIONAL
}

SysInfoType11-vc50ext-IEs ::=		SEQUENCE {
	measurementControlSysInfo			MeasurementControlSysInfo-vc50ext	OPTIONAL,
	-- Measurement IEs
		measurementScalingFactor		MeasurementScalingFactor			OPTIONAL
}

MeasurementScalingFactor ::=	ENUMERATED {
									sf-utra-cf1, sf-utra-cf2}


SysInfoType11bis ::=				SEQUENCE {
	-- Measurement IEs
		measurementControlSysInfo		MeasurementControlSysInfoExtension			OPTIONAL,
		measurementControlSysInfo-LCR	MeasurementControlSysInfoExtension-LCR-r4	OPTIONAL,
		measurementControlSysInfoExtensionAddon-r5
										MeasurementControlSysInfoExtensionAddon-r5	OPTIONAL,
	-- Extension mechanism for non-release99 information
		v7b0NonCriticalExtensions		SEQUENCE {
			sysInfoType11bis-v7b0ext		SysInfoType11bis-v7b0ext-IEs,
			v860NonCriticalExtensions		SEQUENCE {
				sysInfoType11bis-v860ext		SysInfoType11bis-v860ext-IEs,
				va80NonCriticalExtensions		SEQUENCE {
					sysInfoType11bis-va80ext		SysInfoType11bis-va80ext-IEs,
					vc50NonCriticalExtensions		SEQUENCE {
						sysInfoType11bis-vc50ext		SysInfoType11bis-vc50ext-IEs,
						nonCriticalExtensions			SEQUENCE {}				OPTIONAL
					}		OPTIONAL
				}		OPTIONAL
			}		OPTIONAL
		}		OPTIONAL
}

SysInfoType11bis-v7b0ext-IEs ::=		SEQUENCE {
	-- Measurement IEs
		newInterFreqCellList				NewInterFreqCellList-v7b0ext		OPTIONAL
}

SysInfoType11bis-v860ext-IEs ::=		SEQUENCE {
	-- UTRAN mobility IEs
		csg-PSCSplitInfo					CSG-PSCSplitInfo					OPTIONAL,
		csg-DedicatedFrequencyInfoList	CSG-DedicatedFrequencyInfoList		OPTIONAL
}

SysInfoType11bis-va80ext-IEs ::=		SEQUENCE {
	-- Measurement IEs
		multipleFrequencyInfoListFDD		MultipleFrequencyInfoListFDD	OPTIONAL
}

SysInfoType11bis-vc50ext-IEs ::=		SEQUENCE {
	measurementControlSysInfo				MeasurementControlSysInfo-vc50ext	OPTIONAL
}

SysInfoType11ter ::=				SEQUENCE {
	-- Measurement IEs
		measureControlSysInfoInterFreqExt	MeasureControlSysInfoInterFreqExt	OPTIONAL,
		multipleFrequencyInfoListFDD			MultipleFrequencyInfoListFDD		OPTIONAL,
		nonCriticalExtensions					SEQUENCE {}							OPTIONAL
}

SysInfoType12 ::=					SEQUENCE {
	-- Measurement IEs
		fach-MeasurementOccasionInfo	FACH-MeasurementOccasionInfo		OPTIONAL,
		measurementControlSysInfo		MeasurementControlSysInfo,
	-- Extension mechanism for non- release99 information
		v4b0NonCriticalExtensions		SEQUENCE {
			sysInfoType12-v4b0ext			SysInfoType12-v4b0ext-IEs		OPTIONAL,
			v590NonCriticalExtension		SEQUENCE {
				sysInfoType12-v590ext			SysInfoType12-v590ext-IEs,
				v690NonCriticalExtensions		SEQUENCE {
					sysInfoType12-v690ext			SysInfoType12-v690ext-IEs,
					v6b0NonCriticalExtensions		SEQUENCE {
						sysInfoType12-v6b0ext			SysInfoType12-v6b0ext-IEs,
						v7b0NonCriticalExtensions		SEQUENCE {
							sysInfoType12-v7b0ext			SysInfoType12-v7b0ext-IEs,
							va80NonCriticalExtensions		SEQUENCE {
								sysInfoType12-va80ext			SysInfoType12-va80ext-IEs,
								vc50NonCriticalExtensions		SEQUENCE {
									sysInfoType12-vc50ext			SysInfoType12-vc50ext-IEs,
									nonCriticalExtensions			SEQUENCE {}				OPTIONAL
								}							OPTIONAL
							}							OPTIONAL
						}							OPTIONAL
					}							OPTIONAL
				}							OPTIONAL
			}							OPTIONAL
		}							OPTIONAL
}

SysInfoType12-v4b0ext-IEs ::=	SEQUENCE {
	fach-MeasurementOccasionInfo-LCR-Ext	FACH-MeasurementOccasionInfo-LCR-r4-ext	OPTIONAL,
	measurementControlSysInfo-LCR			MeasurementControlSysInfo-LCR-r4-ext
}

SysInfoType12-v590ext-IEs ::=	SEQUENCE {
	--The order of the list corresponds to the order of cell in newIntraFrequencyCellInfoList
	newIntraFrequencyCellInfoList-v590ext	SEQUENCE (SIZE (1..maxCellMeas)) OF
													CellSelectReselectInfo-v590ext	OPTIONAL,
	--The order of the list corresponds to the order of cell in newInterFrequencyCellInfoList
	newInterFrequencyCellInfoList-v590ext	SEQUENCE (SIZE (1..maxCellMeas)) OF
													CellSelectReselectInfo-v590ext	OPTIONAL,
	--The order of the list corresponds to the order of cell in newInterRATCellInfoList
	newInterRATCellInfoList-v590ext			SEQUENCE (SIZE (1..maxCellMeas)) OF
													CellSelectReselectInfo-v590ext	OPTIONAL,
	intraFreqEventCriteriaList-v590ext		Intra-FreqEventCriteriaList-v590ext		OPTIONAL,
	intraFreqReportingCriteria-1b-r5			IntraFreqReportingCriteria-1b-r5		OPTIONAL,
	intraFreqEvent-1d-r5						IntraFreqEvent-1d-r5					OPTIONAL
}

SysInfoType12-v690ext-IEs ::=		SEQUENCE {
	-- dummy is not used in this version of the specification. If received, the UE behaviour
	-- is not specified.
	dummy								Dummy-InterFreqRACHReportingInfo	OPTIONAL
}

SysInfoType12-v6b0ext-IEs ::=		SEQUENCE {
	-- Measurement IEs
	interFreqRACHReportingInfo			InterFreqRACHReportingInfo			OPTIONAL
}

SysInfoType12-v7b0ext-IEs ::=		SEQUENCE {
	-- Measurement IEs
		newInterFreqCellList			NewInterFreqCellList-v7b0ext		OPTIONAL
}

SysInfoType12-va80ext-IEs ::=		SEQUENCE {
	-- Measurement IEs
		multipleFrequencyInfoListFDD		MultipleFrequencyInfoListFDD	OPTIONAL
}

SysInfoType12-vc50ext-IEs ::=		SEQUENCE {
	measurementControlSysInfo			MeasurementControlSysInfo-vc50ext	OPTIONAL
}

SysInfoType13 ::=					SEQUENCE {
	-- Core network IEs
		cn-DomainSysInfoList			CN-DomainSysInfoList,
	-- User equipment IEs
		ue-IdleTimersAndConstants		UE-IdleTimersAndConstants			OPTIONAL,
		capabilityUpdateRequirement		CapabilityUpdateRequirement			OPTIONAL,
	-- Extension mechanism for non- release99 information
		v3a0NonCriticalExtensions			SEQUENCE {
			sysInfoType13-v3a0ext			SysInfoType13-v3a0ext-IEs,
			v4b0NonCriticalExtensions		SEQUENCE {
				sysInfoType13-v4b0ext			SysInfoType13-v4b0ext-IEs,
			-- Extension mechanism for non- release99 information
				v770NonCriticalExtensions		SEQUENCE {
					sysInfoType13-v770ext			SysInfoType13-v770ext-IEs,
					nonCriticalExtensions			SEQUENCE {}						OPTIONAL
				}							OPTIONAL
			}							OPTIONAL
		}							OPTIONAL
}

SysInfoType13-v3a0ext-IEs ::=		SEQUENCE {
	ue-IdleTimersAndConstants-v3a0ext		UE-IdleTimersAndConstants-v3a0ext
}

SysInfoType13-v4b0ext-IEs ::=		SEQUENCE {
	capabilityUpdateRequirement-r4Ext	CapabilityUpdateRequirement-r4-ext	OPTIONAL
}

SysInfoType13-v770ext-IEs ::=		SEQUENCE {
	capabilityUpdateRequirement			CapabilityUpdateRequirement-v770ext	OPTIONAL
}

SysInfoType13-1 ::=				SEQUENCE {
	-- ANSI-41 IEs
		ansi-41-RAND-Information		ANSI-41-RAND-Information,
	-- Extension mechanism for non- release99 information
		nonCriticalExtensions			SEQUENCE {}							OPTIONAL
}

SysInfoType13-2 ::=					SEQUENCE {
	-- ANSI-41 IEs
		ansi-41-UserZoneID-Information	ANSI-41-UserZoneID-Information,
	-- Extension mechanism for non- release99 information
		nonCriticalExtensions				SEQUENCE {}						OPTIONAL
}

SysInfoType13-3 ::=					SEQUENCE {
	-- ANSI-41 IEs
		ansi-41-PrivateNeighbourListInfo ANSI-41-PrivateNeighbourListInfo,
	-- Extension mechanism for non- release99 information
		nonCriticalExtensions				SEQUENCE {}						OPTIONAL
}

SysInfoType13-4 ::=					SEQUENCE {
	-- ANSI-41 IEs
		ansi-41-GlobalServiceRedirectInfo
										ANSI-41-GlobalServiceRedirectInfo,
	-- Extension mechanism for non- release99 information
		nonCriticalExtensions			SEQUENCE {}							OPTIONAL
}

SysInfoType14 ::=					SEQUENCE {
	-- Physical channel IEs
		individualTS-InterferenceList	IndividualTS-InterferenceList,
		expirationTimeFactor			ExpirationTimeFactor				OPTIONAL,
	-- Extension mechanism for non- release99 information
		nonCriticalExtensions			SEQUENCE {}							OPTIONAL
}

SysInfoType15 ::=					SEQUENCE {
	-- Measurement IEs
		ue-positioning-GPS-CipherParameters		UE-Positioning-CipherParameters		OPTIONAL,
		ue-positioning-GPS-ReferenceLocation		ReferenceLocation,
		ue-positioning-GPS-ReferenceTime			UE-Positioning-GPS-ReferenceTime,
		ue-positioning-GPS-Real-timeIntegrity	BadSatList							OPTIONAL,
	-- Extension mechanism for non- release99 information
		v4b0NonCriticalExtensions			SEQUENCE {
			sysInfoType15-v4b0ext				SysInfoType15-v4b0ext-IEs,
		-- Extension mechanism for non- release4 information
			v770NonCriticalExtensions			SEQUENCE {
				sysInfoType15-v770ext				SysInfoType15-v770ext-IEs,
					va40NonCriticalExtensions		SEQUENCE {
						sysInfoType15-va40ext			SysInfoType15-va40ext-IEs,
					nonCriticalExtensions			SEQUENCE {}				OPTIONAL
				}	OPTIONAL
			}	OPTIONAL
		}	OPTIONAL
}

SysInfoType15-v4b0ext-IEs ::=		SEQUENCE {
	up-Ipdl-Parameters-TDD			UE-Positioning-IPDL-Parameters-TDD-r4-ext	OPTIONAL
}

SysInfoType15-v770ext-IEs ::=		SEQUENCE {
	-- Measurement IEs
		ue-Positioning-GPS-ReferenceTime		UE-Positioning-GPS-ReferenceTime-v770ext
}

SysInfoType15-va40ext-IEs ::= 	SEQUENCE {
	-- Measurement IEs
		ue-Positioning-GPS-ReferenceTime		UE-Positioning-GPS-ReferenceTime-va40ext
}

SysInfoType15bis ::=				SEQUENCE {
	-- Measurement IEs
		ue-positioning-GANSS-ReferencePosition	ReferenceLocationGANSS,
		ue-positioning-GANSS-ReferenceTime		UE-Positioning-GANSS-ReferenceTime,
		ue-positioning-GANSS-IonosphericModel	UE-Positioning-GANSS-IonosphericModel	OPTIONAL,
	-- Extension mechanism for non-release99 information
		v860NonCriticalExtensions		SEQUENCE {
			sysInfoType15bis-v860ext		SysInfoType15bis-v860ext-IEs,
				va40NonCriticalExtensions	SEQUENCE {
				sysInfoType15bis-va40ext		SysInfoType15bis-va40ext-IEs,
				nonCriticalExtensions			SEQUENCE {}				OPTIONAL
			}	OPTIONAL
		}	OPTIONAL
}

SysInfoType15bis-v860ext-IEs ::=		SEQUENCE {
	-- Measurement IEs
		ue-Positioning-GANSS-AddIonoModel	UE-Positioning-GANSS-AddIonoModel			OPTIONAL,
		ue-Positioning-GANSS-EarthOrientationPara
											UE-Positioning-GANSS-EarthOrientPara		OPTIONAL
}

SysInfoType15bis-va40ext-IEs ::=		SEQUENCE {
	-- Measurement IEs
		ue-positioning-GANSS-ReferenceTime	UE-Positioning-GANSS-ReferenceTime-va40ext
}

SysInfoType15-1 ::=					SEQUENCE {
	-- DGPS corrections
		ue-positioning-GPS-DGPS-Corrections			UE-Positioning-GPS-DGPS-Corrections,
	-- Extension mechanism for non- release99 information
			v920NonCriticalExtensions		SEQUENCE {
				sysInfoType15-1-v920ext			SysInfoType15-1-v920ext-IEs,
				nonCriticalExtensions			SEQUENCE {}				OPTIONAL
			}	OPTIONAL
}

SysInfoType15-1-v920ext-IEs ::=		SEQUENCE {
	-- Measurement IEs
	ue-positioning-GPS-DGPS-Corrections				UE-Positioning-GPS-DGPS-Corrections-v920ext
}

SysInfoType15-1bis ::=				SEQUENCE {
	-- Measurement IEs
		ue-positioning-GANSS-DGANSS-Corrections	UE-Positioning-DGANSSCorrections,
	-- Extension mechanism for non-release99 information
			v920NonCriticalExtensions		SEQUENCE {
				sysInfoType15-1bis-v920ext		SysInfoType15-1bis-v920ext-IEs,
				nonCriticalExtensions			SEQUENCE {}				OPTIONAL
			}	OPTIONAL
}

SysInfoType15-1bis-v920ext-IEs ::=	SEQUENCE {
	-- Measurement IEs
	ue-positioning-GANSS-DGANSS-Corrections		UE-Positioning-DGANSSCorrections-v920ext
}

SysInfoType15-1ter ::=				SEQUENCE {
	-- Measurement IEs
		uePositioning-BDSCorrections		UE-Positioning-DBDSCorrections		OPTIONAL,
		uePositioningBDSIonoGridModel		UE-Positioning-BDS-IonoGridModel		OPTIONAL,
	-- Extension mechanism for non-release12 information
		nonCriticalExtensions				SEQUENCE {}							OPTIONAL
}

SysInfoType15-2 ::=					SEQUENCE {
	-- Ephemeris and clock corrections
		transmissionTOW					GPS-TOW-1sec,
		satID								SatID,
		ephemerisParameter					EphemerisParameter,
	-- Extension mechanism for non- release99 information
		nonCriticalExtensions				SEQUENCE {}							OPTIONAL
}

SysInfoType15-2bis ::=				SEQUENCE {
	-- Measurement IEs
		ue-positioning-GANSS-navigationModel		UE-Positioning-GANSS-NavigationModel,
	-- Extension mechanism for non-release99 information
		nonCriticalExtensions						SEQUENCE {}					OPTIONAL
}

SysInfoType15-2ter ::=				SEQUENCE {
	-- Measurement IEs
		ue-positioning-GANSS-AddNavigationModels	UE-Positioning-GANSS-AddNavigationModels,
	-- Extension mechanism for non-release99 information
		vc50NonCriticalExtensions		SEQUENCE {
			sysInfoType15-2ter-vc50ext		SysInfoType15-2ter-vc50ext-IEs,
			nonCriticalExtensions				SEQUENCE {}						OPTIONAL
		}	OPTIONAL
}

SysInfoType15-2ter-vc50ext-IEs ::=	SEQUENCE {
	-- Measurement IEs
		ue-positioning-GANSS-AddNavigationModels 	UE-Positioning-GANSS-AddNavigationModels-vc50ext	OPTIONAL
}

SysInfoType15-3 ::=					SEQUENCE {
	-- Almanac and other data
		transmissionTOW					GPS-TOW-1sec,
		ue-positioning-GPS-Almanac		UE-Positioning-GPS-Almanac			OPTIONAL,
		ue-positioning-GPS-IonosphericModel	UE-Positioning-GPS-IonosphericModel		OPTIONAL,
		ue-positioning-GPS-UTC-Model		UE-Positioning-GPS-UTC-Model			OPTIONAL,
		satMask								BIT STRING (SIZE (1..32))				OPTIONAL,
		lsbTOW								BIT STRING (SIZE (8))					OPTIONAL,
	-- Extension mechanism for non- release99 information
		va40NonCriticalExtensions			SEQUENCE {
			sysInfoType15-3-va40ext			SysInfoType15-3-va40ext-IEs,
			nonCriticalExtensions				SEQUENCE {}						OPTIONAL
		}	OPTIONAL
}

SysInfoType15-3-va40ext-IEs ::=		SEQUENCE {
	-- Measurement IEs
		ue-positioning-GPS-Almanac		UE-Positioning-GPS-Almanac-va40ext	OPTIONAL
}

SysInfoType15-3bis ::=				SEQUENCE {
	-- Measurement IEs
		ue-positioning-GANSS-Almanac	UE-Positioning-GANSS-Almanac				OPTIONAL,
		ue-positioning-GANSS-TimeModels	UE-Positioning-GANSS-TimeModels		OPTIONAL,
		ue-positioning-GANSS-UTC-Model	UE-Positioning-GANSS-UTCModel		OPTIONAL,
	-- Extension mechanism for non-release99 information
		v860NonCriticalExtensions		SEQUENCE {
			sysInfoType15-3bis-v860ext		SysInfoType15-3bis-v860ext-IEs,
			va40NonCriticalExtensions	SEQUENCE {
				sysInfoType15-3bis-va40ext	SysInfoType15-3bis-va40ext-IEs,
				vc50NonCriticalExtensions	SEQUENCE {
					sysInfoType15-3bis-vc50ext		SysInfoType15-3bis-vc50ext-IEs,
					nonCriticalExtensions			SEQUENCE {}					OPTIONAL
				}	OPTIONAL
			}	OPTIONAL
		}	OPTIONAL
}

SysInfoType15-3bis-v860ext-IEs ::=	SEQUENCE {
	-- Measurement IEs
		ue-Positioning-GANSS-Almanac			UE-Positioning-GANSS-Almanac-v860ext	OPTIONAL,
		ue-Positioning-GANSS-AddUTCModels	UE-Positioning-GANSS-AddUTCModels	OPTIONAL,
		ue-Positioning-GANSS-AuxiliaryInfo	UE-Positioning-GANSS-AuxiliaryInfo	OPTIONAL
}

SysInfoType15-3bis-va40ext-IEs ::=	SEQUENCE {
	-- Measurement IEs
		ue-Positioning-GANSS-Almanac		UE-Positioning-GANSS-Almanac-va40ext		OPTIONAL,
		ue-positioning-GANSS-TimeModels	UE-Positioning-GANSS-TimeModels-va40ext	OPTIONAL
}

SysInfoType15-3bis-vc50ext-IEs ::= SEQUENCE {
	-- Measurement IEs
		ue-Positioning-GANSS-Almanac			UE-Positioning-GANSS-Almanac-vc50ext	OPTIONAL,
		ue-Positioning-GANSS-AddUTCModels	UE-Positioning-GANSS-AddUTCModels-vc50ext	OPTIONAL
}

SysInfoType15-4 ::=					SEQUENCE {
	-- Measurement IEs
		ue-positioning-OTDOA-CipherParameters	UE-Positioning-CipherParameters	OPTIONAL,
		ue-positioning-OTDOA-AssistanceData		UE-Positioning-OTDOA-AssistanceData,
		v3a0NonCriticalExtensions			SEQUENCE {
			sysInfoType15-4-v3a0ext				SysInfoType15-4-v3a0ext,
		-- Extension mechanism for non- release99 information
			v4b0NonCriticalExtensions			SEQUENCE {
				sysInfoType15-4-v4b0ext				SysInfoType15-4-v4b0ext,
				nonCriticalExtensions				SEQUENCE {}		OPTIONAL
			}	OPTIONAL
		}	OPTIONAL
}

SysInfoType15-4-v3a0ext ::=	SEQUENCE {
	sfn-Offset-Validity				SFN-Offset-Validity							OPTIONAL
}

SysInfoType15-4-v4b0ext ::= SEQUENCE {
	ue-Positioning-OTDOA-AssistanceData-r4ext	UE-Positioning-OTDOA-AssistanceData-r4ext	OPTIONAL
}

SysInfoType15-5 ::=			SEQUENCE {
	-- Measurement IEs
		ue-positioning-OTDOA-AssistanceData-UEB		UE-Positioning-OTDOA-AssistanceData-UEB,
		v3a0NonCriticalExtensions			SEQUENCE {
			sysInfoType15-5-v3a0ext				SysInfoType15-5-v3a0ext,
			-- Extension mechanism for non- release99 information
			v770NonCriticalExtensions			SEQUENCE {
				sysInfoType15-5-v770ext				SysInfoType15-5-v770ext-IEs,
				nonCriticalExtensions				SEQUENCE {}		OPTIONAL
			}	OPTIONAL
		}	OPTIONAL
}

SysInfoType15-5-v3a0ext ::=	SEQUENCE {
	sfn-Offset-Validity			SFN-Offset-Validity		OPTIONAL
}

SysInfoType15-5-v770ext-IEs ::=		SEQUENCE {
	ue-Positioning-OTDOA-AssistanceData-UEB-ext
											UE-Positioning-OTDOA-AssistanceData-UEB-ext		OPTIONAL
}

SysInfoType15-6 ::=					SEQUENCE {
	-- Measurement IEs
		ue-positioning-GANSS-TOD		INTEGER (0..86399),
		ue-positioning-GANSS-ReferenceMeasurementInformation
										UE-Positioning-GANSS-ReferenceMeasurementInfo,
	-- Extension mechanism for non-release99 information
		va40NonCriticalExtensions		SEQUENCE {
			sysInfoType15-6-va40ext			SysInfoType15-6-va40ext-IEs,
				vc50NonCriticalExtensions	SEQUENCE {
				sysInfoType15-6-vc50ext			SysInfoType15-6-vc50ext-IEs,
				nonCriticalExtensions			SEQUENCE {}				OPTIONAL
			}	OPTIONAL
		}	OPTIONAL
}

SysInfoType15-6-va40ext-IEs ::=		SEQUENCE {
	ue-positioning-GANSS-ReferenceMeasurementInformation
										UE-Positioning-GANSS-ReferenceMeasurementInfo-va40ext
}

SysInfoType15-6-vc50ext-IEs ::=		SEQUENCE {
	ue-positioning-GANSS-ReferenceMeasurementInformation
										UE-Positioning-GANSS-ReferenceMeasurementInfo-vc50ext
}

SysInfoType15-7 ::=					SEQUENCE {
	-- Measurement IEs
		ue-positioning-GANSS-DataBitAssistance	UE-Positioning-GANSS-Data-Bit-Assistance,
	-- Extension mechanism for non-release99 information
		nonCriticalExtensions			SEQUENCE {}				OPTIONAL
}

SysInfoType15-8 ::=					SEQUENCE {
	-- Measurement IEs
		ue-positioning-GANSS-DataCipheringInfo	UE-Positioning-CipherParameters	OPTIONAL,
		ue-positioning-GANSS-realTimeIntegrity	UE-Positioning-GANSS-RealTimeIntegrity	OPTIONAL,
	-- Extension mechanism for non-release99 information
		nonCriticalExtensions			SEQUENCE {}				OPTIONAL
}

SysInfoType16 ::=					SEQUENCE {
	-- Radio bearer IEs
		preDefinedRadioConfiguration	PreDefRadioConfiguration,
	-- Extension mechanism for non- release99 information
		v770NonCriticalExtensions		SEQUENCE {
			sysInfoType16-v770ext			SysInfoType16-v770ext-IEs,
			v920NonCriticalExtensions		SEQUENCE {
				sysInfoType16-v920ext			SysInfoType16-v920ext-IEs,
				nonCriticalExtensions			SEQUENCE {}			OPTIONAL
			}	OPTIONAL
		}	OPTIONAL
}

SysInfoType16-v770ext-IEs ::=		SEQUENCE {
		preDefinedRadioConfiguration	PreDefRadioConfiguration-v770ext
}

SysInfoType16-v920ext-IEs ::=		SEQUENCE {
		preDefinedRadioConfiguration	PreDefRadioConfiguration-v920ext
}

SysInfoType17 ::=					SEQUENCE {
	-- Physical channel IEs
		-- If PDSCH/PUSCH is configured for 1.28Mcps or 7.68Mcps TDD, pusch-SysInfoList and
		-- pdsch-SysInfoList should be absent and the info included in the respective
		-- tdd128SpecificInfo or tdd768SpecificInfo instead.
		-- If PDSCH/PUSCH is configured for 3.84Mcps TDD in R5, HCR-r5-SpecificInfo should also be
		-- included.
		pusch-SysInfoList				PUSCH-SysInfoList				OPTIONAL,
		pdsch-SysInfoList				PDSCH-SysInfoList				OPTIONAL,
	-- Extension mechanism for non- release99 information
		v4b0NonCriticalExtensions		SEQUENCE {
			sysInfoType17-v4b0ext			SysInfoType17-v4b0ext-IEs,
			v590NonCriticalExtensions	SEQUENCE {
				sysInfoType17-v590ext			SysInfoType17-v590ext-IEs		OPTIONAL,
				v770NonCriticalExtensions		SEQUENCE {
					sysInfoType17-v770ext			SysInfoType17-v770ext-IEs,
					nonCriticalExtensions			SEQUENCE {}				OPTIONAL
				}							OPTIONAL
			}							OPTIONAL
		}							OPTIONAL
}

SysInfoType17-v4b0ext-IEs ::=		SEQUENCE {
	tdd128SpecificInfo					SEQUENCE {
		pusch-SysInfoList					PUSCH-SysInfoList-LCR-r4		OPTIONAL,
		pdsch-SysInfoList					PDSCH-SysInfoList-LCR-r4		OPTIONAL
	}																	OPTIONAL
}

SysInfoType17-v590ext-IEs ::=		SEQUENCE {
	hcr-r5-SpecificInfo				SEQUENCE {
		pusch-SysInfoList					PUSCH-SysInfoList-HCR-r5	OPTIONAL,
		pdsch-SysInfoList					PDSCH-SysInfoList-HCR-r5	OPTIONAL
	}															OPTIONAL
}

SysInfoType17-v770ext-IEs ::=		SEQUENCE {
	tdd768SpecificInfo					SEQUENCE {
		pusch-SysInfoList-SFN				PUSCH-SysInfoList-SFN-VHCR	OPTIONAL,
		pdsch-SysInfoList-SFN				PDSCH-SysInfoList-VHCR-r7		OPTIONAL
	}		OPTIONAL
}

SysInfoType18 ::=						SEQUENCE {
		idleModePLMNIdentities			PLMNIdentitiesOfNeighbourCells		OPTIONAL,
		connectedModePLMNIdentities	PLMNIdentitiesOfNeighbourCells		OPTIONAL,
	-- Extension mechanism for non- release99 information
		v6b0NonCriticalExtensions		SEQUENCE {
			sysInfoType18-v6b0ext			SysInfoType18-v6b0ext,
			v860NonCriticalExtensions		SEQUENCE {
				sysInfoType18-v860ext			SysInfoType18-v860ext,
				vc50NonCriticalExtensions	SEQUENCE {
					sysInfoType18-vc50ext		SysInfoType18-vc50ext,
					nonCriticalExtensions			SEQUENCE {}		OPTIONAL
				}	OPTIONAL
			}	OPTIONAL
		}	OPTIONAL
}

SysInfoType18-v6b0ext ::=				SEQUENCE {
		idleModePLMNIdentitiesSIB11bis		PLMNIdentitiesOfNeighbourCells		OPTIONAL,
		connectedModePLMNIdentitiesSIB11bis	PLMNIdentitiesOfNeighbourCells		OPTIONAL
}

SysInfoType18-v860ext ::=				SEQUENCE {
		idleModePLMNIdentities			PLMNIdentitiesOfNeighbourCells-v860ext	OPTIONAL,
		connectedModePLMNIdentities		PLMNIdentitiesOfNeighbourCells-v860ext	OPTIONAL
}

SysInfoType18-vc50ext	::=				SEQUENCE {
		idleModePLMNIdentitiesSIB11ter	PLMNIdentitiesOfNeighbourCells-vc50ext	OPTIONAL,
		connectedModePLMNIdentitiesSIB11ter	PLMNIdentitiesOfNeighbourCells-vc50ext	OPTIONAL
}

SysInfoType19 ::=						SEQUENCE {
	-- Measurement IEs
		utra-PriorityInfoList				UTRA-PriorityInfoList,
		gsm-PriorityInfoList				GSM-PriorityInfoList					OPTIONAL,
		eutra-FrequencyAndPriorityInfoList	EUTRA-FrequencyAndPriorityInfoList		OPTIONAL,
	-- Extension mechanism for non-release8 information
		v920NonCriticalExtensions		SEQUENCE {
			sysInfoType19-v920ext			SysInfoType19-v920ext,
			va80NonCriticalExtensions		SEQUENCE {
				sysInfoType19-va80ext			SysInfoType19-va80ext,
				vb30NonCriticalExtensions		SEQUENCE {
					sysInfoType19-vb30ext			SysInfoType19-vb30ext,
					vb50NonCriticalExtensions		SEQUENCE {
						sysInfoType19-vb50ext			SysInfoType19-vb50ext,
						vb80NonCriticalExtensions		SEQUENCE {
							sysInfoType19-vb80ext			SysInfoType19-vb80ext,
							vc50NonCriticalExtensions		SEQUENCE {
								sysInfoType19-vc50ext			SysInfoType19-vc50ext,
								vd20NonCriticalExtensions			SEQUENCE {
									sysInfoType19-vd20ext			SysInfoType19-vd20ext,
									nonCriticalExtensions			SEQUENCE {}			OPTIONAL
								}			OPTIONAL
							}	OPTIONAL
						}	OPTIONAL
					}	OPTIONAL
				}	OPTIONAL
			}	OPTIONAL
		}	OPTIONAL
}

SysInfoType19-v920ext ::=				SEQUENCE {
		utra-PriorityInfoList-v920ext					UTRA-PriorityInfoList-v920ext,
		eutra-FrequencyAndPriorityInfoList-v920ext		EUTRA-FrequencyAndPriorityInfoList-v920ext
}

SysInfoType19-va80ext ::=				SEQUENCE {
		multipleEutraFrequencyInfoList		MultipleEUTRAFrequencyInfoList		OPTIONAL
}

SysInfoType19-vb30ext ::=				SEQUENCE {
		cell-fach-meas-ind					ENUMERATED { high-priority-layers, all-layers }	OPTIONAL
}

SysInfoType19-vb50ext ::=				SEQUENCE {
		gsmTreselectionScalingFactor			TreselectionScalingFactor2			OPTIONAL,
		eutraTreselectionScalingFactor			TreselectionScalingFactor2		OPTIONAL,
		numberOfApplicableEARFCN					INTEGER (0..7)						OPTIONAL,
		eutra-FrequencyAndPriorityInfoList-vb50ext	EUTRA-FrequencyAndPriorityInfoList-vb50ext					OPTIONAL,
		eutra-FrequencyAndPriorityInfoExtensionList	EUTRA-FrequencyAndPriorityInfoExtensionList					OPTIONAL,
		multipleEutraFrequencyInfoExtensionList		MultipleEUTRAFrequencyInfoExtensionList	OPTIONAL,
	-- Measurement IEs
		eutra-FrequencyRACHReportingInfo		EUTRA-FrequencyRACHReportingInfo		OPTIONAL
}

SysInfoType19-vb80ext ::=				SEQUENCE {
		eutra-FrequencyAndPriorityInfoExtensionList-vb80ext		EUTRA-FrequencyAndPriorityInfoExtensionList-vb80ext							OPTIONAL
}

SysInfoType19-vc50ext	::=				SEQUENCE {
		eutra-FrequencyRACHReportingInfo-vc50ext		EUTRA-FrequencyRACHReportingInfo-vc50ext							OPTIONAL,
		eutra-FrequencyAndPriorityInfoList-vc50ext	EUTRA-FrequencyAndPriorityInfoList-vc50ext OPTIONAL,
		eutra-FrequencyAndPriorityInfoExtensionList-vc50ext
									EUTRA-FrequencyAndPriorityInfoExtensionList-vc50ext		OPTIONAL
}

SysInfoType19-vd20ext	::=				SEQUENCE {
		eutra-FrequencyAndPriorityInfoList-vd20ext	EUTRA-FrequencyAndPriorityInfoList-vd20ext OPTIONAL,
		eutra-FrequencyAndPriorityInfoExtensionList-vd20ext
									EUTRA-FrequencyAndPriorityInfoExtensionList-vd20ext		OPTIONAL
}

SysInfoType20 ::=					SEQUENCE {
		hNBName							HNBName										OPTIONAL,
		nonCriticalExtensions			SEQUENCE {}									OPTIONAL
}

SysInfoType21 ::=					SEQUENCE {
		eab-Parameters					EAB-Parameters								OPTIONAL,
		nonCriticalExtensions			SEQUENCE {}									OPTIONAL
}

SysInfoType22 ::=				SEQUENCE {
--	In the Tabular there are separate definitions for prach-PreambleForEnhancedUplinkListType1Ext
--	and prach-PreambleForEnhancedUplinkListType2Ext/prach-PreambleForEnhancedUplinkListType3Ext even
--		though the contents are the same. The only difference is in how the IE “Weight” is used in
--		calculating the weight for each signalled PRACH Control Parameters.
--	To simplify the ASN.1, a single definition is used here for all three cases.
	prach-PreambleForEnhancedUplinkListType1Ext
										PRACH-PreambleForEnhancedUplinkExtList OPTIONAL,
	prach-PreambleForEnhancedUplinkListType2Ext
										PRACH-PreambleForEnhancedUplinkExtList OPTIONAL,
	prach-PreambleForEnhancedUplinkListType3Ext
										PRACH-PreambleForEnhancedUplinkExtList OPTIONAL,
	concurrent-Deployment-2ms-10ms-TTI	Concurrent-Deployment-2ms-10ms-TTI	   		OPTIONAL,
	nodeB-Trigger-HS-DPCCH-Transmission	NodeB-Trigger-HS-DPCCH-Transmission	   		OPTIONAL,
	fallback-R99-PRACH-info				Fallback-R99-PRACH-info-IEs				   	OPTIONAL,
	commonEDCHResourceConfigInfoListExt	CommonEDCHResourceConfigInfoListExt		   	OPTIONAL,
	hs-dsch-DrxCellfach-SecondDrx-info	HS-DSCH-DrxCellfach-SecondDrx-info			OPTIONAL,
	-- Extension mechanism for non- release11 information
	vc50NonCriticalExtensions			SEQUENCE {
		sysInfoType22-vc50ext				SysInfoType22-vc50ext-IEs,
		nonCriticalExtensions				SEQUENCE {}	OPTIONAL
	}	OPTIONAL
}

SysInfoType22-vc50ext-IEs ::= SEQUENCE {
	cell-Reselection-indication-reporting		ENUMERATED { true }					OPTIONAL
}

SysInfoType23 ::=					SEQUENCE {
		wlanRepresentation				CHOICE {
			wlanOffloadInformationPerPLMN-List			WLANOffloadInformationPerPLMN-List,
			wlanOffloadInformationForAll				WLANOffloadInformation
		},
		nonCriticalExtensions			SEQUENCE {}									OPTIONAL
}

SysInfoType24 ::=				SEQUENCE {
	dtchTransmissionBlocked				BIT STRING (SIZE (maxNumAccessGroups))		OPTIONAL,
	expirationTimeFactor				ExpirationTimeFactor2						OPTIONAL,
	nonCriticalExtensions				SEQUENCE {}	OPTIONAL
}

SysInfoType25 ::=					SEQUENCE {
	acdc-Parameters					ACDC-Parameters,
	nonCriticalExtensions				SEQUENCE {}								OPTIONAL
}

SysInfoTypeSB1 ::=					SEQUENCE {
	-- Other IEs
		sib-ReferenceList				SIB-ReferenceList,
	-- Extension mechanism for non- release99 information
		v6b0NonCriticalExtensions		SEQUENCE {
			sysInfoTypeSB1-v6b0ext			SysInfoTypeSB1-v6b0ext,
			v860NonCriticalExtensions		SEQUENCE {
				sysInfoTypeSB1-v860ext			SysInfoTypeSB1-v860ext,
					vc50NonCriticalExtensions	SEQUENCE {
						sysInfoTypeSB1-vc50ext		SysInfoTypeSB1-vc50ext,
				nonCriticalExtensions			SEQUENCE {}						OPTIONAL
				}		OPTIONAL
			}		OPTIONAL
		}		OPTIONAL
}

SysInfoTypeSB1-v6b0ext ::=			SEQUENCE {
	extSIBTypeInfoSchedulingInfo-List	ExtSIBTypeInfoSchedulingInfo-List		OPTIONAL
}

SysInfoTypeSB1-v860ext ::=			SEQUENCE {
	extSIBTypeInfoSchedulingInfo-List	ExtSIBTypeInfoSchedulingInfo-List2		OPTIONAL,
	extGANSS-SIBTypeInfoSchedulingInfoList
										ExtGANSS-SIBTypeInfoSchedulingInfoList	OPTIONAL
}

SysInfoTypeSB1-vc50ext ::=			SEQUENCE {
	sib-ReferenceList					SIBSb-ReferenceList2					OPTIONAL,
	extSIBTypeInfoSchedulingInfo-List	ExtSIBTypeInfoSchedulingInfo-List3		OPTIONAL
}

SysInfoTypeSB2 ::=					SEQUENCE {
	-- Other IEs
		sib-ReferenceList				SIB-ReferenceList,
	-- Extension mechanism for non- release99 information
		v6b0NonCriticalExtensions		SEQUENCE {
			sysInfoTypeSB2-v6b0ext			SysInfoTypeSB2-v6b0ext,
			v860NonCriticalExtensions		SEQUENCE {
				sysInfoTypeSB2-v860ext			SysInfoTypeSB2-v860ext,
					vc50NonCriticalExtensions	SEQUENCE {
						sysInfoTypeSB2-vc50ext		SysInfoTypeSB2-vc50ext,
				nonCriticalExtensions			SEQUENCE {}						OPTIONAL
				}		OPTIONAL
			}		OPTIONAL
		}		OPTIONAL
}

SysInfoTypeSB2-v6b0ext ::=			SEQUENCE {
	extSIBTypeInfoSchedulingInfo-List	ExtSIBTypeInfoSchedulingInfo-List		OPTIONAL
}

SysInfoTypeSB2-v860ext ::=			SEQUENCE {
	extSIBTypeInfoSchedulingInfo-List	ExtSIBTypeInfoSchedulingInfo-List2		OPTIONAL,
	extGANSS-SIBTypeInfoSchedulingInfoList
										ExtGANSS-SIBTypeInfoSchedulingInfoList	OPTIONAL
}

SysInfoTypeSB2-vc50ext ::=			SEQUENCE {
	sib-ReferenceList					SIBSb-ReferenceList2					OPTIONAL,
	extSIBTypeInfoSchedulingInfo-List	ExtSIBTypeInfoSchedulingInfo-List3		OPTIONAL
}


SysInfoTypeSB3 ::=					SEQUENCE {
	-- Other IEs
		sb3-ValueTag					CellValueTag2,
		sib-ReferenceList				SIB-ReferenceList2,
	-- Extension mechanism for non- release99 information
		nonCriticalExtensions			SEQUENCE {}							OPTIONAL
}

TDD-UMTS-Frequency-List ::= 			SEQUENCE (SIZE (1..maxNumTDDFreqs)) OF
											FrequencyInfoTDD

TxFailParams ::=					SEQUENCE {
	modeSpecificInfo					CHOICE {
		fdd									SEQUENCE {
			connEstFailCount					ENUMERATED {n1, n2, n3, n4},
			offsetValidity						ENUMERATED {s30, s60, s120, s240,
															s300, s420, s600, s900},
			connEstFailTempQoffset				INTEGER (0..15)			OPTIONAL
		},
		tdd									NULL
	}
}

UE-HistoryInformation ::=			SEQUENCE {
	ue-InactivityPeriod					INTEGER (1..120),
	ueMobilityStateIndicator			High-MobilityDetected				OPTIONAL,
	ul-dataVolumeHistory				DataVolumeHistory					OPTIONAL,
	dl-dataVolumeHistory				DataVolumeHistory					OPTIONAL
}

-- For systemInformationBlockType11bis the Value Tag Info "CellValueTag" is used
ValueTagInfo ::= CHOICE {
	none								NULL,
	cellValueTag						CellValueTag,
	plmn-ValueTag						PLMN-ValueTag,
	sIBOccurrenceIdentityAndValueTag	SIBOccurrenceIdentityAndValueTag
}

ValueTagInfoExtValueTag ::= CHOICE {
	cellValueTag						CellValueTag2
}

-- ***************************************************
--
--     ANSI-41 INFORMATION ELEMENTS (10.3.9)
--
-- ***************************************************

ANSI-41-GlobalServiceRedirectInfo ::= 	ANSI-41-NAS-Parameter
ANSI-41-PrivateNeighbourListInfo ::= 	ANSI-41-NAS-Parameter
ANSI-41-RAND-Information ::=			ANSI-41-NAS-Parameter
ANSI-41-UserZoneID-Information ::= 		ANSI-41-NAS-Parameter
ANSI-41-NAS-Parameter ::=				BIT STRING (SIZE (1..2048))

Min-P-REV ::=							BIT STRING (SIZE (8))

NAS-SystemInformationANSI-41 ::=		ANSI-41-NAS-Parameter
NID ::=									BIT STRING (SIZE (16))

P-REV ::=								BIT STRING (SIZE (8))

SID ::=									BIT STRING (SIZE (15))

-- ***************************************************
--
--     MBMS INFORMATION ELEMENTS (10.3.9a)
--
-- ***************************************************

MBMS-AccessProbabilityFactor ::=	ENUMERATED {
										apf0, apf32, apf64, apf96, apf128, apf160, apf192,
										apf224, apf256, apf288, apf320, apf352, apf384, apf416,
										apf448, apf480, apf512, apf544, apf576, apf608, apf640,
										apf672, apf704, apf736, apf768, apf800, apf832, apf864,
										apf896, apf928, apf960, apf1000 }

MBMS-CellGroupIdentity-r6 ::=		BIT STRING (SIZE (12))

MBMS-CommonCCTrChIdentity ::=		INTEGER (1..32)

MBMS-CommonPhyChIdentity ::=		INTEGER (1..32)

MBMS-CommonRBIdentity ::=			INTEGER (1..32)

MBMS-CommonRBInformation-r6 ::=		SEQUENCE {
	commonRBIdentity					MBMS-CommonRBIdentity,
	pdcp-Info							PDCP-Info-r4,
	rlc-Info							RLC-Info-MTCH-r6
}

MBMS-CommonRBInformationList-r6 ::= SEQUENCE (SIZE (1..maxMBMS-CommonRB)) OF
										MBMS-CommonRBInformation-r6

MBMS-CommonTrChIdentity ::=			INTEGER (1..32)

MBMS-ConnectedModeCountingScope ::= SEQUENCE {
	countingForUraPCH								BOOLEAN,
	countingForCellPCH								BOOLEAN,
	countingForCellFACH								BOOLEAN
}

MBMS-CurrentCell-SCCPCH-r6 ::=		SEQUENCE {
	sccpchIdentity						MBMS-SCCPCHIdentity					OPTIONAL,
	secondaryCCPCH-Info					MBMS-CommonPhyChIdentity,
	softComb-TimingOffset				MBMS-SoftComb-TimingOffset			OPTIONAL,
	-- If the IE transpCh-InfoCommonForAllTrCh is absent, the default TFCS as specified
	-- in 14.10.1 applies
	transpCh-InfoCommonForAllTrCh		MBMS-CommonCCTrChIdentity			OPTIONAL,
	transpCHInformation					MBMS-TrCHInformation-CurrList
}

MBMS-CurrentCell-SCCPCHList-r6 ::=	SEQUENCE (SIZE (1..maxSCCPCH)) OF
										MBMS-CurrentCell-SCCPCH-r6

MBMS-FACHCarryingMTCH-List ::=		SEQUENCE (SIZE (1..maxFACHPCH)) OF
											TransportFormatSet

MBMS-JoinedInformation-r6 ::=		SEQUENCE {
	p-TMSI								P-TMSI-GSM-MAP						OPTIONAL
}

MBMS-L1CombiningSchedule-32 ::=		SEQUENCE {
	-- Actual L1 combining schedule values (offset, start, duration) = IE value * 4
	cycleOffset							INTEGER (0..7)						OPTIONAL,
	mtch-L1CombiningPeriodList			SEQUENCE (SIZE (1..maxMBMS-L1CP)) OF SEQUENCE {
		periodStart							INTEGER (0..7),
		periodDuration						INTEGER (1..8)
	}
}

MBMS-L1CombiningSchedule-64 ::=		SEQUENCE {
	-- Actual L1 combining schedule values (offset, start, duration) = IE value * 4
	cycleOffset							INTEGER (0..15)						OPTIONAL,
	mtch-L1CombiningPeriodList			SEQUENCE (SIZE (1..maxMBMS-L1CP)) OF SEQUENCE {
		periodStart							INTEGER (0..15),
		periodDuration						INTEGER (1..16)
	}
}

MBMS-L1CombiningSchedule-128 ::=	SEQUENCE {
	-- Actual L1 combining schedule values (offset, start, duration) = IE value * 4
	cycleOffset							INTEGER (0..31)						OPTIONAL,
	mtch-L1CombiningPeriodList			SEQUENCE (SIZE (1..maxMBMS-L1CP)) OF SEQUENCE {
		periodStart							INTEGER (0..31),
		periodDuration						INTEGER (1..32)
	}
}

MBMS-L1CombiningSchedule-256 ::=	SEQUENCE {
	-- Actual L1 combining schedule values (offset, start, duration) = IE value * 4
	cycleOffset							INTEGER (0..63)						OPTIONAL,
	mtch-L1CombiningPeriodList			SEQUENCE (SIZE (1..maxMBMS-L1CP)) OF SEQUENCE {
		periodStart							INTEGER (0..63),
		periodDuration						INTEGER (1..64)
	}
}

MBMS-L1CombiningSchedule-512 ::=	SEQUENCE {
	-- Actual L1 combining schedule values (offset, start, duration) = IE value * 4
	cycleOffset							INTEGER (0..127)						OPTIONAL,
	mtch-L1CombiningPeriodList			SEQUENCE (SIZE (1..maxMBMS-L1CP)) OF SEQUENCE {
		periodStart							INTEGER (0..127),
		periodDuration						INTEGER (1..128)
	}
}

MBMS-L1CombiningSchedule-1024 ::=	SEQUENCE {
	-- Actual L1 combining schedule values (offset, start, duration) = IE value * 4
	cycleOffset							INTEGER (0..255)						OPTIONAL,
	mtch-L1CombiningPeriodList			SEQUENCE (SIZE (1..maxMBMS-L1CP)) OF SEQUENCE {
		periodStart							INTEGER (0..255),
		periodDuration						INTEGER (1..256)
	}
}

MBMS-L1CombiningSchedule ::=		CHOICE {
	cycleLength-32						MBMS-L1CombiningSchedule-32,
	cycleLength-64						MBMS-L1CombiningSchedule-64,
	cycleLength-128						MBMS-L1CombiningSchedule-128,
	cycleLength-256						MBMS-L1CombiningSchedule-256,
	cycleLength-512						MBMS-L1CombiningSchedule-512,
	cycleLength-1024					MBMS-L1CombiningSchedule-1024
}

MBMS-L1CombiningTransmTimeDiff ::=	INTEGER (0..3)

MBMS-L23Configuration ::=			CHOICE {
	sameAsCurrent						SEQUENCE {
		currentCell-SCCPCH					MBMS-SCCPCHIdentity,
		msch-ConfigurationInfo				MBMS-MSCH-ConfigurationInfo-r6		OPTIONAL
	},
	different							SEQUENCE {
		-- If the IE transpCh-InfoCommonForAllTrCh is absent, the default TFCS as specified
		-- in 14.10.1 applies
		transpCh-InfoCommonForAllTrCh		MBMS-CommonCCTrChIdentity			OPTIONAL,
		transpCHInformation					MBMS-TrCHInformation-NeighbList
	}
}

MBMS-LogicalChIdentity ::=			INTEGER (1..15)

MBMS-MCCH-ConfigurationInfo-r6 ::=	SEQUENCE {
	accessInfoPeriodCoefficient			INTEGER (0..3),
	repetitionPeriodCoefficient			INTEGER (0..3),
	modificationPeriodCoefficient		INTEGER (7..10),
	rlc-Info							RLC-Info-MCCH-r6,
	tctf-Presence						MBMS-TCTF-Presence					OPTIONAL
}

MBMS-MICHConfigurationInfo-r6 ::=	SEQUENCE {
	michPowerOffset						MBMS-MICHPowerOffset,
	mode								CHOICE {
		fdd									SEQUENCE {
			channelisationCode256				ChannelisationCode256,
			ni-CountPerFrame					MBMS-NI-CountPerFrame,
			sttd-Indicator						BOOLEAN
		},
		-- The CHOICE tdd384 is used for both tdd384 and tdd768. If IE
		-- 'MBMS-MICHConfigurationInfo-v770ext' is not present, tdd384 applies.
		tdd384								SEQUENCE {
			timeslot							TimeslotNumber,
			midambleShiftAndBurstType			MidambleShiftAndBurstType,
			channelisationCode					DL-TS-ChannelisationCode,
			repetitionPeriodLengthOffset		RepPerLengthOffset-MICH		OPTIONAL,
			mbmsNotificationIndLength			MBMS-MICHNotificationIndLength	DEFAULT mn4
		},
		tdd128								SEQUENCE {
			timeslot							TimeslotNumber-LCR-r4,
			midambleShiftAndBurstType			MidambleShiftAndBurstType-LCR-r4,
			channelisationCodeList				SEQUENCE (SIZE (1..2)) OF
													DL-TS-ChannelisationCode,
			repetitionPeriodLengthOffset		RepPerLengthOffset-MICH		OPTIONAL,
			mbmsNotificationIndLength			MBMS-MICHNotificationIndLength	DEFAULT mn4
		}
	}
}

MBMS-MICHConfigurationInfo-v770ext ::= SEQUENCE {
	mode								CHOICE {
		-- For tdd384, IE 'MidambleShiftAndBurstType-r7' replaces IE 'MidambleShiftAndBurstType'
		-- in IE 'MBMS-MICHConfigurationInfo-r6'. IE 'MidambleShiftAndBurstType' shall be ignored.
		tdd384								SEQUENCE {
			midambleShiftAndBurstType			MidambleShiftAndBurstType-r7
		},
		-- For tdd768, the CHIOCE tdd384 in IE 'MBMS-MICHConfigurationInfo-r6' applies, except
		-- that IE 'MidambleShiftAndBurstType-VHCR' replaces IE 'MidambleShiftAndBurstType'. IE
		-- 'MidambleShiftAndBurstType' shall be ignored.
		tdd768								SEQUENCE {
			midambleShiftAndBurstType			MidambleShiftAndBurstType-VHCR
		},
		tdd128								SEQUENCE {
			mbsfnSpecialTimeSlot				TimeSlotLCR-ext					OPTIONAL
		}
	}
}

MBMS-MICHConfigurationInfo-v890ext ::= SEQUENCE {
	mode								CHOICE {
		imb384								SEQUENCE {
			channelisationCode256				ChannelisationCode256,
			ni-CountPerFrame					MBMS-NI-CountPerFrame-IMB384
		}
	}
}

MBMS-MICHNotificationIndLength ::=	ENUMERATED { mn4, mn8, mn16 }

MBMS-MICHPowerOffset ::=			INTEGER (-10..5)

MBMS-ModifedService-r6 ::=			SEQUENCE {
	mbms-TransmissionIdentity			MBMS-TransmissionIdentity,
	mbms-RequiredUEAction				MBMS-RequiredUEAction-Mod,
	mbms-PreferredFrequency				CHOICE {
		mcch								MBMS-PFLIndex,
		dcch								MBMS-PFLInfo
	}		OPTIONAL,
	--dummy is not used. If received it shall be ignored.
	dummy								ENUMERATED { true }					OPTIONAL,
	continueMCCHReading					BOOLEAN
}

MBMS-ModifedServiceList-r6 ::=		SEQUENCE (SIZE (1..maxMBMSservModif)) OF
										MBMS-ModifedService-r6

MBMS-ModifiedService-v770ext ::=	SEQUENCE {
	mbsfnClusterFrequency				MBSFN-ClusterFrequency-r7			OPTIONAL
}

MBMS-ModifiedService-LCR-v7c0ext ::= SEQUENCE {
	rbReleaseCause						MBMS-PTM-RBReleaseCause-LCR-r7		OPTIONAL
}

-- IE 'MBMS-ModifiedServiceList-v770ext' contains a list of extension data
-- associated with the MBMS transmission identities at the corresponding
-- positions in IE 'MBMS-ModifedServiceList-r6'
MBMS-ModifiedServiceList-v770ext ::= SEQUENCE (SIZE (1..maxMBMSservModif)) OF
										MBMS-ModifiedService-v770ext

-- IE 'MBMS-ModifiedServiceList-LCR-v7c0ext' contains a list of extension data
-- associated with the MBMS transmission identities at the corresponding
-- positions in IE 'MBMS-ModifedServiceList-r6'
MBMS-ModifiedServiceList-LCR-v7c0ext ::= SEQUENCE (SIZE (1..maxMBMSservModif)) OF
										MBMS-ModifiedService-LCR-v7c0ext

MBMS-MSCH-ConfigurationInfo-r6 ::=	SEQUENCE {
	mschShedulingInfo					MBMS-MSCHSchedulingInfo				OPTIONAL,
	rlc-Info							RLC-Info-MSCH-r6					OPTIONAL,
	tctf-Presence						MBMS-TCTF-Presence					OPTIONAL
}

MBMS-MSCHSchedulingInfo ::=			CHOICE {
	schedulingPeriod-32-Offset			INTEGER (0..31),
	schedulingPeriod-64-Offset			INTEGER (0..63),
	schedulingPeriod-128-Offset			INTEGER (0..127),
	schedulingPeriod-256-Offset			INTEGER (0..255),
	schedulingPeriod-512-Offset			INTEGER (0..511),
	schedulingPeriod-1024-Offset		INTEGER (0..1023)
}

MBMS-NeighbouringCellSCCPCH-r6 ::=	SEQUENCE {
	secondaryCCPCH-Info					MBMS-CommonPhyChIdentity,
	secondaryCCPCHPwrOffsetDiff			MBMS-SCCPCHPwrOffsetDiff			OPTIONAL,
	layer1Combining						CHOICE {
		fdd									SEQUENCE {
			softComb-TimingOffset				MBMS-SoftComb-TimingOffset,
			mbms-L1CombiningTransmTimeDiff		MBMS-L1CombiningTransmTimeDiff,
			mbms-L1CombiningSchedule			MBMS-L1CombiningSchedule	OPTIONAL
		},
		tdd									NULL
	}		OPTIONAL,
	mbms-L23Configuration				MBMS-L23Configuration
}

MBMS-NeighbouringCellSCCPCH-v770ext ::= SEQUENCE {
	secondaryCCPCH-Info					MBMS-CommonPhyChIdentity			OPTIONAL,
	secondaryCCPCH-InfoDiff				SecondaryCCPCHInfoDiff-MBMS,
	secondaryCCPCHPwrOffsetDiff			MBMS-SCCPCHPwrOffsetDiff			OPTIONAL,
	layer1Combining						CHOICE {
		fdd									SEQUENCE {
			softComb-TimingOffset				MBMS-SoftComb-TimingOffset,
			mbms-L1CombiningTransmTimeDiff		MBMS-L1CombiningTransmTimeDiff,
			mbms-L1CombiningSchedule			MBMS-L1CombiningSchedule	OPTIONAL
		},
		tdd									NULL
	}		OPTIONAL,
	mbms-L23Configuration				MBMS-L23Configuration
}

MBMS-NeighbouringCellSCCPCHList-r6 ::= SEQUENCE (SIZE (1..maxSCCPCH)) OF
										MBMS-NeighbouringCellSCCPCH-r6

-- IE "MBMS-NeighbouringCellSCCPCHList-v770ext" may be received as an extension of the IE
-- "MBMS-NeighbouringCellSCCPCHList-r6". When both lists are received in the same message
-- and the total number of list elements is greater than constant value 'maxSCCPCH', the
-- UE behaviour is unspecified.
MBMS-NeighbouringCellSCCPCHList-v770ext ::= SEQUENCE (SIZE (1..maxSCCPCH)) OF
										MBMS-NeighbouringCellSCCPCH-v770ext

MBMS-NetworkStandardTimeInformation-LCR-v890ext ::= SEQUENCE {
	networkStandardTime					BIT STRING (SIZE (40)),
	correlativeSFN						INTEGER (0..4095) 			OPTIONAL
}

MBMS-NI-CountPerFrame ::=			ENUMERATED { ni18, ni36, ni72, ni144 }

MBMS-NI-CountPerFrame-IMB384 ::=	ENUMERATED { ni16, ni32, ni64, ni128 }

MBMS-NumberOfNeighbourCells-r6 ::=		INTEGER (0..32)

MBMS-PFLIndex ::=					INTEGER (1..maxMBMS-Freq)

MBMS-PFLInfo ::=					FrequencyInfo

MBMS-PhyChInformation-IMB384 ::=	SEQUENCE {
	mbms-CommonPhyChIdentity			MBMS-CommonPhyChIdentity,
	secondaryCCPCHInfo-MBMS				SecondaryCCPCHFrameType2Info
}

MBMS-PhyChInformationList-IMB384 ::= SEQUENCE (SIZE (1..maxMBMS-CommonPhyCh)) OF
										MBMS-PhyChInformation-IMB384

MBMS-PhyChInformation-r6 ::=		SEQUENCE {
	mbms-CommonPhyChIdentity			MBMS-CommonPhyChIdentity,
	secondaryCCPCHInfo-MBMS				SecondaryCCPCHInfo-MBMS-r6
}

MBMS-PhyChInformation-r7 ::=		SEQUENCE {
	mbms-CommonPhyChIdentity			MBMS-CommonPhyChIdentity,
	secondaryCCPCHInfo-MBMS				SecondaryCCPCHInfo-MBMS-r7
}

MBMS-PhyChInformationList-r6 ::=	SEQUENCE (SIZE (1..maxMBMS-CommonPhyCh)) OF
										MBMS-PhyChInformation-r6

MBMS-PhyChInformationList-r7 ::=	SEQUENCE (SIZE (1..maxMBMS-CommonPhyCh)) OF
										MBMS-PhyChInformation-r7

MBMS-PL-ServiceRestrictInfo-r6 ::=	ENUMERATED { true }

MBMS-PreferredFrequencyInfo-r6 ::=	SEQUENCE {
	mbmsPreferredFrequency				INTEGER (1..maxMBMS-Freq)			OPTIONAL,
	layerConvergenceInformation			CHOICE {
		mbms-Qoffset						MBMS-Qoffset,
		mbms-HCSoffset						INTEGER (0..7)
	},
	mbms-PL-ServiceRestrictInfo			MBMS-PL-ServiceRestrictInfo-r6		OPTIONAL
}

MBMS-PreferredFrequencyList-r6 ::=	SEQUENCE (SIZE (1..maxMBMS-Freq)) OF
										MBMS-PreferredFrequencyInfo-r6

MBMS-PTMActivationTime-r6 ::=		INTEGER (0..2047)

MBMS-PTM-RBInformation-C ::=		SEQUENCE {
	rbInformation						MBMS-CommonRBIdentity,
	shortTransmissionID					MBMS-ShortTransmissionID,
	logicalChIdentity					MBMS-LogicalChIdentity
}

MBMS-PTM-RBInformation-CList ::=	SEQUENCE (SIZE (1..maxRBperTrCh)) OF
										MBMS-PTM-RBInformation-C

MBMS-PTM-RBInformation-N ::=		SEQUENCE {
	shortTransmissionID					MBMS-ShortTransmissionID,
	logicalChIdentity					MBMS-LogicalChIdentity,
	layer1-CombiningStatus				BOOLEAN}

MBMS-PTM-RBInformation-NList ::=	SEQUENCE (SIZE (1..maxRBperTrCh)) OF
										MBMS-PTM-RBInformation-N

MBMS-PTM-RBReleaseCause-LCR-r7 ::=	ENUMERATED {
										normalRelease, outOfMBMSServiceCoverageInRAN,
										networkAbnormalRelease,
										spare5, spare4, spare3, spare2, spare1 }

MBMS-Qoffset ::=					ENUMERATED { q4, q8, q12, q16, q20, q30, q40, qInfinity }

MBMS-RequiredUEAction-Mod ::=		ENUMERATED {
										none,
										acquireCountingInfo,
										acquireCountingInfoPTM-RBsUnmodified,
										acquirePTM-RBInfo,
										requestPTPRB,
										releasePTM-RB }

MBMS-RequiredUEAction-UMod ::=		ENUMERATED {
										none,
										acquirePTM-RBInfo,
										requestPTPRB }

MBMS-SCCPCHIdentity ::=				INTEGER (1..maxSCCPCH)

MBMS-SCCPCHPwrOffsetDiff ::=		ENUMERATED { mcpo-minus6, mcpo-minus3, mcpo-plus3, mcpo-plus6 }

MBMS-SelectedServiceInfo ::=		SEQUENCE {
	status								CHOICE {
		none								NULL,
		some								MBMS-SelectedServicesListFull
	}
}

MBMS-SelectedServicesListFull ::=	SEQUENCE (SIZE (1..maxMBMSservSelect)) OF
										MBMS-ServiceIdentity-r6

MBMS-SelectedServicesListShort ::=	SEQUENCE (SIZE (1..maxMBMSservSelect)) OF
										MBMS-ShortTransmissionID

MBMS-SelectedServicesShort ::=		SEQUENCE {
	mbms-SelectedServicesList			MBMS-SelectedServicesListShort,
	modificationPeriodIdentity			INTEGER (0..1)
}

MBMS-ServiceAccessInfo-r6 ::=		SEQUENCE {
	shortTransmissionID					MBMS-ShortTransmissionID,
	accessprobabilityFactor-Idle		MBMS-AccessProbabilityFactor,
	accessprobabilityFactor-Connected	MBMS-AccessProbabilityFactor		OPTIONAL,
	mbms-ConnectedModeCountingScope		MBMS-ConnectedModeCountingScope
}

MBMS-ServiceAccessInfoList-r6 ::=	SEQUENCE (SIZE (1..maxMBMSservCount)) OF
										MBMS-ServiceAccessInfo-r6

MBMS-ServiceIdentity-r6 ::=			SEQUENCE {
	serviceIdentity						OCTET STRING (SIZE (3)),
	plmn-Identity						CHOICE {
		-- The 'sameAsMIB-PLMN-Id' choice refers to the 'PLMN Identity' (R99) in MIB.
		sameAsMIB-PLMN-Id					NULL,
		other								CHOICE {
			-- The 'sameAsMIB-MultiPLMN-Id' choice refers to one of the (1..5) PLMN Identities
			-- provided in the 'Multiple PLMN List' (REL-6) in MIB.
			sameAsMIB-MultiPLMN-Id				INTEGER (1..5),
			explicitPLMN-Id						PLMN-Identity
		}
	}
}

MBMS-ServiceSchedulingInfo-r6 ::=	SEQUENCE {
	mbms-TransmissionIdentity			MBMS-TransmissionIdentity,
	mbms-ServiceTransmInfoList			MBMS-ServiceTransmInfoList			OPTIONAL,
	nextSchedulingperiod				INTEGER (0..31)
}

MBMS-ServiceSchedulingInfoList-r6 ::= SEQUENCE (SIZE (1..maxMBMSservSched)) OF
										MBMS-ServiceSchedulingInfo-r6

MBMS-ServiceTransmInfo ::=			SEQUENCE {
	-- Actual values (start, duration) = IE values * 4
	start								INTEGER (0..255),
	duration							INTEGER (1..256)
}

MBMS-ServiceTransmInfoList ::=		SEQUENCE (SIZE (1..maxMBMSTransmis)) OF
										MBMS-ServiceTransmInfo

MBMS-SessionIdentity ::=			OCTET STRING (SIZE (1))

MBMS-ShortTransmissionID ::=		INTEGER (1..maxMBMSservUnmodif)

MBMS-SIBType5-SCCPCH-r6 ::=			SEQUENCE {
	sccpchIdentity						MBMS-SCCPCHIdentity,
	transpCHInformation					MBMS-TrCHInformation-SIB5List
}

MBMS-SIBType5-SCCPCHList-r6 ::=		SEQUENCE (SIZE (1..maxSCCPCH)) OF
										MBMS-SIBType5-SCCPCH-r6

MBMS-SoftComb-TimingOffset ::=		ENUMERATED { ms0, ms10, ms20, ms40 }

MBMS-TCTF-Presence ::=				ENUMERATED { false }

MBMS-TimersAndCounters-r6 ::=		SEQUENCE {
	t-318								T-318								DEFAULT ms1000
}

MBMS-TransmissionIdentity ::=		SEQUENCE {
	mbms-ServiceIdentity				MBMS-ServiceIdentity-r6,
	mbms-SessionIdentity				MBMS-SessionIdentity				OPTIONAL
}

MBMS-TranspChInfoForCCTrCh-r6 ::=	SEQUENCE {
	commonCCTrChIdentity				MBMS-CommonCCTrChIdentity,
	transportFormatCombinationSet		TFCS
}


MBMS-TranspChInfoForEachCCTrCh-r6 ::= SEQUENCE (SIZE (1..maxMBMS-CommonCCTrCh)) OF
										MBMS-TranspChInfoForCCTrCh-r6

MBMS-TranspChInfoForEachTrCh-r6 ::= SEQUENCE (SIZE (1..maxMBMS-CommonTrCh)) OF
										MBMS-TranspChInfoForTrCh-r6

MBMS-TranspChInfoForTrCh-r6 ::=		SEQUENCE {
	commonTrChIdentity					MBMS-CommonTrChIdentity,
	transportFormatSet					TransportFormatSet
}

MBMS-TrCHInformation-Curr ::=		SEQUENCE {
	transpCh-Info						MBMS-CommonTrChIdentity,
	rbInformation						MBMS-PTM-RBInformation-CList		OPTIONAL,
	msch-ConfigurationInfo				MBMS-MSCH-ConfigurationInfo-r6		OPTIONAL
}

MBMS-TrCHInformation-CurrList ::=	SEQUENCE (SIZE (1..maxFACHPCH)) OF
										MBMS-TrCHInformation-Curr

MBMS-TrCHInformation-Neighb ::=		SEQUENCE {
	transpCh-Info						MBMS-CommonTrChIdentity,
	transpCh-CombiningStatus			BOOLEAN,
	rbInformation						MBMS-PTM-RBInformation-NList		OPTIONAL,
	msch-ConfigurationInfo				MBMS-MSCH-ConfigurationInfo-r6		OPTIONAL
}

MBMS-TrCHInformation-NeighbList ::=	SEQUENCE (SIZE (1..maxFACHPCH)) OF
										MBMS-TrCHInformation-Neighb

MBMS-TrCHInformation-SIB5 ::=		SEQUENCE {
	transpCh-Identity					INTEGER (1..maxFACHPCH),
	rbInformation						MBMS-PTM-RBInformation-CList		OPTIONAL,
	msch-ConfigurationInfo				MBMS-MSCH-ConfigurationInfo-r6		OPTIONAL
}

MBMS-TrCHInformation-SIB5List ::=	SEQUENCE (SIZE (1..maxFACHPCH)) OF
										MBMS-TrCHInformation-SIB5

MBMS-UnmodifiedService-r6 ::=		SEQUENCE {
	mbms-TransmissionIdentity			MBMS-TransmissionIdentity,
	mbms-RequiredUEAction				MBMS-RequiredUEAction-UMod,
	mbms-PreferredFrequency				MBMS-PFLIndex						OPTIONAL
}

MBMS-UnmodifiedServiceList-r6 ::=	SEQUENCE (SIZE (1..maxMBMSservUnmodif)) OF
										MBMS-UnmodifiedService-r6

MBMS-UnmodifiedService-v770ext ::=	SEQUENCE {
	mbsfnClusterFrequency				MBSFN-ClusterFrequency-r7			OPTIONAL
}

-- IE 'MBMS-UnmodifiedServiceList-v770ext' contains a list of extension data
-- associated with the MBMS transmission identities at the corresponding
-- positions in IE 'MBMS-UnmodifiedServiceList-r6'
MBMS-UnmodifiedServiceList-v770ext ::= SEQUENCE (SIZE (1..maxMBMSservUnmodif)) OF
										MBMS-UnmodifiedService-v770ext

MBSFN-ClusterFrequency-r7 ::=		INTEGER (1..maxMBSFNClusters)

MBSFNFrequency ::=					SEQUENCE {
	frequencyInfo						FrequencyInfo,
	-- IE "cellParameterID" is used only for MBSFN clusters operating in 1.28 Mcps TDD mode.
	cellParametersID					CellParametersID					OPTIONAL
}

MBSFNFrequency-v860ext ::=			SEQUENCE {
	imb-Indication						ENUMERATED { true }					OPTIONAL
}

MBSFNFrequencyList ::=				SEQUENCE (SIZE (0..maxMBSFNClusters)) OF
										MBSFNFrequency

-- List of extensions to the corresponding elements of IE "MBSFNFrequencyList"
MBSFNFrequencyList-v860ext ::=		SEQUENCE (SIZE (0..maxMBSFNClusters)) OF
										MBSFNFrequency-v860ext

MBSFNOnlyService ::=				ENUMERATED {true}

MBSFNservicesNotNotified-r7 ::=		SEQUENCE {
	notificationOfAllMBSFNServicesInTheBand
										ENUMERATED { true }					OPTIONAL
}

MBSFNInterFrequencyNeighbour-r7 ::=	SEQUENCE {
	mbsfnFrequency						FrequencyInfo,
	mbsfnServicesNotification			CHOICE {
		mbsfnServicesNotified				NULL,
		mbsfnServicesNotNotified			MBSFNservicesNotNotified-r7
	}
}

MBSFNInterFrequencyNeighbour-v860ext ::= SEQUENCE {
	imb-Indication						ENUMERATED { true }					OPTIONAL
}

MBSFN-InterFrequencyNeighbourList-r7 ::= SEQUENCE (SIZE (1..maxMBSFNClusters)) OF
										MBSFNInterFrequencyNeighbour-r7

-- List of extensions to the corresponding elements of IE "MBSFN-InterFrequencyNeighbourList-r7"
MBSFN-InterFrequencyNeighbourList-v860ext ::= SEQUENCE (SIZE (1..maxMBSFNClusters)) OF
										MBSFNInterFrequencyNeighbour-v860ext

MBSFN-TDDInformation ::=			SEQUENCE (SIZE (1..maxTS)) OF
										MBSFN-TDDTimeSlotInfo

MBSFN-TDDInformation-LCR ::=		SEQUENCE (SIZE (1..maxMBSFNClusters)) OF
										MBSFN-TDDTimeSlotInfo-LCR

MBSFN-TDDTimeSlotInfo ::=			SEQUENCE {
	timeSlotNumber						TimeslotNumber-LCR-r4,
	cellParametersID					CellParametersID
}

MBSFN-TDDTimeSlotInfo-LCR ::=		SEQUENCE {
	frequencyIndex						INTEGER (1..maxMBSFNClusters),
	timeSlotList						MBSFN-TDDInformation
}

MBSFN-TDM-Info ::=					SEQUENCE {
	shortTransmissionID					MBMS-ShortTransmissionID,
	tDMPeriod							INTEGER (2..9),
	tDMOffset							INTEGER (0..8),
	tDMLength							INTEGER (1..8)
}

MBSFN-TDM-Info-List ::=				SEQUENCE (SIZE (1..maxMBMSservUnmodif)) OF
										MBSFN-TDM-Info

-- ***************************************************
--
--     WLAN Offload INFORMATION ELEMENTS (10.3.9b)
--
-- ***************************************************

WLANOffloadConfig	::=		SEQUENCE {
	threshServingRSCP 				WLANThreshServingRSCP					OPTIONAL,
	threshServingECNO 				WLANThreshServingECNO					OPTIONAL,
	threshChannelUtilization		WLANThreshChannelUtilization			OPTIONAL,
	threshBackhaulBandwidth			WLANThreshBackhaulBandwidth				OPTIONAL,
	threshBeaconRSSI				WLANThreshBeaconRSSI					OPTIONAL,
	offloadPreferenceIndicator		BIT STRING (SIZE (16))					OPTIONAL,
	t-SteeringWLAN					T-Reselection-S							OPTIONAL
}

WLANThreshServingRSCP	::=	SEQUENCE {
	-- Actual value = IE value * 2 + 1
	threshServingLow				INTEGER (-60..-13),
	-- Actual value = IE value * 2 + 1
	threshServingHigh				INTEGER (-60..-13)
}

WLANThreshServingECNO	::=	SEQUENCE {
	threshServingLow2				INTEGER (-24..0),
	threshServingHigh2 				INTEGER (-24..0)
}

WLANThreshChannelUtilization	::=	SEQUENCE {
	threshChannelUtilizationLow			INTEGER (0..255),
	threshChannelUtilizationHigh		INTEGER (0..255)
}

WLANThreshBackhaulBandwidth	::=		SEQUENCE {
	threshBackhaulDLBandwidthLow		WLANThreshBackhaulRate,
	threshBackhaulDLBandwidthHigh 		WLANThreshBackhaulRate,
	threshBackhaulULBandwidthLow		WLANThreshBackhaulRate,
	threshBackhaulULBandwidthHigh		WLANThreshBackhaulRate
}

WLANThreshBeaconRSSI 		::=		SEQUENCE {
	-- Actual value = IE value - 128
threshBeaconRSSILow					INTEGER (0..255),
	-- Actual value = IE value - 128
threshBeaconRSSIHigh				INTEGER (0..255)
}

WLANIdentifierList ::=				SEQUENCE (SIZE (1..maxWLANID)) OF
										WLANIdentifier

WLANIdentifier ::=				SEQUENCE {
	ssid							OCTET STRING (SIZE (1..32))		OPTIONAL,
	bssid							OCTET STRING (SIZE (6))			OPTIONAL,
	hessid							OCTET STRING (SIZE (6))			OPTIONAL
}

WLANOffloadInformationPerPLMN-List ::= 		SEQUENCE (SIZE (1..6)) OF WLANOffloadInformation

WLANOffloadInformation ::=	SEQUENCE {
	wlanOffloadConfig					WLANOffloadConfig 					OPTIONAL,
	wlanIdentifierList					WLANIdentifierList 					OPTIONAL
}

WLANThreshBackhaulRate	::=	ENUMERATED { r0, r4, r8, r16, r32, r64, r128, r256,
											 r512, r1024, r2048, r4096, r8192, r16384, r32768,
											 r65536, r131072, r262144, r524288, r1048576,
											 r2097152, r4194304, r8388608, r16777216,
											 r33554432, r67108864, r134217728, r268435456,
											 r536870912, r1073741824, r2147483648, r4294967296
}

END

-- 3GPP TS 25.331 V17.1.0 (2022-06)
--
-- 11.4	Constant definitions
--
Constant-definitions DEFINITIONS AUTOMATIC TAGS ::=

BEGIN

hiPDSCHidentities			INTEGER ::= 64
hiPUSCHidentities			INTEGER ::= 64
hiRM						INTEGER ::= 256
maxAC						INTEGER ::= 16
maxAdditionalMeas 			INTEGER ::= 4
maxAddPos					INTEGER ::= 8
maxASC						INTEGER ::= 8
maxASCmap					INTEGER ::= 7
maxASCpersist				INTEGER ::= 6
maxBeacons					INTEGER ::= 64
maxBTs						INTEGER ::= 32
maxCCTrCH					INTEGER ::= 8
maxCellMeas 				INTEGER ::= 32
maxCellMeas-ext 				INTEGER ::= 80
maxCellMeas-ext2			INTEGER ::= 48
maxCellMeasOnSecULFreq 		INTEGER ::= 32
maxCellMeas-1				INTEGER ::= 31
maxCellMeas-ext-1 			INTEGER ::= 79
maxCellMeasOnSecULFreq-1	INTEGER ::= 31
maxCNdomains				INTEGER ::= 4
maxCommonHRNTI				INTEGER ::= 4
maxCommonQueueID			INTEGER ::= 2
maxCPCHsets					INTEGER ::= 16
maxDedicatedCSGFreq			INTEGER ::= 4
maxDPCH-DLchan				INTEGER ::= 8
maxDPDCH-UL					INTEGER ::= 6
maxDRACclasses				INTEGER ::= 8
maxExcludedDetectedSetCells	INTEGER ::= 64
maxE-DCHMACdFlow			INTEGER ::= 8
maxE-DCHMACdFlow-1			INTEGER ::= 7
maxMultipleFrequencyBandsFDD	INTEGER ::= 8
maxMultipleFrequencyBandsEUTRA	INTEGER ::= 8
maxEUTRACellPerFreq			INTEGER ::= 16
maxEUTRATargetFreqs			INTEGER ::= 8
maxEDCHRL					INTEGER ::= 4
maxEDCHRL-1					INTEGER ::= 3
maxEDCHs					INTEGER ::= 32
maxEDCHs-1					INTEGER ::= 31
maxEDCHTxPattern-TDD128		INTEGER ::= 4 -- maxEDCHTxPattern-TDD128	should be 3
maxEDCHTxPattern-TDD128-1	INTEGER ::= 3 -- maxEDCHTxPattern-TDD128-1	should be 2
maxERNTIgroup				INTEGER ::= 32
maxERNTIperGroup			INTEGER ::= 2
maxERUCCH					INTEGER ::= 256
maxFACHPCH					INTEGER ::= 8
maxFreq						INTEGER ::= 8
maxFreqBandsEUTRA			INTEGER ::= 16
maxFreqBandsEUTRA-ext		INTEGER ::= 48
maxFreqBandsFDD				INTEGER ::= 8
maxFreqBandsFDD2			INTEGER ::= 22
maxFreqBandsFDD3			INTEGER ::= 86
maxFreqBandsFDD-ext			INTEGER ::= 15	-- maxFreqBandsFDD-ext ::= 22 - (maxFreqBandsFDD - 1)
maxFreqBandsFDD-ext2		INTEGER ::= 64	-- maxFreqBandsFDD-ext2 ::= 86 - maxFreqBandsFDD2
maxFreqBandsFDD-ext3		INTEGER ::= 78	-- maxFreqBandsFDD-ext3 ::= 86 - maxFreqBandsFDD
maxFreqBandsIndicatorSupport	INTEGER ::= 2
maxFreqBandsTDD				INTEGER ::= 4
maxFreqBandsTDD-ext			INTEGER ::= 16
maxFreqBandsGSM				INTEGER ::= 16
maxFreqMeasWithoutCM		INTEGER ::= 2
maxGANSS					INTEGER ::= 8
maxGANSS-1					INTEGER ::= 7
maxGANSSSat					INTEGER ::= 64
maxGANSSSat-1				INTEGER ::= 63
maxGERAN-SI					INTEGER ::= 8
maxGSMTargetCells			INTEGER ::= 32
maxHNBNameSize				INTEGER ::= 48
maxHProcesses 				INTEGER ::= 8
maxHS-SCCHLessTrBlk			INTEGER ::= 4
maxHSDSCHTBIndex			INTEGER ::= 64
maxHSDSCHTBIndex-tdd384		INTEGER ::= 512
maxHSSCCHs					INTEGER ::= 4
maxHSSCCHs-1				INTEGER ::= 3
maxHSSICH-TDD128			INTEGER ::= 4
maxHSSICH-TDD128-1			INTEGER ::= 3
maxIGPInfo					INTEGER ::= 320
maxInterSysMessages			INTEGER ::= 4
maxLoCHperRLC				INTEGER ::= 2
maxLoggedMeasReport			INTEGER	::=	128
maxMAC-d-PDUsizes			INTEGER ::= 8
maxMBMS-CommonCCTrCh		INTEGER ::= 32
maxMBMS-CommonPhyCh			INTEGER ::= 32
maxMBMS-CommonRB			INTEGER ::= 32
maxMBMS-CommonTrCh			INTEGER ::= 32
maxMBMS-Freq				INTEGER ::= 4
maxMBMS-L1CP				INTEGER ::= 4
maxMBMSservCount			INTEGER ::= 8
maxMBMSservModif			INTEGER ::= 32
maxMBMSservSched			INTEGER ::= 16
maxMBMSservSelect			INTEGER ::= 8
maxMBMSservUnmodif			INTEGER ::= 64
maxMBMSTransmis				INTEGER ::= 4
maxMBSFNClusters			INTEGER ::= 16
maxMeasCSGRange				INTEGER ::= 4
maxMeasEvent				INTEGER ::= 8
maxMeasEventOnSecULFreq		INTEGER ::= 8
maxMeasIdentity				INTEGER ::= 32
maxMeasIntervals			INTEGER ::= 3
maxMeasOccasionPattern		INTEGER ::= 5
maxMeasOccasionPattern-1	INTEGER ::= 4
maxMeasParEvent				INTEGER ::= 2
maxNonContiguousMultiCellCombinations	INTEGER ::= 3
maxNumAccessGroups			INTEGER ::= 16
maxNumAcdcCategory			INTEGER ::= 16
maxNumCDMA2000Freqs			INTEGER ::=  8
maxNumE-AGCH				INTEGER ::= 4
maxNumE-HICH				INTEGER ::= 4
maxNumEUTRAFreqs			INTEGER ::= 8
maxNumEUTRAFreqs-FACH		INTEGER ::= 4
maxNumEUTRAFreqs-FACH-ext	INTEGER ::= 8
maxNumGSMCellGroup			INTEGER ::= 16
maxNumGSMFreqRanges			INTEGER ::= 32
maxNumFDDFreqs				INTEGER ::=  8
maxNumANRLoggedItems		INTEGER ::= 4
maxnumLoggedMeas			INTEGER ::=  8
maxNumMDTPLMN               INTEGER ::= 15
maxNumTDDFreqs				INTEGER ::=  8
maxNoOfMeas					INTEGER ::= 16
maxOtherRAT					INTEGER ::= 15
maxOtherRAT-16				INTEGER ::= 16
maxPage1					INTEGER ::= 8
maxPCPCH-APsig				INTEGER ::= 16
maxPCPCH-APsubCh			INTEGER ::= 12
maxPCPCH-CDsig				INTEGER ::= 16
maxPCPCH-CDsubCh			INTEGER ::= 12
maxPCPCH-SF					INTEGER ::= 7
maxPCPCHs					INTEGER ::= 64
maxPDCPAlgoType				INTEGER ::= 8
maxPDSCH					INTEGER ::= 8
maxPDSCH-TFCIgroups	 		INTEGER ::= 256
maxPRACH					INTEGER ::= 16
maxPRACH-EUL				INTEGER ::= 4
maxPRACH-FPACH				INTEGER ::= 8
maxPredefConfig				INTEGER ::= 16
maxOtherStateConfig			INTEGER ::= 4
maxOtherStateConfig-1		INTEGER ::= 3
maxPrio						INTEGER ::= 8
maxPrio-1					INTEGER ::= 7
maxPrio-ext					INTEGER	::= 16
maxPUSCH					INTEGER ::= 8
maxQueueIDs					INTEGER ::= 8
maxRABsetup					INTEGER ::= 16
maxRAT						INTEGER ::= 16
maxRB						INTEGER ::= 32
maxRBallRABs				INTEGER ::= 27
maxRBMuxOptions				INTEGER ::= 8
maxRBperRAB					INTEGER ::= 8
maxRBperTrCh				INTEGER ::= 16
maxReportedEUTRACellPerFreq	INTEGER ::= 4
maxReportedEUTRAFreqs		INTEGER ::= 4
maxReportedEUTRAFreqs-ext	INTEGER ::= 8
maxReportedGSMCells			INTEGER ::= 8
maxRetrievConfig			INTEGER ::= 8
maxRetrievConfig-1			INTEGER ::= 7
maxRL						INTEGER ::= 8
maxRL-1						INTEGER ::= 7
maxRLCPDUsizePerLogChan		INTEGER ::= 32
maxRMPfrequencies			INTEGER ::= 8
maxRFC3095-CID				INTEGER ::= 16384
maxROHC-PacketSizes-r4		INTEGER ::= 16
maxROHC-Profile-r4			INTEGER ::= 8
maxRxPatternForHSDSCH-TDD128	INTEGER ::= 4 -- maxRxPatternForHSDSCH-TDD128	should be 3
maxRxPatternForHSDSCH-TDD128-1	INTEGER ::= 3 -- maxRxPatternForHSDSCH-TDD128-1 should be 2
maxSat						INTEGER ::= 16
maxSatClockModels			INTEGER ::= 4
maxSCCPCH					INTEGER ::= 16
maxSgnType					INTEGER ::= 8
maxSIB						INTEGER ::= 32
maxSIB2						INTEGER ::= 64
maxSIB-FACH					INTEGER ::= 8
maxSIBperMsg				INTEGER ::= 16
maxSIrequest				INTEGER ::= 4
maxSRBsetup					INTEGER ::= 8
maxSystemCapability			INTEGER ::= 16
maxTDD128Carrier			INTEGER ::= 6
maxTDD128Carrier-1			INTEGER ::= 5
maxTbsForHSDSCH-TDD128		INTEGER ::= 4
maxTbsForHSDSCH-TDD128-1	INTEGER ::= 3
maxTF						INTEGER ::= 32
maxTF-CPCH					INTEGER ::= 16
maxTFC						INTEGER ::= 1024
maxTFCsub					INTEGER ::= 1024
maxTFCI-2-Combs	 			INTEGER ::= 512
maxTGPS						INTEGER ::= 6
maxTrCH						INTEGER ::= 32
maxTrCHConcat				INTEGER ::= 3
-- maxTrCHpreconf should be 16 but has been set to 32 for compatibility
maxTrCHpreconf				INTEGER ::= 32
maxTS						INTEGER ::= 14
maxTS-1						INTEGER ::= 13
maxTS-2						INTEGER ::= 12
maxTS-LCR					INTEGER ::= 6
maxTS-LCR-1					INTEGER ::= 5
maxURA						INTEGER ::= 8
maxURNTI-Group				INTEGER ::= 8
maxWLANID					INTEGER ::= 16
maxWLANs					INTEGER ::= 64

END

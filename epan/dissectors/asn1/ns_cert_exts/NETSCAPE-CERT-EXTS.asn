-- NetScape Certificate Extensions
-- based on information from http://wp.netscape.com/eng/security/cert-exts.html

NS-CERT-EXTS { 2 16 840 1 113730 1 } DEFINITIONS EXPLICIT TAGS ::=
BEGIN

BaseUrl ::= IA5String

RevocationUrl ::= IA5String

CaRevocationUrl ::= IA5String

CaPolicyUrl ::= IA5String

Comment ::= IA5String

SslServerName ::= IA5String

CertRenewalUrl ::= IA5String

CertType ::= BIT STRING {
	ssl-client(0),
	ssl-server(1),
	smime(2),
	object-signing(3),
	reserved-for-future-use(4),
	ssl-ca(5),
	smime-ca(6),
	object-signing-ca(7)
}

END -- of NS-CERT-EXTS

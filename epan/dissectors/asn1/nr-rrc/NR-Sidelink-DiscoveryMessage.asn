-- 3GPP TS 38.331 V19.4.0 (2026-09)

NR-Sidelink-DiscoveryMessage DEFINITIONS AUTOMATIC TAGS ::=

BEGIN
IMPORTS
    CellAccessRelatedInfo,
    SL-ServingCellInfo-r17,
    SL-RelayIndicationMP-r18
FROM NR-RRC-Definitions;

SL-AccessInfo-L2U2N-r17 ::=             SEQUENCE {
    cellAccessRelatedInfo-r17               CellAccessRelatedInfo,
    sl-ServingCellInfo-r17                  SL-ServingCellInfo-r17,
    ...,
    [[
    sl-RelayIndication-r18                  SL-RelayIndicationMP-r18                  OPTIONAL
    ]],
    [[
    relayUE-RRC-State-r19                   SL-RelayUE-RRC-State-r19                  OPTIONAL
    ]]
}

-- TAG-SL-ACCESSINFO-L2U2N-STOP
-- TAG-SLRELAYUERRCSTATE-START

SL-RelayUE-RRC-State-r19 ::=   ENUMERATED {rrc-Connected, spare1}

END

-- ASN1START
-- **************************************************************
--
-- PDU definitions for E2AP
-- Derived from 3GPP 38.413 (NGAP)
--
-- **************************************************************

E2AP-PDU-Contents {
iso(1) identified-organization(3) dod(6) internet(1) private(4) enterprise(1) 53148 e2(1) version2 (2) e2ap(1) e2ap-PDU-Contents (1) }

DEFINITIONS AUTOMATIC TAGS ::=

BEGIN

-- **************************************************************
--
-- IE parameter types from other modules.
--
-- **************************************************************

IMPORTS
        Cause,
        CriticalityDiagnostics,
        E2nodeComponentConfiguration,
        E2nodeComponentConfigurationAck,
        E2nodeComponentID,
        E2nodeComponentInterfaceType,
        GlobalE2node-ID,
        GlobalRIC-ID,
        RANfunctionDefinition,
        RANfunctionID,
        RANfunctionOID,
        RANfunctionRevision,
        RICactionDefinition,
        RICactionExecutionOrder,
        RICactionID,
        RICactionType,
        RICcallProcessID,
        RICcontrolAckRequest,
        RICcontrolHeader,
        RICcontrolMessage,
        RICcontrolOutcome,
        RICeventTriggerDefinition,
        RICindicationHeader,
        RICindicationMessage,
        RICindicationSN,
        RICindicationType,
        RICrequestID,
        RICsubsequentAction,
        RICsubscriptionTime,
        RICqueryHeader,
        RICqueryDefinition,
        RICqueryOutcome,
        TimeToWait,
        TNLinformation,
        TNLusage,
        TransactionID
FROM E2AP-IEs

        ProtocolIE-Container{},
        ProtocolIE-ContainerList{},
        ProtocolIE-SingleContainer{},
        E2AP-PROTOCOL-IES,
        E2AP-PROTOCOL-IES-PAIR
FROM E2AP-Containers

        id-Cause,
        id-CriticalityDiagnostics,
        id-E2connectionSetup,
        id-E2connectionSetupFailed,
        id-E2connectionSetupFailed-Item,
        id-E2connectionFailed-Item,
        id-E2connectionUpdate-Item,
        id-E2connectionUpdateAdd,
        id-E2connectionUpdateModify,
        id-E2connectionUpdateRemove,
        id-E2connectionUpdateRemove-Item,
        id-E2nodeComponentConfigAddition,
        id-E2nodeComponentConfigAddition-Item,
        id-E2nodeComponentConfigAdditionAck,
        id-E2nodeComponentConfigAdditionAck-Item,
        id-E2nodeComponentConfigRemoval,
        id-E2nodeComponentConfigRemoval-Item,
        id-E2nodeComponentConfigRemovalAck,
        id-E2nodeComponentConfigRemovalAck-Item,
        id-E2nodeComponentConfigUpdate,
        id-E2nodeComponentConfigUpdate-Item,
        id-E2nodeComponentConfigUpdateAck,
        id-E2nodeComponentConfigUpdateAck-Item,
        id-E2nodeTNLassociationRemoval,
        id-E2nodeTNLassociationRemoval-Item,
        id-GlobalE2node-ID,
        id-GlobalRIC-ID,
        id-RANfunctionID,
        id-RANfunctionID-Item,
        id-RANfunctionIEcause-Item,
        id-RANfunction-Item,
        id-RANfunctionsAccepted,
        id-RANfunctionsAdded,
        id-RANfunctionsDeleted,
        id-RANfunctionsModified,
        id-RANfunctionsRejected,
        id-RICaction-Admitted-Item,
        id-RICactionID,
        id-RICaction-NotAdmitted-Item,
        id-RICactions-Admitted,
        id-RICactions-NotAdmitted,
        id-RICaction-ToBeSetup-Item,
        id-RICactionsToBeRemovedForModification-List,
        id-RICaction-ToBeRemovedForModification-Item,
        id-RICactionsToBeModifiedForModification-List,
        id-RICaction-ToBeModifiedForModification-Item,
        id-RICactionsToBeAddedForModification-List,
        id-RICaction-ToBeAddedForModification-Item,
        id-RICactionsRemovedForModification-List,
        id-RICaction-RemovedForModification-Item,
        id-RICactionsFailedToBeRemovedForModification-List,
        id-RICaction-FailedToBeRemovedForModification-Item,
        id-RICactionsModifiedForModification-List,
        id-RICaction-ModifiedForModification-Item,
        id-RICactionsFailedToBeModifiedForModification-List,
        id-RICaction-FailedToBeModifiedForModification-Item,
        id-RICactionsAddedForModification-List,
        id-RICaction-AddedForModification-Item,
        id-RICactionsFailedToBeAddedForModification-List,
        id-RICaction-FailedToBeAddedForModification-Item,
        id-RICactionsRequiredToBeModified-List,
        id-RICaction-RequiredToBeModified-Item,
        id-RICactionsRequiredToBeRemoved-List,
        id-RICaction-RequiredToBeRemoved-Item,
        id-RICactionsConfirmedForModification-List,
        id-RICaction-ConfirmedForModification-Item,
        id-RICactionsRefusedToBeModified-List,
        id-RICaction-RefusedToBeModified-Item,
        id-RICactionsConfirmedForRemoval-List,
        id-RICaction-ConfirmedForRemoval-Item,
        id-RICactionsRefusedToBeRemoved-List,
        id-RICaction-RefusedToBeRemoved-Item,
        id-RICcallProcessID,
        id-RICcontrolAckRequest,
        id-RICcontrolHeader,
        id-RICcontrolMessage,
        id-RICcontrolOutcome,
        id-RICeventTriggerDefinitionToBeModified,
        id-RICindicationHeader,
        id-RICindicationMessage,
        id-RICindicationSN,
        id-RICindicationType,
        id-RICrequestID,
        id-RICserviceQuery,
        id-RICsubscriptionDetails,
        id-RICsubscriptionToBeRemoved,
        id-RICsubscription-withCause-Item,
        id-RICsubscriptionStartTime,
        id-RICsubscriptionEndTime,
        id-RICqueryHeader,
        id-RICqueryDefinition,
        id-RICqueryOutcome,
        id-TimeToWait,
        id-TNLinformation,
        id-TransactionID,

        maxofE2nodeComponents,
        maxofRANfunctionID,
        maxofRICactionID,
        maxofRICrequestID,
        maxofTNLA
FROM E2AP-Constants;


-- **************************************************************
--
-- MESSAGES FOR RIC FUNCTIONAL PROCEDURES
--
-- **************************************************************

-- **************************************************************
--
-- RIC Subscription Elementary Procedure
--
-- **************************************************************
-- **************************************************************
--
-- RIC SUBSCRIPTION REQUEST
--
-- **************************************************************
RICsubscriptionRequest ::= SEQUENCE {
        protocolIEs					ProtocolIE-Container	{{RICsubscriptionRequest-IEs}},
        ...
}

RICsubscriptionRequest-IEs E2AP-PROTOCOL-IES ::= {
        { ID id-RICrequestID				CRITICALITY reject	TYPE RICrequestID					PRESENCE mandatory}|
        { ID id-RANfunctionID				CRITICALITY reject	TYPE RANfunctionID					PRESENCE mandatory}|
        { ID id-RICsubscriptionDetails		CRITICALITY reject	TYPE RICsubscriptionDetails			PRESENCE mandatory},
        ...,
        { ID id-RICsubscriptionStartTime	CRITICALITY reject	TYPE RICsubscriptionTime			PRESENCE optional}|
        { ID id-RICsubscriptionEndTime		CRITICALITY reject	TYPE RICsubscriptionTime			PRESENCE optional}
}


RICsubscriptionDetails ::= SEQUENCE {
        ricEventTriggerDefinition	RICeventTriggerDefinition,
        ricAction-ToBeSetup-List	RICactions-ToBeSetup-List,
        ...
}

RICactions-ToBeSetup-List ::= SEQUENCE (SIZE(1..maxofRICactionID)) OF ProtocolIE-SingleContainer { {RICaction-ToBeSetup-ItemIEs} }

RICaction-ToBeSetup-ItemIEs 	E2AP-PROTOCOL-IES ::= {
        { ID id-RICaction-ToBeSetup-Item	CRITICALITY ignore 	TYPE RICaction-ToBeSetup-Item 	PRESENCE mandatory },
        ...
}

RICaction-ToBeSetup-Item ::= SEQUENCE {
        ricActionID					RICactionID,
        ricActionType				RICactionType,
        ricActionDefinition			RICactionDefinition 	OPTIONAL,
        ricSubsequentAction			RICsubsequentAction 	OPTIONAL,
        ...,
        ricActionExecutionOrder		RICactionExecutionOrder	OPTIONAL		-- New in E2APv03.00

}

-- **************************************************************
--
-- RIC SUBSCRIPTION RESPONSE
--
-- **************************************************************
RICsubscriptionResponse ::= SEQUENCE {
        protocolIEs					ProtocolIE-Container{{RICsubscriptionResponse-IEs}},
        ...
}

RICsubscriptionResponse-IEs E2AP-PROTOCOL-IES ::= {
        { ID id-RICrequestID				CRITICALITY reject		TYPE RICrequestID				PRESENCE mandatory } |
        { ID id-RANfunctionID				CRITICALITY reject		TYPE RANfunctionID				PRESENCE mandatory } |
        { ID id-RICactions-Admitted			CRITICALITY reject		TYPE RICaction-Admitted-List	PRESENCE mandatory } |
        { ID id-RICactions-NotAdmitted		CRITICALITY reject		TYPE RICaction-NotAdmitted-List	PRESENCE optional },
        ...
}



RICaction-Admitted-List ::= SEQUENCE (SIZE(1..maxofRICactionID)) OF ProtocolIE-SingleContainer{{RICaction-Admitted-ItemIEs}}

RICaction-Admitted-ItemIEs E2AP-PROTOCOL-IES ::= {
        { ID id-RICaction-Admitted-Item		CRITICALITY ignore		TYPE RICaction-Admitted-Item	PRESENCE mandatory },
        ...
}

RICaction-Admitted-Item ::= SEQUENCE {
        ricActionID					RICactionID,
        ...
}

RICaction-NotAdmitted-List ::= SEQUENCE (SIZE(0..maxofRICactionID)) OF ProtocolIE-SingleContainer { {RICaction-NotAdmitted-ItemIEs} }

RICaction-NotAdmitted-ItemIEs E2AP-PROTOCOL-IES ::= {
        { ID id-RICaction-NotAdmitted-Item	CRITICALITY ignore	TYPE RICaction-NotAdmitted-Item		PRESENCE mandatory },
        ...
}

RICaction-NotAdmitted-Item ::= SEQUENCE {
        ricActionID					RICactionID,
        cause						Cause,
        ...
}

-- **************************************************************
--
-- RIC SUBSCRIPTION FAILURE
--
-- **************************************************************
RICsubscriptionFailure ::= SEQUENCE {
        protocolIEs					ProtocolIE-Container	{{RICsubscriptionFailure-IEs}},
        ...
}

RICsubscriptionFailure-IEs E2AP-PROTOCOL-IES ::= {
        { ID id-RICrequestID				CRITICALITY reject	TYPE RICrequestID					PRESENCE mandatory	}|
        { ID id-RANfunctionID				CRITICALITY reject	TYPE RANfunctionID					PRESENCE mandatory	}|
        { ID id-Cause						CRITICALITY reject	TYPE Cause		PRESENCE mandatory	}|
        { ID id-CriticalityDiagnostics		CRITICALITY ignore	TYPE CriticalityDiagnostics			PRESENCE optional	},
        ...
}

-- **************************************************************
--
-- RIC Subscription Delete Elementary Procedure
--
-- **************************************************************
-- **************************************************************
--
-- RIC SUBSCRIPTION DELETE REQUEST
--
-- **************************************************************
RICsubscriptionDeleteRequest ::= SEQUENCE {
        protocolIEs					ProtocolIE-Container	{{RICsubscriptionDeleteRequest-IEs}},
        ...
}

RICsubscriptionDeleteRequest-IEs E2AP-PROTOCOL-IES ::= {
        { ID id-RICrequestID				CRITICALITY reject	TYPE RICrequestID					PRESENCE mandatory	}|
        { ID id-RANfunctionID				CRITICALITY reject	TYPE RANfunctionID					PRESENCE mandatory	},
        ...
}

-- **************************************************************
--
-- RIC SUBSCRIPTION DELETE RESPONSE
--
-- **************************************************************
RICsubscriptionDeleteResponse ::= SEQUENCE {
        protocolIEs					ProtocolIE-Container	{{RICsubscriptionDeleteResponse-IEs}},
        ...
}

RICsubscriptionDeleteResponse-IEs E2AP-PROTOCOL-IES ::= {
        { ID id-RICrequestID				CRITICALITY reject	TYPE RICrequestID					PRESENCE mandatory	}|
        { ID id-RANfunctionID				CRITICALITY reject	TYPE RANfunctionID					PRESENCE mandatory	},
        ...
}
-- **************************************************************
--
-- RIC SUBSCRIPTION DELETE FAILURE
--
-- **************************************************************
RICsubscriptionDeleteFailure ::= SEQUENCE {
        protocolIEs					ProtocolIE-Container	{{RICsubscriptionDeleteFailure-IEs}},
        ...
}

RICsubscriptionDeleteFailure-IEs E2AP-PROTOCOL-IES ::= {
        { ID id-RICrequestID				CRITICALITY reject	TYPE RICrequestID					PRESENCE mandatory	}|
        { ID id-RANfunctionID				CRITICALITY reject	TYPE RANfunctionID					PRESENCE mandatory	}|
        { ID id-Cause						CRITICALITY ignore	TYPE Cause							PRESENCE mandatory	}|
        { ID id-CriticalityDiagnostics		CRITICALITY ignore	TYPE CriticalityDiagnostics			PRESENCE optional	},
        ...
}

-- **************************************************************
--
-- RIC Subscription Delete Required Elementary Procedure
--
-- **************************************************************
-- **************************************************************
--
-- RIC SUBSCRIPTION DELETE REQUIRED
--
-- **************************************************************

RICsubscriptionDeleteRequired ::= SEQUENCE {
        protocolIEs					ProtocolIE-Container	{{RICsubscriptionDeleteRequired-IEs}},
        ...
}

RICsubscriptionDeleteRequired-IEs E2AP-PROTOCOL-IES ::= {
        { ID id-RICsubscriptionToBeRemoved		CRITICALITY ignore	TYPE RICsubscription-List-withCause	PRESENCE mandatory	},
        ...
}

RICsubscription-List-withCause ::= SEQUENCE (SIZE(1..maxofRICrequestID)) OF ProtocolIE-SingleContainer { {RICsubscription-withCause-ItemIEs} }

RICsubscription-withCause-ItemIEs	E2AP-PROTOCOL-IES ::= {
        { ID id-RICsubscription-withCause-Item	CRITICALITY ignore 	TYPE RICsubscription-withCause-Item 	PRESENCE mandatory	},
        ...
}

RICsubscription-withCause-Item ::= SEQUENCE {
        ricRequestID				RICrequestID,
        ranFunctionID				RANfunctionID,
        cause						Cause,
        ...
}

-- **************************************************************
--
-- RIC Subscription Modification Elementary Procedure
--
-- **************************************************************
-- **************************************************************
--
-- RIC SUBSCRIPTION MODIFICATION REQUEST
--
-- **************************************************************
RICsubscriptionModificationRequest ::= SEQUENCE {
        protocolIEs					ProtocolIE-Container	{{RICsubscriptionModificationRequest-IEs}},
        ...
}

RICsubscriptionModificationRequest-IEs E2AP-PROTOCOL-IES ::= {
        { ID id-RICrequestID								CRITICALITY reject	TYPE RICrequestID					PRESENCE mandatory}|
        { ID id-RANfunctionID								CRITICALITY reject	TYPE RANfunctionID					PRESENCE mandatory}|
        { ID id-RICeventTriggerDefinitionToBeModified		CRITICALITY ignore	TYPE RICeventTriggerDefinition	PRESENCE optional}|
        { ID id-RICactionsToBeRemovedForModification-List	CRITICALITY ignore	TYPE RICactions-ToBeRemovedForModification-List	PRESENCE optional}|
        { ID id-RICactionsToBeModifiedForModification-List	CRITICALITY ignore	TYPE RICactions-ToBeModifiedForModification-List	PRESENCE optional}|
        { ID id-RICactionsToBeAddedForModification-List		CRITICALITY ignore	TYPE RICactions-ToBeAddedForModification-List		PRESENCE optional},
        ...
}

RICactions-ToBeRemovedForModification-List ::= SEQUENCE (SIZE(0..maxofRICactionID)) OF ProtocolIE-SingleContainer {{RICaction-ToBeRemovedForModification-ItemIEs}	}

RICaction-ToBeRemovedForModification-ItemIEs 	E2AP-PROTOCOL-IES ::= {
        { ID id-RICaction-ToBeRemovedForModification-Item	CRITICALITY ignore 	TYPE RICaction-ToBeRemovedForModification-Item 	PRESENCE mandatory },
        ...
}

RICaction-ToBeRemovedForModification-Item ::= SEQUENCE {
        ricActionID					RICactionID,
        ...
}

RICactions-ToBeModifiedForModification-List ::= SEQUENCE (SIZE(0..maxofRICactionID)) OF ProtocolIE-SingleContainer {{RICaction-ToBeModifiedForModification-ItemIEs} }

RICaction-ToBeModifiedForModification-ItemIEs 	E2AP-PROTOCOL-IES ::= {
        { ID id-RICaction-ToBeModifiedForModification-Item	CRITICALITY ignore 	TYPE RICaction-ToBeModifiedForModification-Item 	PRESENCE mandatory },
        ...
}

RICaction-ToBeModifiedForModification-Item ::= SEQUENCE {
        ricActionID					RICactionID,
        ricActionDefinition			RICactionDefinition		OPTIONAL,
        ricActionExecutionOrder		RICactionExecutionOrder	OPTIONAL,
        ricSubsequentAction			RICsubsequentAction		OPTIONAL,
        ...
}


RICactions-ToBeAddedForModification-List ::= SEQUENCE (SIZE(0..maxofRICactionID)) OF ProtocolIE-SingleContainer {{RICaction-ToBeAddedForModification-ItemIEs} }

RICaction-ToBeAddedForModification-ItemIEs 	E2AP-PROTOCOL-IES ::= {
        { ID id-RICaction-ToBeAddedForModification-Item	CRITICALITY ignore 	TYPE RICaction-ToBeAddedForModification-Item 	PRESENCE mandatory },
        ...
}

RICaction-ToBeAddedForModification-Item ::= SEQUENCE {
        ricActionID					RICactionID,
        ricActionType				RICactionType,
        ricActionDefinition			RICactionDefinition,
        ricActionExecutionOrder		RICactionExecutionOrder,
        ricSubsequentAction			RICsubsequentAction		OPTIONAL,
        ...
}
-- **************************************************************
--
-- RIC SUBSCRIPTION MODIFICATION RESPONSE
--
-- **************************************************************
RICsubscriptionModificationResponse ::= SEQUENCE {
        protocolIEs					ProtocolIE-Container	{{RICsubscriptionModificationResponse-IEs}},
        ...
}

RICsubscriptionModificationResponse-IEs E2AP-PROTOCOL-IES ::= {
        { ID id-RICrequestID										CRITICALITY reject	TYPE RICrequestID					PRESENCE mandatory}|
        { ID id-RANfunctionID										CRITICALITY reject	TYPE RANfunctionID					PRESENCE mandatory}|
        { ID id-RICactionsRemovedForModification-List				CRITICALITY ignore	TYPE RICactions-RemovedForModification-List	PRESENCE optional}|
        { ID id-RICactionsFailedToBeRemovedForModification-List		CRITICALITY ignore	TYPE RICactions-FailedToBeRemovedForModification-List	PRESENCE optional}|
        { ID id-RICactionsModifiedForModification-List				CRITICALITY ignore	TYPE RICactions-ModifiedForModification-List	PRESENCE optional}|
        { ID id-RICactionsFailedToBeModifiedForModification-List	CRITICALITY ignore	TYPE RICactions-FailedToBeModifiedForModification-List	PRESENCE optional}|
        { ID id-RICactionsAddedForModification-List					CRITICALITY ignore	TYPE RICactions-AddedForModification-List	PRESENCE optional}|
        { ID id-RICactionsFailedToBeAddedForModification-List		CRITICALITY ignore	TYPE RICactions-FailedToBeAddedForModification-List		PRESENCE optional},
        ...
}

RICactions-RemovedForModification-List ::= SEQUENCE (SIZE(0..maxofRICactionID)) OF ProtocolIE-SingleContainer {{RICaction-RemovedForModification-ItemIEs} }

RICaction-RemovedForModification-ItemIEs 	E2AP-PROTOCOL-IES ::= {
        { ID id-RICaction-RemovedForModification-Item	CRITICALITY ignore 	TYPE RICaction-RemovedForModification-Item 	PRESENCE mandatory },
        ...
}

RICaction-RemovedForModification-Item ::=	SEQUENCE {
        ricActionID					RICactionID,
        ...
}
RICactions-FailedToBeRemovedForModification-List ::= SEQUENCE (SIZE(0..maxofRICactionID)) OF ProtocolIE-SingleContainer {{RICaction-FailedToBeRemovedForModification-ItemIEs} }

RICaction-FailedToBeRemovedForModification-ItemIEs 	E2AP-PROTOCOL-IES ::= {
        { ID id-RICaction-FailedToBeRemovedForModification-Item	CRITICALITY ignore 	TYPE RICaction-FailedToBeRemovedForModification-Item 	PRESENCE mandatory },
        ...
}

RICaction-FailedToBeRemovedForModification-Item ::=	SEQUENCE {
        ricActionID					RICactionID,
        cause						Cause,
        ...
}

RICactions-ModifiedForModification-List ::= SEQUENCE (SIZE(0..maxofRICactionID)) OF ProtocolIE-SingleContainer {{RICaction-ModifiedForModification-ItemIEs} }

RICaction-ModifiedForModification-ItemIEs 	E2AP-PROTOCOL-IES ::= {
        { ID id-RICaction-ModifiedForModification-Item	CRITICALITY ignore 	TYPE RICaction-ModifiedForModification-Item 	PRESENCE mandatory },
        ...
}

RICaction-ModifiedForModification-Item ::=	SEQUENCE {
        ricActionID					RICactionID,
        ...
}

RICactions-FailedToBeModifiedForModification-List ::= SEQUENCE (SIZE(0..maxofRICactionID)) OF ProtocolIE-SingleContainer {{RICaction-FailedToBeModifiedForModification-ItemIEs} }

RICaction-FailedToBeModifiedForModification-ItemIEs 	E2AP-PROTOCOL-IES ::= {
        { ID id-RICaction-FailedToBeModifiedForModification-Item	CRITICALITY ignore 	TYPE RICaction-FailedToBeModifiedForModification-Item 	PRESENCE mandatory },
        ...
}

RICaction-FailedToBeModifiedForModification-Item ::=	SEQUENCE {
        ricActionID					RICactionID,
        cause						Cause,
        ...
}

RICactions-AddedForModification-List ::= SEQUENCE (SIZE(0..maxofRICactionID)) OF ProtocolIE-SingleContainer {{RICaction-AddedForModification-ItemIEs} }

RICaction-AddedForModification-ItemIEs 	E2AP-PROTOCOL-IES ::= {
        { ID id-RICaction-AddedForModification-Item	CRITICALITY ignore 	TYPE RICaction-AddedForModification-Item 	PRESENCE mandatory },
        ...
}

RICaction-AddedForModification-Item ::=	SEQUENCE {
        ricActionID					RICactionID,
        ...
}

RICactions-FailedToBeAddedForModification-List ::= SEQUENCE (SIZE(0..maxofRICactionID)) OF ProtocolIE-SingleContainer {{RICaction-FailedToBeAddedForModification-ItemIEs} }

RICaction-FailedToBeAddedForModification-ItemIEs 	E2AP-PROTOCOL-IES ::= {
        { ID id-RICaction-FailedToBeAddedForModification-Item	CRITICALITY ignore 	TYPE RICaction-FailedToBeAddedForModification-Item 	PRESENCE mandatory },
        ...
}

RICaction-FailedToBeAddedForModification-Item ::=	SEQUENCE {
        ricActionID					RICactionID,
        cause						Cause,
        ...
}

-- **************************************************************
--
-- RIC SUBSCRIPTION MODIFICATION FAILURE
--
-- **************************************************************
RICsubscriptionModificationFailure ::= SEQUENCE {
        protocolIEs					ProtocolIE-Container	{{RICsubscriptionModificationFailure-IEs}},
        ...
}

RICsubscriptionModificationFailure-IEs E2AP-PROTOCOL-IES ::= {
        { ID id-RICrequestID				CRITICALITY reject	TYPE RICrequestID					PRESENCE mandatory}|
        { ID id-RANfunctionID				CRITICALITY reject	TYPE RANfunctionID					PRESENCE mandatory}|
        { ID id-Cause						CRITICALITY reject	TYPE Cause		PRESENCE mandatory}|
        { ID id-CriticalityDiagnostics		CRITICALITY ignore	TYPE CriticalityDiagnostics			PRESENCE optional},
        ...
}

-- **************************************************************
--
-- RIC Subscription Modification Required Elementary Procedure
--
-- **************************************************************
-- **************************************************************
--
-- RIC SUBSCRIPTION MODIFICATION REQUIRED
--
-- **************************************************************
RICsubscriptionModificationRequired ::= SEQUENCE {
        protocolIEs					ProtocolIE-Container	{{RICsubscriptionModificationRequired-IEs}},
        ...
}

RICsubscriptionModificationRequired-IEs E2AP-PROTOCOL-IES ::= {
        { ID id-RICrequestID						CRITICALITY reject	TYPE RICrequestID					PRESENCE mandatory}|
        { ID id-RANfunctionID						CRITICALITY reject	TYPE RANfunctionID					PRESENCE mandatory}|
        { ID id-RICactionsRequiredToBeModified-List	CRITICALITY ignore	TYPE RICactions-RequiredToBeModified-List	PRESENCE optional}|
        { ID id-RICactionsRequiredToBeRemoved-List	CRITICALITY ignore	TYPE RICactions-RequiredToBeRemoved-List	PRESENCE optional},
        ...
}

RICactions-RequiredToBeModified-List ::= SEQUENCE (SIZE(0..maxofRICactionID)) OF ProtocolIE-SingleContainer {{RICaction-RequiredToBeModified-ItemIEs} }

RICaction-RequiredToBeModified-ItemIEs 	E2AP-PROTOCOL-IES ::= {
        { ID id-RICaction-RequiredToBeModified-Item	CRITICALITY ignore 	TYPE RICaction-RequiredToBeModified-Item 	PRESENCE mandatory },
        ...
}

RICaction-RequiredToBeModified-Item ::=	SEQUENCE {
        ricActionID				RICactionID,
        ricTimeToWait			RICtimeToWait,
        ...
}

RICactions-RequiredToBeRemoved-List ::= SEQUENCE (SIZE(0..maxofRICactionID)) OF ProtocolIE-SingleContainer {{RICaction-RequiredToBeRemoved-ItemIEs} }

RICaction-RequiredToBeRemoved-ItemIEs 	E2AP-PROTOCOL-IES ::= {
        { ID id-RICaction-RequiredToBeRemoved-Item	CRITICALITY ignore 	TYPE RICaction-RequiredToBeRemoved-Item 	PRESENCE mandatory },
        ...
}

RICaction-RequiredToBeRemoved-Item ::=	SEQUENCE {
        ricActionID				RICactionID,
        cause					Cause,
        ...
}

-- **************************************************************
--
-- RIC SUBSCRIPTION MODIFICATION CONFIRM
--
-- **************************************************************
RICsubscriptionModificationConfirm ::= SEQUENCE {
        protocolIEs					ProtocolIE-Container	{{RICsubscriptionModificationConfirm-IEs}},
        ...
}

RICsubscriptionModificationConfirm-IEs E2AP-PROTOCOL-IES ::= {
        { ID id-RICrequestID							CRITICALITY reject	TYPE RICrequestID					PRESENCE mandatory}|
        { ID id-RANfunctionID							CRITICALITY reject	TYPE RANfunctionID					PRESENCE mandatory}|
        { ID id-RICactionsConfirmedForModification-List	CRITICALITY ignore	TYPE RICactions-ConfirmedForModification-List	PRESENCE optional}|
        { ID id-RICactionsRefusedToBeModified-List		CRITICALITY ignore	TYPE RICactions-RefusedToBeModified-List	PRESENCE optional}|
        { ID id-RICactionsConfirmedForRemoval-List		CRITICALITY ignore	TYPE RICactions-ConfirmedForRemoval-List	PRESENCE optional}|
        { ID id-RICactionsRefusedToBeRemoved-List		CRITICALITY ignore	TYPE RICactions-RefusedToBeRemoved-List		PRESENCE optional},
        ...
}

RICactions-ConfirmedForModification-List ::= SEQUENCE (SIZE(0..maxofRICactionID)) OF ProtocolIE-SingleContainer {{RICaction-ConfirmedForModification-ItemIEs} }

RICaction-ConfirmedForModification-ItemIEs 	E2AP-PROTOCOL-IES ::= {
        { ID id-RICaction-ConfirmedForModification-Item			CRITICALITY ignore 	TYPE RICaction-ConfirmedForModification-Item 	PRESENCE mandatory },
        ...
}

RICaction-ConfirmedForModification-Item ::=	SEQUENCE {
        ricActionID					RICactionID,
        ...
}
RICactions-RefusedToBeModified-List ::= SEQUENCE (SIZE(0..maxofRICactionID)) OF ProtocolIE-SingleContainer {{RICaction-RefusedToBeModified-ItemIEs} }

RICaction-RefusedToBeModified-ItemIEs 	E2AP-PROTOCOL-IES ::= {
        { ID id-RICaction-RefusedToBeModified-Item			CRITICALITY ignore 	TYPE RICaction-RefusedToBeModified-Item 	PRESENCE mandatory },
        ...
}

RICaction-RefusedToBeModified-Item ::=	SEQUENCE {
        ricActionID					RICactionID,
        cause						Cause,
        ...
}

RICactions-ConfirmedForRemoval-List ::= SEQUENCE (SIZE(0..maxofRICactionID)) OF ProtocolIE-SingleContainer {{RICaction-ConfirmedForRemoval-ItemIEs} }

RICaction-ConfirmedForRemoval-ItemIEs 	E2AP-PROTOCOL-IES ::= {
        { ID id-RICaction-ConfirmedForRemoval-Item			CRITICALITY ignore 	TYPE RICaction-ConfirmedForRemoval-Item 	PRESENCE mandatory },
        ...
}

RICaction-ConfirmedForRemoval-Item ::=	SEQUENCE {
        ricActionID					RICactionID,
        ...
}

RICactions-RefusedToBeRemoved-List ::= SEQUENCE (SIZE(0..maxofRICactionID)) OF ProtocolIE-SingleContainer {{RICaction-RefusedToBeRemoved-ItemIEs} }

RICaction-RefusedToBeRemoved-ItemIEs 	E2AP-PROTOCOL-IES ::= {
        { ID id-RICaction-RefusedToBeRemoved-Item			CRITICALITY ignore 	TYPE RICaction-RefusedToBeRemoved-Item 	PRESENCE mandatory },
        ...
}

RICaction-RefusedToBeRemoved-Item ::=	SEQUENCE {
        ricActionID					RICactionID,
        cause						Cause,
        ...
}

-- **************************************************************
--
-- RIC SUBSCRIPTION MODIFICATION REFUSE
--
-- **************************************************************
RICsubscriptionModificationRefuse ::= SEQUENCE {
        protocolIEs					ProtocolIE-Container	{{RICsubscriptionModificationRefuse-IEs}},
        ...
}


RICsubscriptionModificationRefuse-IEs E2AP-PROTOCOL-IES ::= {
        { ID id-RICrequestID				CRITICALITY reject	TYPE RICrequestID					PRESENCE mandatory}|
        { ID id-RANfunctionID				CRITICALITY reject	TYPE RANfunctionID					PRESENCE mandatory}|
        { ID id-Cause						CRITICALITY reject	TYPE Cause		PRESENCE mandatory}|
        { ID id-CriticalityDiagnostics		CRITICALITY ignore	TYPE CriticalityDiagnostics			PRESENCE optional},
        ...
}


-- **************************************************************
--
-- RIC Indication Elementary Procedure
--
-- **************************************************************
-- **************************************************************
--
-- RIC INDICATION
--
-- **************************************************************
RICindication ::= SEQUENCE {
        protocolIEs					ProtocolIE-Container	{{RICindication-IEs}},
        ...
}

RICindication-IEs E2AP-PROTOCOL-IES ::= {
        { ID id-RICrequestID				CRITICALITY reject	TYPE RICrequestID					PRESENCE mandatory	}|
        { ID id-RANfunctionID				CRITICALITY reject	TYPE RANfunctionID					PRESENCE mandatory	}|
        { ID id-RICactionID					CRITICALITY reject	TYPE RICactionID					PRESENCE mandatory	}|
        { ID id-RICindicationSN				CRITICALITY reject	TYPE RICindicationSN				PRESENCE optional	}|
        { ID id-RICindicationType			CRITICALITY reject	TYPE RICindicationType				PRESENCE mandatory	}|
        { ID id-RICindicationHeader			CRITICALITY reject	TYPE RICindicationHeader			PRESENCE mandatory	}|
        { ID id-RICindicationMessage		CRITICALITY reject	TYPE RICindicationMessage			PRESENCE mandatory	}|
        { ID id-RICcallProcessID			CRITICALITY reject	TYPE RICcallProcessID				PRESENCE optional	},
        ...
}

-- **************************************************************
--
-- RIC Control Elementary Procedure
--
-- **************************************************************
-- **************************************************************
--
-- RIC CONTROL REQUEST
--
-- **************************************************************
RICcontrolRequest ::= SEQUENCE {
        protocolIEs					ProtocolIE-Container	{{RICcontrolRequest-IEs}},
        ...
}

RICcontrolRequest-IEs E2AP-PROTOCOL-IES ::= {
        { ID id-RICrequestID				CRITICALITY reject	TYPE RICrequestID					PRESENCE mandatory	}|
        { ID id-RANfunctionID				CRITICALITY reject	TYPE RANfunctionID					PRESENCE mandatory	}|
        { ID id-RICcallProcessID			CRITICALITY reject	TYPE RICcallProcessID				PRESENCE optional	}|
        { ID id-RICcontrolHeader			CRITICALITY reject	TYPE RICcontrolHeader				PRESENCE mandatory	}|
        { ID id-RICcontrolMessage			CRITICALITY reject	TYPE RICcontrolMessage				PRESENCE mandatory	}|
        { ID id-RICcontrolAckRequest		CRITICALITY reject	TYPE RICcontrolAckRequest			PRESENCE optional	},
        ...
}
-- **************************************************************
--
-- RIC CONTROL ACKNOWLEDGE
--
-- **************************************************************
RICcontrolAcknowledge ::= SEQUENCE {
        protocolIEs					ProtocolIE-Container	{{RICcontrolAcknowledge-IEs}},
        ...
}

RICcontrolAcknowledge-IEs E2AP-PROTOCOL-IES ::= {
        { ID id-RICrequestID				CRITICALITY reject	TYPE RICrequestID					PRESENCE mandatory	}|
        { ID id-RANfunctionID				CRITICALITY reject	TYPE RANfunctionID					PRESENCE mandatory	}|
        { ID id-RICcallProcessID			CRITICALITY reject	TYPE RICcallProcessID				PRESENCE optional	}|
        { ID id-RICcontrolOutcome			CRITICALITY reject	TYPE RICcontrolOutcome				PRESENCE optional	},
        ...
}
-- **************************************************************
--
-- RIC CONTROL FAILURE
--
-- **************************************************************
RICcontrolFailure ::= SEQUENCE {
        protocolIEs					ProtocolIE-Container	{{RICcontrolFailure-IEs}},
        ...
}

RICcontrolFailure-IEs E2AP-PROTOCOL-IES ::= {
        { ID id-RICrequestID				CRITICALITY reject	TYPE RICrequestID					PRESENCE mandatory	}|
        { ID id-RANfunctionID				CRITICALITY reject	TYPE RANfunctionID					PRESENCE mandatory	}|
        { ID id-RICcallProcessID			CRITICALITY reject	TYPE RICcallProcessID				PRESENCE optional	}|
        { ID id-Cause						CRITICALITY ignore	TYPE Cause							PRESENCE mandatory	}|
        { ID id-RICcontrolOutcome			CRITICALITY reject	TYPE RICcontrolOutcome				PRESENCE optional	},
        ...,
        { ID id-CriticalityDiagnostics		CRITICALITY ignore	TYPE CriticalityDiagnostics			PRESENCE optional	}
}

-- **************************************************************
--
-- RIC QUERY Elementary Procedure
--
-- **************************************************************
-- **************************************************************
--
-- RIC QUERY REQUEST
--
-- **************************************************************
RICQueryRequest ::= SEQUENCE {
        protocolIEs					ProtocolIE-Container	{{RICQueryRequest-IEs}},
        ...
}

RICQueryRequest-IEs E2AP-PROTOCOL-IES ::= {
        { ID id-RICrequestID				CRITICALITY reject	TYPE RICrequestID					PRESENCE mandatory	}|
        { ID id-RANfunctionID				CRITICALITY reject	TYPE RANfunctionID					PRESENCE mandatory	}|
        { ID id-RICqueryHeader				CRITICALITY reject	TYPE RICqueryHeader					PRESENCE mandatory	}|
        { ID id-RICqueryDefinition			CRITICALITY reject	TYPE RICqueryDefinition					PRESENCE mandatory	},
        ...
}

-- **************************************************************
--
-- RIC QUERY RESPONSE
--
-- **************************************************************
RICQueryResponse ::= SEQUENCE {
        protocolIEs					ProtocolIE-Container	{{RICQueryResponse-IEs}},
        ...
}

RICQueryResponse-IEs E2AP-PROTOCOL-IES ::= {
        { ID id-RICrequestID				CRITICALITY reject	TYPE RICrequestID					PRESENCE mandatory	}|
        { ID id-RANfunctionID				CRITICALITY reject	TYPE RANfunctionID					PRESENCE mandatory	}|
        { ID id-RICqueryOutcome				CRITICALITY reject	TYPE RICqueryOutcome					PRESENCE mandatory	},
        ...
}
-- **************************************************************
--
-- RIC QUERY FAILURE
--
-- **************************************************************
RICQueryFailure ::= SEQUENCE {
        protocolIEs					ProtocolIE-Container	{{RICQueryFailure-IEs}},
        ...
}

RICQueryFailure-IEs E2AP-PROTOCOL-IES ::= {
        { ID id-RICrequestID				CRITICALITY reject	TYPE RICrequestID					PRESENCE mandatory	}|
        { ID id-RANfunctionID				CRITICALITY reject	TYPE RANfunctionID					PRESENCE mandatory	}|
        { ID id-Cause						CRITICALITY ignore	TYPE Cause							PRESENCE mandatory	}|
        { ID id-CriticalityDiagnostics		CRITICALITY ignore	TYPE CriticalityDiagnostics			PRESENCE optional	},
        ...
}

-- **************************************************************
--
-- MESSAGES FOR GLOBAL PROCEDURES
--
-- **************************************************************

-- **************************************************************
--
-- Error Indication Elementary Procedure
--
-- **************************************************************
-- **************************************************************
--
-- ERROR INDICATION
--
-- **************************************************************
ErrorIndication ::= SEQUENCE {
        protocolIEs					ProtocolIE-Container	{{ErrorIndication-IEs}},
        ...
}

ErrorIndication-IEs E2AP-PROTOCOL-IES ::= {
        { ID id-TransactionID				CRITICALITY reject	TYPE TransactionID				PRESENCE optional	}|
        { ID id-RICrequestID				CRITICALITY reject	TYPE RICrequestID				PRESENCE optional	}|
        { ID id-RANfunctionID				CRITICALITY reject	TYPE RANfunctionID				PRESENCE optional	}|
        { ID id-Cause						CRITICALITY ignore	TYPE Cause						PRESENCE optional	}|
        { ID id-CriticalityDiagnostics		CRITICALITY ignore	TYPE CriticalityDiagnostics		PRESENCE optional	},
        ...
}

-- **************************************************************
--
-- E2 Setup Elementary Procedure
--
-- **************************************************************
-- **************************************************************
--
-- E2 SETUP REQUEST
--
-- **************************************************************

E2setupRequest ::= SEQUENCE {
        protocolIEs		ProtocolIE-Container		{ {E2setupRequestIEs} },
        ...
}

E2setupRequestIEs E2AP-PROTOCOL-IES ::= {
        { ID id-TransactionID					CRITICALITY reject	TYPE TransactionID						PRESENCE mandatory	}|
        { ID id-GlobalE2node-ID					CRITICALITY reject	TYPE GlobalE2node-ID				PRESENCE mandatory	}|
        { ID id-RANfunctionsAdded				CRITICALITY reject	TYPE RANfunctions-List				PRESENCE mandatory	}|
        { ID id-E2nodeComponentConfigAddition	CRITICALITY reject	TYPE E2nodeComponentConfigAddition-List	PRESENCE mandatory	},
        ...
}

-- **************************************************************
--
-- E2 SETUP RESPONSE
--
-- **************************************************************

E2setupResponse ::= SEQUENCE {
        protocolIEs		ProtocolIE-Container		{ {E2setupResponseIEs} },
        ...
}

E2setupResponseIEs E2AP-PROTOCOL-IES ::= {
        { ID id-TransactionID						CRITICALITY reject	TYPE TransactionID							PRESENCE mandatory	}|
        { ID id-GlobalRIC-ID						CRITICALITY reject	TYPE GlobalRIC-ID							PRESENCE mandatory	}|
        { ID id-RANfunctionsAccepted				CRITICALITY reject	TYPE RANfunctionsID-List					PRESENCE optional	}|
        { ID id-RANfunctionsRejected				CRITICALITY reject	TYPE RANfunctionsIDcause-List				PRESENCE optional	}|
        { ID id-E2nodeComponentConfigAdditionAck	CRITICALITY reject	TYPE E2nodeComponentConfigAdditionAck-List	PRESENCE mandatory	},
        ...
}

-- **************************************************************
--
-- E2 SETUP FAILURE
--
-- **************************************************************

E2setupFailure ::= SEQUENCE {
        protocolIEs		ProtocolIE-Container		{ {E2setupFailureIEs} },
        ...
}

E2setupFailureIEs E2AP-PROTOCOL-IES ::= {
        { ID id-TransactionID				CRITICALITY reject	TYPE TransactionID				PRESENCE mandatory	}|
        { ID id-Cause						CRITICALITY ignore	TYPE Cause						PRESENCE mandatory	}|
        { ID id-TimeToWait					CRITICALITY ignore	TYPE TimeToWait					PRESENCE optional	}|
        { ID id-CriticalityDiagnostics		CRITICALITY ignore	TYPE CriticalityDiagnostics		PRESENCE optional	}|
        { ID id-TNLinformation				CRITICALITY ignore	TYPE TNLinformation				PRESENCE optional	},
        ...
}

-- **************************************************************
--
-- E2 Connection Update Elementary Procedure
--
-- **************************************************************
-- **************************************************************
--
-- E2 CONNECTION UPDATE
--
-- **************************************************************
E2connectionUpdate ::= SEQUENCE {
        protocolIEs					ProtocolIE-Container	{{E2connectionUpdate-IEs}},
        ...
}

E2connectionUpdate-IEs E2AP-PROTOCOL-IES ::= {
        { ID id-TransactionID				CRITICALITY reject	TYPE TransactionID						PRESENCE mandatory	}|
        { ID id-E2connectionUpdateAdd		CRITICALITY reject	TYPE E2connectionUpdate-List			PRESENCE optional	}|
        { ID id-E2connectionUpdateRemove	CRITICALITY reject	TYPE E2connectionUpdateRemove-List		PRESENCE optional	}|
        { ID id-E2connectionUpdateModify	CRITICALITY reject	TYPE E2connectionUpdate-List			PRESENCE optional	},
        ...
}

E2connectionUpdate-List ::= SEQUENCE (SIZE(1..maxofTNLA)) OF ProtocolIE-SingleContainer { {E2connectionUpdate-ItemIEs} }

E2connectionUpdate-ItemIEs 	E2AP-PROTOCOL-IES ::= {
        { ID id-E2connectionUpdate-Item			CRITICALITY ignore 	TYPE E2connectionUpdate-Item 		PRESENCE mandatory	},
        ...
}

E2connectionUpdate-Item ::= SEQUENCE {
        tnlInformation					TNLinformation,
        tnlUsage						TNLusage,
        ...
}

E2connectionUpdateRemove-List ::= SEQUENCE (SIZE(1..maxofTNLA)) OF ProtocolIE-SingleContainer { {E2connectionUpdateRemove-ItemIEs} }

E2connectionUpdateRemove-ItemIEs 	E2AP-PROTOCOL-IES ::= {
        { ID id-E2connectionUpdateRemove-Item	CRITICALITY ignore 	TYPE E2connectionUpdateRemove-Item 	PRESENCE mandatory	},
        ...
}

E2connectionUpdateRemove-Item ::= SEQUENCE {
        tnlInformation					TNLinformation,
        ...
}



-- **************************************************************
--
-- E2 CONNECTION UPDATE ACKNOWLEDGE
--
-- **************************************************************
E2connectionUpdateAcknowledge ::= SEQUENCE {
        protocolIEs					ProtocolIE-Container	{{E2connectionUpdateAck-IEs}},
        ...
}

E2connectionUpdateAck-IEs E2AP-PROTOCOL-IES ::= {
        { ID id-TransactionID				CRITICALITY reject	TYPE TransactionID						PRESENCE mandatory	}|
        { ID id-E2connectionSetup			CRITICALITY reject	TYPE E2connectionUpdate-List			PRESENCE optional	}|
        { ID id-E2connectionSetupFailed		CRITICALITY reject	TYPE E2connectionSetupFailed-List		PRESENCE optional	},
        ...
}

E2connectionSetupFailed-List ::= SEQUENCE (SIZE(1..maxofTNLA)) OF ProtocolIE-SingleContainer { {E2connectionSetupFailed-ItemIEs} }

E2connectionSetupFailed-ItemIEs 	E2AP-PROTOCOL-IES ::= {
        { ID id-E2connectionSetupFailed-Item			CRITICALITY ignore 	TYPE E2connectionSetupFailed-Item 		PRESENCE mandatory	},
        ...
}

E2connectionSetupFailed-Item ::= SEQUENCE {
        tnlInformation					TNLinformation,
        cause							Cause,
        ...
}

-- **************************************************************
--
-- E2 CONNECTION UPDATE FAILURE
--
-- **************************************************************
E2connectionUpdateFailure ::= SEQUENCE {
        protocolIEs			ProtocolIE-Container	{{E2connectionUpdateFailure-IEs}},
        ...
}

E2connectionUpdateFailure-IEs E2AP-PROTOCOL-IES ::= {
        { ID id-TransactionID						CRITICALITY reject	TYPE TransactionID							PRESENCE mandatory	}|
        { ID id-Cause								CRITICALITY reject	TYPE Cause									PRESENCE optional	}|
        { ID id-TimeToWait							CRITICALITY ignore	TYPE TimeToWait								PRESENCE optional	}|
        { ID id-CriticalityDiagnostics				CRITICALITY ignore	TYPE CriticalityDiagnostics					PRESENCE optional	},
        ...
}

-- **************************************************************
--
-- E2 Node Configuration Update Elementary Procedure
--
-- **************************************************************
-- **************************************************************
--
-- E2 NODE CONFIGURATION UPDATE
--
-- **************************************************************
E2nodeConfigurationUpdate ::= SEQUENCE {
        protocolIEs					ProtocolIE-Container	{{E2nodeConfigurationUpdate-IEs}},
        ...
}

E2nodeConfigurationUpdate-IEs E2AP-PROTOCOL-IES ::= {
        { ID id-TransactionID					CRITICALITY reject	TYPE TransactionID								PRESENCE mandatory	}|
        { ID id-GlobalE2node-ID					CRITICALITY reject	TYPE GlobalE2node-ID							PRESENCE optional	}|
        { ID id-E2nodeComponentConfigAddition	CRITICALITY reject	TYPE E2nodeComponentConfigAddition-List			PRESENCE optional	}|
        { ID id-E2nodeComponentConfigUpdate		CRITICALITY reject	TYPE E2nodeComponentConfigUpdate-List			PRESENCE optional	}|
        { ID id-E2nodeComponentConfigRemoval	CRITICALITY reject	TYPE E2nodeComponentConfigRemoval-List			PRESENCE optional	}|
        { ID id-E2nodeTNLassociationRemoval		CRITICALITY reject	TYPE E2nodeTNLassociationRemoval-List			PRESENCE optional	},
        ...
}

E2nodeComponentConfigAddition-List ::= SEQUENCE (SIZE(1..maxofE2nodeComponents)) OF ProtocolIE-SingleContainer { {E2nodeComponentConfigAddition-ItemIEs} }

E2nodeComponentConfigAddition-ItemIEs 	E2AP-PROTOCOL-IES ::= {
        { ID id-E2nodeComponentConfigAddition-Item	CRITICALITY reject 	TYPE E2nodeComponentConfigAddition-Item 		PRESENCE mandatory	},
        ...
}

E2nodeComponentConfigAddition-Item ::= SEQUENCE {
        e2nodeComponentInterfaceType		E2nodeComponentInterfaceType,
        e2nodeComponentID					E2nodeComponentID,
        e2nodeComponentConfiguration		E2nodeComponentConfiguration,
        ...
}

E2nodeComponentConfigUpdate-List ::= SEQUENCE (SIZE(1..maxofE2nodeComponents)) OF ProtocolIE-SingleContainer { {E2nodeComponentConfigUpdate-ItemIEs} }

E2nodeComponentConfigUpdate-ItemIEs 	E2AP-PROTOCOL-IES ::= {
        { ID id-E2nodeComponentConfigUpdate-Item	CRITICALITY reject 	TYPE E2nodeComponentConfigUpdate-Item 		PRESENCE mandatory	},
        ...
}

E2nodeComponentConfigUpdate-Item ::= SEQUENCE {
        e2nodeComponentInterfaceType		E2nodeComponentInterfaceType,
        e2nodeComponentID					E2nodeComponentID,
        e2nodeComponentConfiguration		E2nodeComponentConfiguration,
        ...
}

E2nodeComponentConfigRemoval-List ::= SEQUENCE (SIZE(1..maxofE2nodeComponents)) OF ProtocolIE-SingleContainer { {E2nodeComponentConfigRemoval-ItemIEs} }

E2nodeComponentConfigRemoval-ItemIEs 	E2AP-PROTOCOL-IES ::= {
        { ID id-E2nodeComponentConfigRemoval-Item	CRITICALITY reject 	TYPE E2nodeComponentConfigRemoval-Item 		PRESENCE mandatory	},
        ...
}

E2nodeComponentConfigRemoval-Item ::= SEQUENCE {
        e2nodeComponentInterfaceType		E2nodeComponentInterfaceType,
        e2nodeComponentID					E2nodeComponentID,
        ...
}

E2nodeTNLassociationRemoval-List ::= SEQUENCE (SIZE(1..maxofTNLA)) OF ProtocolIE-SingleContainer { {E2nodeTNLassociationRemoval-ItemIEs} }

E2nodeTNLassociationRemoval-ItemIEs 	E2AP-PROTOCOL-IES ::= {
        { ID id-E2nodeTNLassociationRemoval-Item	CRITICALITY reject 	TYPE E2nodeTNLassociationRemoval-Item 		PRESENCE mandatory	},
        ...
}

E2nodeTNLassociationRemoval-Item ::= SEQUENCE {
        tnlInformation						TNLinformation,
        tnlInformationRIC					TNLinformation,
        ...
}

-- **************************************************************
--
-- E2 NODE CONFIGURATION UPDATE ACKNOWLEDGE
--
-- **************************************************************
E2nodeConfigurationUpdateAcknowledge ::= SEQUENCE {
        protocolIEs					ProtocolIE-Container	{{E2nodeConfigurationUpdateAcknowledge-IEs}},
        ...
}

E2nodeConfigurationUpdateAcknowledge-IEs E2AP-PROTOCOL-IES ::= {
        { ID id-TransactionID							CRITICALITY reject	TYPE TransactionID								PRESENCE mandatory	}|
        { ID id-E2nodeComponentConfigAdditionAck		CRITICALITY reject	TYPE E2nodeComponentConfigAdditionAck-List		PRESENCE optional	}|
        { ID id-E2nodeComponentConfigUpdateAck			CRITICALITY reject	TYPE E2nodeComponentConfigUpdateAck-List		PRESENCE optional	}|
        { ID id-E2nodeComponentConfigRemovalAck			CRITICALITY reject	TYPE E2nodeComponentConfigRemovalAck-List		PRESENCE optional	},
        ...
}

E2nodeComponentConfigAdditionAck-List ::= SEQUENCE (SIZE(1..maxofE2nodeComponents)) OF ProtocolIE-SingleContainer { {E2nodeComponentConfigAdditionAck-ItemIEs} }

E2nodeComponentConfigAdditionAck-ItemIEs 	E2AP-PROTOCOL-IES ::= {
        { ID id-E2nodeComponentConfigAdditionAck-Item			CRITICALITY reject 	TYPE E2nodeComponentConfigAdditionAck-Item 	PRESENCE mandatory	},
        ...
}

E2nodeComponentConfigAdditionAck-Item ::= SEQUENCE {
        e2nodeComponentInterfaceType		E2nodeComponentInterfaceType,
        e2nodeComponentID					E2nodeComponentID,
        e2nodeComponentConfigurationAck		E2nodeComponentConfigurationAck,
        ...
}

E2nodeComponentConfigUpdateAck-List ::= SEQUENCE (SIZE(1..maxofE2nodeComponents)) OF ProtocolIE-SingleContainer { {E2nodeComponentConfigUpdateAck-ItemIEs} }

E2nodeComponentConfigUpdateAck-ItemIEs 	E2AP-PROTOCOL-IES ::= {
        { ID id-E2nodeComponentConfigUpdateAck-Item			CRITICALITY reject 	TYPE E2nodeComponentConfigUpdateAck-Item 	PRESENCE mandatory	},
        ...
}

E2nodeComponentConfigUpdateAck-Item ::= SEQUENCE {
        e2nodeComponentInterfaceType		E2nodeComponentInterfaceType,
        e2nodeComponentID					E2nodeComponentID,
        e2nodeComponentConfigurationAck		E2nodeComponentConfigurationAck,
        ...
}

E2nodeComponentConfigRemovalAck-List ::= SEQUENCE (SIZE(1..maxofE2nodeComponents)) OF ProtocolIE-SingleContainer { {E2nodeComponentConfigRemovalAck-ItemIEs} }

E2nodeComponentConfigRemovalAck-ItemIEs 	E2AP-PROTOCOL-IES ::= {
        { ID id-E2nodeComponentConfigRemovalAck-Item			CRITICALITY reject 	TYPE E2nodeComponentConfigRemovalAck-Item 	PRESENCE mandatory	},
        ...
}

E2nodeComponentConfigRemovalAck-Item ::= SEQUENCE {
        e2nodeComponentInterfaceType		E2nodeComponentInterfaceType,
        e2nodeComponentID					E2nodeComponentID,
        e2nodeComponentConfigurationAck		E2nodeComponentConfigurationAck,
        ...
}

-- **************************************************************
--
-- E2 NODE CONFIGURATION UPDATE FAILURE
--
-- **************************************************************
E2nodeConfigurationUpdateFailure ::= SEQUENCE {
        protocolIEs			ProtocolIE-Container	{{E2nodeConfigurationUpdateFailure-IEs}},
        ...
}

E2nodeConfigurationUpdateFailure-IEs E2AP-PROTOCOL-IES ::= {
        { ID id-TransactionID						CRITICALITY reject	TYPE TransactionID								PRESENCE mandatory	}|
        { ID id-Cause								CRITICALITY ignore	TYPE Cause										PRESENCE mandatory	}|
        { ID id-TimeToWait							CRITICALITY ignore	TYPE TimeToWait									PRESENCE optional	}|
        { ID id-CriticalityDiagnostics				CRITICALITY ignore	TYPE CriticalityDiagnostics						PRESENCE optional	},
        ...
}

-- **************************************************************
--
-- Reset Elementary Procedure
--
-- **************************************************************

-- **************************************************************
--
-- RESET REQUEST
--
-- **************************************************************

ResetRequest ::= SEQUENCE {
        protocolIEs		ProtocolIE-Container		{ {ResetRequestIEs} },
        ...
}

ResetRequestIEs E2AP-PROTOCOL-IES ::= {
        { ID id-TransactionID				CRITICALITY reject	TYPE TransactionID				PRESENCE mandatory	}|
        { ID id-Cause						CRITICALITY ignore	TYPE Cause						PRESENCE mandatory	},
        ...
}

-- **************************************************************
--
-- RESET RESPONSE
--
-- **************************************************************

ResetResponse ::= SEQUENCE {
        protocolIEs		ProtocolIE-Container		{ {ResetResponseIEs} },
        ...
}

ResetResponseIEs E2AP-PROTOCOL-IES ::= {
        { ID id-TransactionID				CRITICALITY reject	TYPE TransactionID				PRESENCE mandatory	}|
        { ID id-CriticalityDiagnostics		CRITICALITY ignore	TYPE CriticalityDiagnostics		PRESENCE optional	},
        ...
}

-- **************************************************************
--
-- RIC Service Update Elementary Procedure
--
-- **************************************************************
-- **************************************************************
--
-- RIC SERVICE UPDATE
--
-- **************************************************************
RICserviceUpdate ::= SEQUENCE {
        protocolIEs					ProtocolIE-Container	{{RICserviceUpdate-IEs}},
        ...
}

RICserviceUpdate-IEs E2AP-PROTOCOL-IES ::= {
        { ID id-TransactionID				CRITICALITY reject	TYPE TransactionID					PRESENCE mandatory	}|
        { ID id-RANfunctionsAdded			CRITICALITY reject	TYPE RANfunctions-List				PRESENCE optional	}|
        { ID id-RANfunctionsModified		CRITICALITY reject	TYPE RANfunctions-List				PRESENCE optional	}|
        { ID id-RANfunctionsDeleted			CRITICALITY reject	TYPE RANfunctionsID-List			PRESENCE optional	},
        ...
}

RANfunctions-List ::= SEQUENCE (SIZE(1..maxofRANfunctionID)) OF ProtocolIE-SingleContainer { {RANfunction-ItemIEs} }

RANfunction-ItemIEs 	E2AP-PROTOCOL-IES ::= {
        { ID id-RANfunction-Item			CRITICALITY ignore 	TYPE RANfunction-Item 				PRESENCE mandatory	},
        ...
}


RANfunction-Item ::= SEQUENCE {
        ranFunctionID				RANfunctionID,
        ranFunctionDefinition		RANfunctionDefinition,
        ranFunctionRevision			RANfunctionRevision,
        ranFunctionOID				RANfunctionOID,
        ...
}

RANfunctionsID-List ::= SEQUENCE (SIZE(1..maxofRANfunctionID)) OF ProtocolIE-SingleContainer{{RANfunctionID-ItemIEs}}

RANfunctionID-ItemIEs E2AP-PROTOCOL-IES ::= {
        { ID id-RANfunctionID-Item			CRITICALITY ignore		TYPE RANfunctionID-Item			PRESENCE mandatory	},
        ...
}

RANfunctionID-Item ::= SEQUENCE {
        ranFunctionID				RANfunctionID,
        ranFunctionRevision			RANfunctionRevision,
        ...
}

-- **************************************************************
--
-- RIC SERVICE UPDATE ACKNOWLEDGE
--
-- **************************************************************
RICserviceUpdateAcknowledge ::= SEQUENCE {
        protocolIEs					ProtocolIE-Container	{{RICserviceUpdateAcknowledge-IEs}},
        ...
}

RICserviceUpdateAcknowledge-IEs E2AP-PROTOCOL-IES ::= {
        { ID id-TransactionID				CRITICALITY reject	TYPE TransactionID					PRESENCE mandatory	}|
        { ID id-RANfunctionsAccepted		CRITICALITY reject	TYPE RANfunctionsID-List			PRESENCE optional	}|
        { ID id-RANfunctionsRejected		CRITICALITY reject	TYPE RANfunctionsIDcause-List		PRESENCE optional	},
        ...
}

RANfunctionsIDcause-List ::= SEQUENCE (SIZE(1..maxofRANfunctionID)) OF ProtocolIE-SingleContainer { {RANfunctionIDcause-ItemIEs} }

RANfunctionIDcause-ItemIEs 	E2AP-PROTOCOL-IES ::= {
        { ID id-RANfunctionIEcause-Item		CRITICALITY ignore 	TYPE RANfunctionIDcause-Item 		PRESENCE mandatory	},
        ...
}


RANfunctionIDcause-Item ::= SEQUENCE {
        ranFunctionID				RANfunctionID,
        cause						Cause,
        ...
}


-- **************************************************************
--
-- RIC SERVICE UPDATE FAILURE
--
-- **************************************************************
RICserviceUpdateFailure ::= SEQUENCE {
        protocolIEs			ProtocolIE-Container	{{RICserviceUpdateFailure-IEs}},
        ...
}

RICserviceUpdateFailure-IEs E2AP-PROTOCOL-IES ::= {
        { ID id-TransactionID				CRITICALITY reject	TYPE TransactionID					PRESENCE mandatory	}|
        { ID id-Cause						CRITICALITY reject	TYPE Cause							PRESENCE mandatory	}|
        { ID id-TimeToWait					CRITICALITY ignore	TYPE TimeToWait						PRESENCE optional	}|
        { ID id-CriticalityDiagnostics		CRITICALITY ignore	TYPE CriticalityDiagnostics			PRESENCE optional	},
        ...
}

-- **************************************************************
--
-- RIC Service Query Elementary Procedure
--
-- **************************************************************
-- **************************************************************
--
-- RIC SERVICE QUERY
--
-- **************************************************************
RICserviceQuery ::= SEQUENCE {
        protocolIEs					ProtocolIE-Container	{{RICserviceQuery-IEs}},
        ...
}

RICserviceQuery-IEs E2AP-PROTOCOL-IES ::= {
        { ID id-TransactionID				CRITICALITY reject	TYPE TransactionID					PRESENCE mandatory	}|
        { ID id-RANfunctionsAccepted		CRITICALITY reject	TYPE RANfunctionsID-List			PRESENCE optional	},
        ...
}

-- **************************************************************
--
-- E2 Removal Elementary Procedure
--
-- **************************************************************
-- **************************************************************
--
-- E2 REMOVAL REQUEST
--
-- **************************************************************

E2RemovalRequest ::= SEQUENCE {
        protocolIEs					ProtocolIE-Container	{ {E2RemovalRequestIEs} },
        ...
}

E2RemovalRequestIEs E2AP-PROTOCOL-IES ::= {
        { ID id-TransactionID				CRITICALITY reject	TYPE TransactionID						PRESENCE mandatory	},
        ...
}

-- **************************************************************
--
-- E2 REMOVAL RESPONSE
--
-- **************************************************************

E2RemovalResponse ::= SEQUENCE {
        protocolIEs					ProtocolIE-Container	{ {E2RemovalResponseIEs} },
        ...
}

E2RemovalResponseIEs E2AP-PROTOCOL-IES ::= {
        { ID id-TransactionID				CRITICALITY reject	TYPE TransactionID							PRESENCE mandatory	}|
        { ID id-CriticalityDiagnostics		CRITICALITY ignore	TYPE CriticalityDiagnostics		PRESENCE optional	},
        ...
}

-- **************************************************************
--
-- E2 REMOVAL FAILURE
--
-- **************************************************************

E2RemovalFailure ::= SEQUENCE {
        protocolIEs					ProtocolIE-Container	{ {E2RemovalFailureIEs} },
        ...
}

E2RemovalFailureIEs E2AP-PROTOCOL-IES ::= {
        { ID id-TransactionID				CRITICALITY reject	TYPE TransactionID				PRESENCE mandatory	}|
        { ID id-Cause						CRITICALITY ignore	TYPE Cause						PRESENCE mandatory	}|
        { ID id-CriticalityDiagnostics		CRITICALITY ignore	TYPE CriticalityDiagnostics		PRESENCE optional	},
        ...
}

END
-- ASN1STOP

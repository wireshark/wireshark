-- This ASN.1 module was taken from 3GPP TS 33.128 V19.3.0 (2025-06) and modified to pass through asn2wrs

TS33128Payloads
{itu-t(0) identified-organization(4) etsi(0) securityDomain(2) lawfulIntercept(2) threeGPP(4) ts33128(19) r19(19) version3(3)}

DEFINITIONS IMPLICIT TAGS ::=

BEGIN

IMPORTS

-- from ETSI TS 102 232-3 [6]
    IPIRIPacketReport
        FROM IPAccessPDU
        {itu-t(0) identified-organization(4) etsi(0) securityDomain(2) lawfulIntercept(2) li-ps(5) iPAccess(3) version18(18)};

-- end of IMPORTS

-- =============
-- Relative OIDs
-- =============

tS33128PayloadsOID          RELATIVE-OID ::= {threeGPP(4) ts33128(19) r19(19) version3(3)}

xIRIPayloadOID              RELATIVE-OID ::= {tS33128PayloadsOID xIRI(1)}
xCCPayloadOID               RELATIVE-OID ::= {tS33128PayloadsOID xCC(2)}
iRIPayloadOID               RELATIVE-OID ::= {tS33128PayloadsOID iRI(3)}
cCPayloadOID                RELATIVE-OID ::= {tS33128PayloadsOID cC(4)}
lINotificationPayloadOID    RELATIVE-OID ::= {tS33128PayloadsOID lINotification(5)}

-- ===============
-- X2 xIRI payload
-- ===============

XIRIPayload ::= SEQUENCE
{
    xIRIPayloadOID      [1] RELATIVE-OID,
    event               [2] XIRIEvent
}

XIRIEvent ::= CHOICE
{
    -- AMF events, see clause 6.2.2.2
    registration                                        [1] AMFRegistration,
    deregistration                                      [2] AMFDeregistration,
    locationUpdate                                      [3] AMFLocationUpdate,
    startOfInterceptionWithRegisteredUE                 [4] AMFStartOfInterceptionWithRegisteredUE,
    unsuccessfulAMProcedure                             [5] AMFUnsuccessfulProcedure,

    -- SMF events, see clause 6.2.3.2
    pDUSessionEstablishment                             [6] SMFPDUSessionEstablishment,
    pDUSessionModification                              [7] SMFPDUSessionModification,
    pDUSessionRelease                                   [8] SMFPDUSessionRelease,
    startOfInterceptionWithEstablishedPDUSession        [9] SMFStartOfInterceptionWithEstablishedPDUSession,
    unsuccessfulSMProcedure                             [10] SMFUnsuccessfulProcedure,

    -- UDM events, see clause 7.2.2.3
    servingSystemMessage                                [11] UDMServingSystemMessage,

    -- SMS events, see clause 6.2.5.2
    sMSMessage                                          [12] SMSMessage,

    -- LALS events, see clause 7.3.1.4
    lALSReport                                          [13] LALSReport,

    -- PDHR/PDSR events, see clauses 6.2.3.5 and 6.2.3.9
    pDHeaderReport                                      [14] PDHeaderReport,
    pDSummaryReport                                     [15] PDSummaryReport,

    -- Tag 16 is reserved because there is no equivalent mDFCellSiteReport in XIRIEvent.

    -- MMS events, see clause 7.4.3 see also MMSConverted events ([162-163] below)
    mMSSend                                             [17] MMSSend,
    mMSSendByNonLocalTarget                             [18] MMSSendByNonLocalTarget,
    mMSNotification                                     [19] MMSNotification,
    mMSSendToNonLocalTarget                             [20] MMSSendToNonLocalTarget,
    mMSNotificationResponse                             [21] MMSNotificationResponse,
    mMSRetrieval                                        [22] MMSRetrieval,
    mMSDeliveryAck                                      [23] MMSDeliveryAck,
    mMSForward                                          [24] MMSForward,
    mMSDeleteFromRelay                                  [25] MMSDeleteFromRelay,
    mMSDeliveryReport                                   [26] MMSDeliveryReport,
    mMSDeliveryReportNonLocalTarget                     [27] MMSDeliveryReportNonLocalTarget,
    mMSReadReport                                       [28] MMSReadReport,
    mMSReadReportNonLocalTarget                         [29] MMSReadReportNonLocalTarget,
    mMSCancel                                           [30] MMSCancel,
    mMSMBoxStore                                        [31] MMSMBoxStore,
    mMSMBoxUpload                                       [32] MMSMBoxUpload,
    mMSMBoxDelete                                       [33] MMSMBoxDelete,
    mMSMBoxViewRequest                                  [34] MMSMBoxViewRequest,
    mMSMBoxViewResponse                                 [35] MMSMBoxViewResponse,

    -- PTC events, see clause 7.5.2
    pTCRegistration                                     [36] PTCRegistration,
    pTCSessionInitiation                                [37] PTCSessionInitiation,
    pTCSessionAbandon                                   [38] PTCSessionAbandon,
    pTCSessionStart                                     [39] PTCSessionStart,
    pTCSessionEnd                                       [40] PTCSessionEnd,
    pTCStartOfInterception                              [41] PTCStartOfInterception,
    pTCPreEstablishedSession                            [42] PTCPreEstablishedSession,
    pTCInstantPersonalAlert                             [43] PTCInstantPersonalAlert,
    pTCPartyJoin                                        [44] PTCPartyJoin,
    pTCPartyDrop                                        [45] PTCPartyDrop,
    pTCPartyHold                                        [46] PTCPartyHold,
    pTCMediaModification                                [47] PTCMediaModification,
    pTCGroupAdvertisement                               [48] PTCGroupAdvertisement,
    pTCFloorControl                                     [49] PTCFloorControl,
    pTCTargetPresence                                   [50] PTCTargetPresence,
    pTCParticipantPresence                              [51] PTCParticipantPresence,
    pTCListManagement                                   [52] PTCListManagement,
    pTCAccessPolicy                                     [53] PTCAccessPolicy,

    -- UDM events, see clause 7.2.2.3, continued from tag 11
    subscriberRecordChangeMessage                       [54] UDMSubscriberRecordChangeMessage,
    cancelLocationMessage                               [55] UDMCancelLocationMessage,

    -- SMS events, see clause 6.2.5.2, continued from tag 12
    sMSReport                                           [56] SMSReport,

    -- SMF MA PDU session events, see clause 6.2.3.2.7
    sMFMAPDUSessionEstablishment                        [57] SMFMAPDUSessionEstablishment,
    sMFMAPDUSessionModification                         [58] SMFMAPDUSessionModification,
    sMFMAPDUSessionRelease                              [59] SMFMAPDUSessionRelease,
    startOfInterceptionWithEstablishedMAPDUSession      [60] SMFStartOfInterceptionWithEstablishedMAPDUSession,
    unsuccessfulMASMProcedure                           [61] SMFMAUnsuccessfulProcedure,

    -- Identifier Association events, see clauses 6.2.2.2.7 and 6.3.2.2.2
    aMFIdentifierAssociation                            [62] AMFIdentifierAssociation,
    mMEIdentifierAssociation                            [63] MMEIdentifierAssociation,

    -- SMF PDU to MA PDU session events, see clause 6.2.3.2.8
    sMFPDUtoMAPDUSessionModification                    [64] SMFPDUtoMAPDUSessionModification,

    -- NEF events, see clause 7.7.2.1
    nEFPDUSessionEstablishment                          [65] NEFPDUSessionEstablishment,
    nEFPDUSessionModification                           [66] NEFPDUSessionModification,
    nEFPDUSessionRelease                                [67] NEFPDUSessionRelease,
    nEFUnsuccessfulProcedure                            [68] NEFUnsuccessfulProcedure,
    nEFStartOfInterceptionWithEstablishedPDUSession     [69] NEFStartOfInterceptionWithEstablishedPDUSession,
    nEFdeviceTrigger                                    [70] NEFDeviceTrigger,
    nEFdeviceTriggerReplace                             [71] NEFDeviceTriggerReplace,
    nEFdeviceTriggerCancellation                        [72] NEFDeviceTriggerCancellation,
    nEFdeviceTriggerReportNotify                        [73] NEFDeviceTriggerReportNotify,
    nEFMSISDNLessMOSMS                                  [74] NEFMSISDNLessMOSMS,
    nEFExpectedUEBehaviourUpdate                        [75] NEFExpectedUEBehaviourUpdate,

    -- SCEF events, see clause 7.8.2.1
    sCEFPDNConnectionEstablishment                      [76] SCEFPDNConnectionEstablishment,
    sCEFPDNConnectionUpdate                             [77] SCEFPDNConnectionUpdate,
    sCEFPDNConnectionRelease                            [78] SCEFPDNConnectionRelease,
    sCEFUnsuccessfulProcedure                           [79] SCEFUnsuccessfulProcedure,
    sCEFStartOfInterceptionWithEstablishedPDNConnection [80] SCEFStartOfInterceptionWithEstablishedPDNConnection,
    sCEFdeviceTrigger                                   [81] SCEFDeviceTrigger,
    sCEFdeviceTriggerReplace                            [82] SCEFDeviceTriggerReplace,
    sCEFdeviceTriggerCancellation                       [83] SCEFDeviceTriggerCancellation,
    sCEFdeviceTriggerReportNotify                       [84] SCEFDeviceTriggerReportNotify,
    sCEFMSISDNLessMOSMS                                 [85] SCEFMSISDNLessMOSMS,
    sCEFCommunicationPatternUpdate                      [86] SCEFCommunicationPatternUpdate,

    -- MME events, see clause 6.3.2.2
    mMEAttach                                           [87] MMEAttach,
    mMEDetach                                           [88] MMEDetach,
    mMELocationUpdate                                   [89] MMELocationUpdate,
    mMEStartOfInterceptionWithEPSAttachedUE             [90] MMEStartOfInterceptionWithEPSAttachedUE,
    mMEUnsuccessfulProcedure                            [91] MMEUnsuccessfulProcedure,

    -- AKMA key management events, see clauses 7.9.1.3 and 7.9.1.4
    aAnFAnchorKeyRegister                               [92] AAnFAnchorKeyRegister,
    aAnFKAKMAApplicationKeyGet                          [93] AAnFKAKMAApplicationKeyGet,
    aAnFStartOfInterceptWithEstablishedAKMAKeyMaterial  [94] AAnFStartOfInterceptWithEstablishedAKMAKeyMaterial,
    aAnFAKMAContextRemovalRecord                        [95] AAnFAKMAContextRemovalRecord,
    aFAKMAApplicationKeyRefresh                         [96] AFAKMAApplicationKeyRefresh,
    aFStartOfInterceptWithEstablishedAKMAApplicationKey [97] AFStartOfInterceptWithEstablishedAKMAApplicationKey,
    aFAuxiliarySecurityParameterEstablishment           [98] AFAuxiliarySecurityParameterEstablishment,
    aFApplicationKeyRemoval                             [99] AFApplicationKeyRemoval,

    -- HR LI events, see clause 7.10.3.3
    n9HRPDUSessionInfo                                  [100] N9HRPDUSessionInfo,
    s8HRBearerInfo                                      [101] S8HRBearerInfo,

    -- Separated Location Reporting, see clause 7.3.4.1
    separatedLocationReporting                          [102] SeparatedLocationReporting,

    -- STIR SHAKEN and RCD/eCNAM events, see clause 7.11.2
    sTIRSHAKENSignatureGeneration                       [103] STIRSHAKENSignatureGeneration,
    sTIRSHAKENSignatureValidation                       [104] STIRSHAKENSignatureValidation,

    -- IMS events, see clause 7.12.4.2
    iMSMessage                                          [105] IMSMessage,
    startOfInterceptionForActiveIMSSession              [106] StartOfInterceptionForActiveIMSSession,
    iMSCCUnavailable                                    [107] IMSCCUnavailable,

    -- UDM events, see clause 7.2.2.3, continued from tag 55
    uDMLocationInformationResult                        [108] UDMLocationInformationResult,
    uDMUEInformationResponse                            [109] UDMUEInformationResponse,
    uDMUEAuthenticationResponse                         [110] UDMUEAuthenticationResponse,

    -- AMF events, see 6.2.2.2.8, continued from tag 5
    positioningInfoTransfer                             [111] AMFPositioningInfoTransfer,

    -- MME events, see clause 6.3.2.2.8, continued from tag 91
    mMEPositioningInfoTransfer                          [112] MMEPositioningInfoTransfer,

    -- AMF events, see 6.2.2.2.9, continued from tag 111
    aMFRANHandoverCommand                               [113] AMFRANHandoverCommand,
    aMFRANHandoverRequest                               [114] AMFRANHandoverRequest,

    -- EES events, see clause 7.14.2
    eESEECRegistration                                  [115] EESEECRegistration,
    eESEASDiscovery                                     [116] EESEASDiscovery,
    eESEASDiscoverySubscription                         [117] EESEASDiscoverySubscription,
    eESEASDiscoveryNotification                         [118] EESEASDiscoveryNotification,
    eESAppContextRelocation                             [119] EESAppContextRelocation,
    eESACRSubscription                                  [120] EESACRSubscription,
    eESACRNotification                                  [121] EESACRNotification,
    eESEECContextRelocation                             [122] EESEECContextRelocation,
    eESStartOfInterceptionWithRegisteredEEC             [123] EESStartOfInterceptionWithRegisteredEEC,

    -- UDM events, see clause 7.2.2.3, continued from tag 110
    uDMStartOfInterceptionWithRegisteredTarget          [124] UDMStartOfInterceptionWithRegisteredTarget,

    -- 5GMS AF events, see clause 7.15.2
    fiveGMSAFServiceAccessInformation                   [125] FiveGMSAFServiceAccessInformation,
    fiveGMSAFConsumptionReporting                       [126] FiveGMSAFConsumptionReporting,
    fiveGMSAFDynamicPolicyInvocation                    [127] FiveGMSAFDynamicPolicyInvocation,
    fiveGMSAFMetricsReporting                           [128] FiveGMSAFMetricsReporting,
    fiveGMSAFNetworkAssistance                          [129] FiveGMSAFNetworkAssistance,
    fiveGMSAFUnsuccessfulProcedure                      [130] FiveGMSAFUnsuccessfulProcedure,
    fiveGMSAFStartOfInterceptionWithAlreadyConfiguredUE [131] FiveGMSAFStartOfInterceptionWithAlreadyConfiguredUE,

    -- AMF events, see 6.2.2.2.10, continued from tag 114
    aMFUEConfigurationUpdate                            [132] AMFUEConfigurationUpdate,

    -- HSS events, see clause 7.2.3.3
    hSSServingSystemMessage                             [133] HSSServingSystemMessage,
    hSSStartOfInterceptionWithRegisteredTarget          [134] HSSStartOfInterceptionWithRegisteredTarget,

    -- NEF events, see clause 7.7.6.1
    nEFAFSessionWithQoSProvision                        [135] NEFAFSessionWithQoSProvision,
    nEFAFSessionWithQoSNotification                     [136] NEFAFSessionWithQoSNotification,

    -- SCEF events, see clause 7.8.6.1
    sCEFASSessionWithQoSProvision                       [137] SCEFASSessionWithQoSProvision,
    sCEFASSessionWithQoSNotification                    [138] SCEFASSessionWithQoSNotification,

    -- AMF events, see 6.2.2.3, continued from tag 132
    aMFRANTraceReport                                   [139] AMFRANTraceReport,

    -- RCS events, see clause 7.13.3
    rCSRegistration                                     [140] RCSRegistration,
    rCSMessage                                          [141] RCSMessage,
    rCSCapabilityDiscovery                              [142] RCSCapabilityDiscovery,
    rCSSessionEstablishment                             [143] RCSSessionEstablishment,
    rCSSessionModification                              [144] RCSSessionModification,
    rCSSessionRelease                                   [145] RCSSessionRelease,

    -- AMF events, see clause 6.2.2.2.12, continued from tag 139
    aMFUEPolicyTransfer                                 [146] AMFUEPolicyTransfer,
    aMFUEServiceAccept                                  [147] AMFUEServiceAccept,

    -- MME events, see clause 6.3.2.2, continued from tag 112
    ePSRANHandoverCommand                               [148] EPSRANHandoverCommand,
    ePSRANHandoverRequest                               [149] EPSRANHandoverRequest,
    mMERANTraceReport                                   [150] MMERANTraceReport,
    mMEUEServiceAccept                                  [151] MMEUEServiceAccept,

    --NWDAF events, see clause 7.16.2
    nWDAFEventsSubscription                             [152] NWDAFEventsSubscription,
    nWDAFEventsNotification                             [153] NWDAFEventsNotification,
    nWDAFAnalyticsInfoQuery                             [154] NWDAFAnalyticsInfoQuery,
    nWDAFRoamingAnalyticsSubscription                   [155] NWDAFRoamingAnalyticsSubscription,
    nWDAFRoamingAnalyticsNotification                   [156] NWDAFRoamingAnalyticsNotification,

    -- RCS events, see clause 7.13.3, continued from tag 145
    startOfInterceptForRegisteredRCSUser                [157] StartOfInterceptForRegisteredRCSUser,
    startOfInterceptWithEstablisedRCSSession            [158] StartOfInterceptWithEstablisedRCSSession,

    -- UDM events, see clause 7.2.2.3, continued from tag 124
    uDMProSeTargetIdentifierDeconcealment               [159] UDMProSeTargetIdentifierDeconcealment,
    uDMProSeTargetAuthentication                        [160] UDMProSeTargetAuthentication,

    -- IP Packet Report, see clause 6.2.3.9.5
    iPIRIPacketReport                                   [161] IPIRIPacketReport,

    -- IMS events, see clause 7.12.4.2, continued from tag 107
    iMSDataChannelSetup                                 [162] IMSDataChannelSetup,
    iMSDataChannelModification                          [163] IMSDataChannelModification,
    iMSDataChannelTermination                           [164] IMSDataChannelTermination,

    -- MMS-related events continued from choice 35
    mMSConvertedFromEmail                               [165] MMSConvertedFromEmail,
    mMSConvertedToEmail                                 [166] MMSConvertedToEmail,

    -- NEF events, see clause 7.7.7.1
    nEF5GVNGroupCreation                                [167] NEF5GVNGroupCreation,
    nEF5GVNGroupUpdate                                  [168] NEF5GVNGroupUpdate,
    nEF5GVNGroupDeletion                                [169] NEF5GVNGroupDeletion,
    nEF5GVNGroupQuery                                   [170] NEF5GVNGroupQuery,

    -- HSS events, see clause 7.2.3.3
    hSSSubscriberRecordChange                           [171] HSSSubscriberRecordChange,

    -- IMS HSS events, see clause 7.2.4.3
    iMSHSSServingSystemMessage                          [172] IMSHSSServingSystemMessage,
    iMSHSSStartOfInterceptionWithRegisteredTarget       [173] IMSHSSStartOfInterceptionWithRegisteredTarget,
    iMSHSSSubscriberRecordChange                        [174] IMSHSSSubscriberRecordChange,

    -- AMF events, see clause 6.2.2.2.14, continued from tag 147
    aMFUEContextUpdate                                  [175] AMFUEContextUpdate,

    -- SGW events, see clause 6.3.3.2
    ePSPDNConnectionEstablishment                       [176] EPSPDNConnectionEstablishment,
    ePSPDNConnectionModification                        [177] EPSPDNConnectionModification,
    ePSPDNConnectionRelease                             [178] EPSPDNConnectionRelease,
    ePSStartOfInterceptionWithEstablishedPDNConnection  [179] EPSStartOfInterceptionWithEstablishedPDNConnection,
    ePSPDNUnsuccessfulProcedure                         [180] EPSPDNUnsuccessfulProcedure,

    -- IMS events, see clause 7.12.4.2, continued from tag 164
    startOfInterceptionWithEstablishedIMSDataChannel    [181] StartOfInterceptionWithEstablishedIMSDataChannel,

    -- SMF events, see clause 6.2.3.2 continued from tag 61
    sMFProSeRemoteUEReport                              [182] SMFProSeRemoteUEReport,
    sMFStartOfInterceptionWithConnectedProSeRemoteUE    [183] SMFStartOfInterceptionWithConnectedProSeRemoteUE,

    -- 5G ProSe Direct Communication events, see clause 7.17.2
    fiveGDDNMFProSeUNIDirectDiscovery                   [184] FiveGDDNMFProSeUNIDirectDiscovery,
    fiveGDDNMFProSeNNIDirectDiscovery                   [185] FiveGDDNMFProSeNNIDirectDiscovery,

    -- Additional Identifier Association events, see clauses 6.2.2.2.7 and 6.3.2.2.2
    aMFIdentifierDeassociation                          [186] AMFIdentifierDeassociation,
    mMEIdentifierDeassociation                          [187] MMEIdentifierDeassociation,

    -- 5G Personal IoT events, see clause 7.18.2
    fiveGPINAPPMessage                                  [188] FiveGPINAPPMessage,
    fiveGStartOfInterceptionWithPINClientInPIN          [189] FiveGStartOfInterceptionWithPINClientInPIN,

    -- Charging data event records, see clause 7.19
    chargingDataEvent                                   [190] ChargingDataEvent
}

-- ==============
-- X3 xCC payload
-- ==============

-- No additional xCC payload definitions required in the present document.

-- ===============
-- HI2 IRI payload
-- ===============

IRIPayload ::= SEQUENCE
{
    iRIPayloadOID          [1] RELATIVE-OID,
    event                  [2] IRIEvent,
    targetIdentifiers      [3] SEQUENCE OF IRITargetIdentifier OPTIONAL,
    mediatedFromIndicator  [4] MediatedFromIndicator OPTIONAL
}

IRIEvent ::= CHOICE
{
    -- AMF events, see clause 6.2.2.3
    registration                                        [1] AMFRegistration,
    deregistration                                      [2] AMFDeregistration,
    locationUpdate                                      [3] AMFLocationUpdate,
    startOfInterceptionWithRegisteredUE                 [4] AMFStartOfInterceptionWithRegisteredUE,
    unsuccessfulAMProcedure                             [5] AMFUnsuccessfulProcedure,

    -- SMF events, see clause 6.2.3.7
    pDUSessionEstablishment                             [6] SMFPDUSessionEstablishment,
    pDUSessionModification                              [7] SMFPDUSessionModification,
    pDUSessionRelease                                   [8] SMFPDUSessionRelease,
    startOfInterceptionWithEstablishedPDUSession        [9] SMFStartOfInterceptionWithEstablishedPDUSession,
    unsuccessfulSMProcedure                             [10] SMFUnsuccessfulProcedure,

    -- UDM events, see clause 7.2.2.4
    servingSystemMessage                                [11] UDMServingSystemMessage,

    -- SMS events, see clause 6.2.5.4
    sMSMessage                                          [12] SMSMessage,

    -- LALS events, see clause 7.3.1.5
    lALSReport                                          [13] LALSReport,

    -- PDHR/PDSR events, see clause 6.2.3.9
    pDHeaderReport                                      [14] PDHeaderReport,
    pDSummaryReport                                     [15] PDSummaryReport,

    -- MDF events, see clause 7.3.2.2
    mDFCellSiteReport                                   [16] MDFCellSiteReport,

    -- MMS events, see clause 7.4.4.1 see also MMSConverted events ([162-163] below)
    mMSSend                                             [17] MMSSend,
    mMSSendByNonLocalTarget                             [18] MMSSendByNonLocalTarget,
    mMSNotification                                     [19] MMSNotification,
    mMSSendToNonLocalTarget                             [20] MMSSendToNonLocalTarget,
    mMSNotificationResponse                             [21] MMSNotificationResponse,
    mMSRetrieval                                        [22] MMSRetrieval,
    mMSDeliveryAck                                      [23] MMSDeliveryAck,
    mMSForward                                          [24] MMSForward,
    mMSDeleteFromRelay                                  [25] MMSDeleteFromRelay,
    mMSDeliveryReport                                   [26] MMSDeliveryReport,
    mMSDeliveryReportNonLocalTarget                     [27] MMSDeliveryReportNonLocalTarget,
    mMSReadReport                                       [28] MMSReadReport,
    mMSReadReportNonLocalTarget                         [29] MMSReadReportNonLocalTarget,
    mMSCancel                                           [30] MMSCancel,
    mMSMBoxStore                                        [31] MMSMBoxStore,
    mMSMBoxUpload                                       [32] MMSMBoxUpload,
    mMSMBoxDelete                                       [33] MMSMBoxDelete,
    mMSMBoxViewRequest                                  [34] MMSMBoxViewRequest,
    mMSMBoxViewResponse                                 [35] MMSMBoxViewResponse,

    -- PTC events, see clauses 7.5.2 and 7.5.3.1
    pTCRegistration                                     [36] PTCRegistration,
    pTCSessionInitiation                                [37] PTCSessionInitiation,
    pTCSessionAbandon                                   [38] PTCSessionAbandon,
    pTCSessionStart                                     [39] PTCSessionStart,
    pTCSessionEnd                                       [40] PTCSessionEnd,
    pTCStartOfInterception                              [41] PTCStartOfInterception,
    pTCPreEstablishedSession                            [42] PTCPreEstablishedSession,
    pTCInstantPersonalAlert                             [43] PTCInstantPersonalAlert,
    pTCPartyJoin                                        [44] PTCPartyJoin,
    pTCPartyDrop                                        [45] PTCPartyDrop,
    pTCPartyHold                                        [46] PTCPartyHold,
    pTCMediaModification                                [47] PTCMediaModification,
    pTCGroupAdvertisement                               [48] PTCGroupAdvertisement,
    pTCFloorControl                                     [49] PTCFloorControl,
    pTCTargetPresence                                   [50] PTCTargetPresence,
    pTCParticipantPresence                              [51] PTCParticipantPresence,
    pTCListManagement                                   [52] PTCListManagement,
    pTCAccessPolicy                                     [53] PTCAccessPolicy,

    -- UDM events, see clause 7.2.2.4, continued from tag 11
    subscriberRecordChangeMessage                       [54] UDMSubscriberRecordChangeMessage,
    cancelLocationMessage                               [55] UDMCancelLocationMessage,

    -- SMS events, see clause 6.2.5.4, continued from tag 12
    sMSReport                                           [56] SMSReport,

    -- SMF MA PDU session events, see clause 6.2.3.7
    sMFMAPDUSessionEstablishment                        [57] SMFMAPDUSessionEstablishment,
    sMFMAPDUSessionModification                         [58] SMFMAPDUSessionModification,
    sMFMAPDUSessionRelease                              [59] SMFMAPDUSessionRelease,
    startOfInterceptionWithEstablishedMAPDUSession      [60] SMFStartOfInterceptionWithEstablishedMAPDUSession,
    unsuccessfulMASMProcedure                           [61] SMFMAUnsuccessfulProcedure,

    -- Identifier Association events, see clauses 6.2.2.3 and 6.3.2.3
    aMFIdentifierAssociation                            [62] AMFIdentifierAssociation,
    mMEIdentifierAssociation                            [63] MMEIdentifierAssociation,

    -- SMF PDU to MA PDU session events, see clause 6.2.3.7
    sMFPDUtoMAPDUSessionModification                    [64] SMFPDUtoMAPDUSessionModification,

    -- NEF events, see clause 7.7.2.3
    nEFPDUSessionEstablishment                          [65] NEFPDUSessionEstablishment,
    nEFPDUSessionModification                           [66] NEFPDUSessionModification,
    nEFPDUSessionRelease                                [67] NEFPDUSessionRelease,
    nEFUnsuccessfulProcedure                            [68] NEFUnsuccessfulProcedure,
    nEFStartOfInterceptionWithEstablishedPDUSession     [69] NEFStartOfInterceptionWithEstablishedPDUSession,
    nEFdeviceTrigger                                    [70] NEFDeviceTrigger,
    nEFdeviceTriggerReplace                             [71] NEFDeviceTriggerReplace,
    nEFdeviceTriggerCancellation                        [72] NEFDeviceTriggerCancellation,
    nEFdeviceTriggerReportNotify                        [73] NEFDeviceTriggerReportNotify,
    nEFMSISDNLessMOSMS                                  [74] NEFMSISDNLessMOSMS,
    nEFExpectedUEBehaviourUpdate                        [75] NEFExpectedUEBehaviourUpdate,

    -- SCEF events, see clause 7.8.2.3
    sCEFPDNConnectionEstablishment                      [76] SCEFPDNConnectionEstablishment,
    sCEFPDNConnectionUpdate                             [77] SCEFPDNConnectionUpdate,
    sCEFPDNConnectionRelease                            [78] SCEFPDNConnectionRelease,
    sCEFUnsuccessfulProcedure                           [79] SCEFUnsuccessfulProcedure,
    sCEFStartOfInterceptionWithEstablishedPDNConnection [80] SCEFStartOfInterceptionWithEstablishedPDNConnection,
    sCEFdeviceTrigger                                   [81] SCEFDeviceTrigger,
    sCEFdeviceTriggerReplace                            [82] SCEFDeviceTriggerReplace,
    sCEFdeviceTriggerCancellation                       [83] SCEFDeviceTriggerCancellation,
    sCEFdeviceTriggerReportNotify                       [84] SCEFDeviceTriggerReportNotify,
    sCEFMSISDNLessMOSMS                                 [85] SCEFMSISDNLessMOSMS,
    sCEFCommunicationPatternUpdate                      [86] SCEFCommunicationPatternUpdate,

    -- MME events, see clause 6.3.2.3
    mMEAttach                                           [87] MMEAttach,
    mMEDetach                                           [88] MMEDetach,
    mMELocationUpdate                                   [89] MMELocationUpdate,
    mMEStartOfInterceptionWithEPSAttachedUE             [90] MMEStartOfInterceptionWithEPSAttachedUE,
    mMEUnsuccessfulProcedure                            [91] MMEUnsuccessfulProcedure,

    -- AKMA key management events, see clause 7.9.1.5
    aAnFAnchorKeyRegister                               [92] AAnFAnchorKeyRegister,
    aAnFKAKMAApplicationKeyGet                          [93] AAnFKAKMAApplicationKeyGet,
    aAnFStartOfInterceptWithEstablishedAKMAKeyMaterial  [94] AAnFStartOfInterceptWithEstablishedAKMAKeyMaterial,
    aAnFAKMAContextRemovalRecord                        [95] AAnFAKMAContextRemovalRecord,
    aFAKMAApplicationKeyRefresh                         [96] AFAKMAApplicationKeyRefresh,
    aFStartOfInterceptWithEstablishedAKMAApplicationKey [97] AFStartOfInterceptWithEstablishedAKMAApplicationKey,
    aFAuxiliarySecurityParameterEstablishment           [98] AFAuxiliarySecurityParameterEstablishment,
    aFApplicationKeyRemoval                             [99] AFApplicationKeyRemoval,

    -- Tag 100 is reserved because there is no equivalent n9HRPDUSessionInfo in IRIEvent.
    -- Tag 101 is reserved because there is no equivalent S8HRBearerInfo in IRIEvent.

    -- Separated Location Reporting, see clause 7.3.4.1
    separatedLocationReporting                          [102] SeparatedLocationReporting,

    -- STIR SHAKEN and RCD/eCNAM events, see clause 7.11.3
    sTIRSHAKENSignatureGeneration                       [103] STIRSHAKENSignatureGeneration,
    sTIRSHAKENSignatureValidation                       [104] STIRSHAKENSignatureValidation,

    -- IMS events, see clause 7.12.7
    iMSMessage                                          [105] IMSMessage,
    startOfInterceptionForActiveIMSSession              [106] StartOfInterceptionForActiveIMSSession,
    iMSCCUnavailable                                    [107] IMSCCUnavailable,

    -- UDM events, see clause 7.2.2.4, continued from tag 55
    uDMLocationInformationResult                        [108] UDMLocationInformationResult,
    uDMUEInformationResponse                            [109] UDMUEInformationResponse,
    uDMUEAuthenticationResponse                         [110] UDMUEAuthenticationResponse,

    -- AMF events, see 6.2.2.3, continued from tag 5
    positioningInfoTransfer                             [111] AMFPositioningInfoTransfer,

    -- MME events, see clause 6.3.2.3, continued from tag 91
    mMEPositioningInfoTransfer                          [112] MMEPositioningInfoTransfer,

    -- AMF events, see 6.2.2.3, continued from tag 111
    aMFRANHandoverCommand                               [113] AMFRANHandoverCommand,
    aMFRANHandoverRequest                               [114] AMFRANHandoverRequest,

    -- EES events, see clause 7.14.2.11
    eESEECRegistration                                  [115] EESEECRegistration,
    eESEASDiscovery                                     [116] EESEASDiscovery,
    eESEASDiscoverySubscription                         [117] EESEASDiscoverySubscription,
    eESEASDiscoveryNotification                         [118] EESEASDiscoveryNotification,
    eESAppContextRelocation                             [119] EESAppContextRelocation,
    eESACRSubscription                                  [120] EESACRSubscription,
    eESACRNotification                                  [121] EESACRNotification,
    eESEECContextRelocation                             [122] EESEECContextRelocation,
    eESStartOfInterceptionWithRegisteredEEC             [123] EESStartOfInterceptionWithRegisteredEEC,

    -- UDM events, see clause 7.2.2.4, continued from tag 110
    uDMStartOfInterceptionWithRegisteredTarget          [124] UDMStartOfInterceptionWithRegisteredTarget,

    -- 5GMS AF events, see clause 7.15.3
    fiveGMSAFServiceAccessInformation                   [125] FiveGMSAFServiceAccessInformation,
    fiveGMSAFConsumptionReporting                       [126] FiveGMSAFConsumptionReporting,
    fiveGMSAFDynamicPolicyInvocation                    [127] FiveGMSAFDynamicPolicyInvocation,
    fiveGMSAFMetricsReporting                           [128] FiveGMSAFMetricsReporting,
    fiveGMSAFNetworkAssistance                          [129] FiveGMSAFNetworkAssistance,
    fiveGMSAFUnsuccessfulProcedure                      [130] FiveGMSAFUnsuccessfulProcedure,
    fiveGMSAFStartOfInterceptionWithAlreadyConfiguredUE [131] FiveGMSAFStartOfInterceptionWithAlreadyConfiguredUE,

    -- AMF events, see 6.2.2.3, continued from tag 114
    aMFUEConfigurationUpdate                            [132] AMFUEConfigurationUpdate,

    -- HSS events, see clause 7.2.3.4
    hSSServingSystemMessage                             [133] HSSServingSystemMessage,
    hSSStartOfInterceptionWithRegisteredTarget          [134] HSSStartOfInterceptionWithRegisteredTarget,

    -- NEF events, see clause 7.7.6.2
    nEFAFSessionWithQoSProvision                        [135] NEFAFSessionWithQoSProvision,
    nEFAFSessionWithQoSNotification                     [136] NEFAFSessionWithQoSNotification,

    -- SCEF events, see clause 7.8.6.2
    sCEFASSessionWithQoSProvision                       [137] SCEFASSessionWithQoSProvision,
    sCEFASSessionWithQoSNotification                    [138] SCEFASSessionWithQoSNotification,

    -- AMF events, see 6.2.2.3, continued from tag 132
    aMFRANTraceReport                                   [139] AMFRANTraceReport,

    -- RCS events, see clause 7.13.3
    rCSRegistration                                     [140] RCSRegistration,
    rCSMessage                                          [141] RCSMessage,
    rCSCapabilityDiscovery                              [142] RCSCapabilityDiscovery,
    rCSSessionEstablishment                             [143] RCSSessionEstablishment,
    rCSSessionModification                              [144] RCSSessionModification,
    rCSSessionRelease                                   [145] RCSSessionRelease,

    -- AMF events, see clause 6.2.2.3, continued from tag 139
    aMFUEPolicyTransfer                                 [146] AMFUEPolicyTransfer,
    aMFUEServiceAccept                                  [147] AMFUEServiceAccept,

    -- MME events, see clause 6.3.2.3, continued from tag 112
    ePSRANHandoverCommand                               [148] EPSRANHandoverCommand,
    ePSRANHandoverRequest                               [149] EPSRANHandoverRequest,
    mMERANTraceReport                                   [150] MMERANTraceReport,
    mMEUEServiceAccept                                  [151] MMEUEServiceAccept,

    --NWDAF events, see clause 7.16.3
    nWDAFEventsSubscription                             [152] NWDAFEventsSubscription,
    nWDAFEventsNotification                             [153] NWDAFEventsNotification,
    nWDAFAnalyticsInfoQuery                             [154] NWDAFAnalyticsInfoQuery,
    nWDAFRoamingAnalyticsSubscription                   [155] NWDAFRoamingAnalyticsSubscription,
    nWDAFRoamingAnalyticsNotification                   [156] NWDAFRoamingAnalyticsNotification,

    -- RCS events, see clause 7.13.3, continued from tag 145
    startOfInterceptForRegisteredRCSUser                [157] StartOfInterceptForRegisteredRCSUser,
    startOfInterceptWithEstablisedRCSSession            [158] StartOfInterceptWithEstablisedRCSSession,

    -- UDM events, see clause 7.2.2.3, continued from tag 124
    uDMProSeTargetIdentifierDeconcealment               [159] UDMProSeTargetIdentifierDeconcealment,
    uDMProSeTargetAuthentication                        [160] UDMProSeTargetAuthentication,

    -- Tag 161 is reserved because there is no equivalent IP Packet Report in IRIEvent.

    -- IMS events, see clause 7.12.7, continued from tag 107
    iMSDataChannelSetup                                 [162] IMSDataChannelSetup,
    iMSDataChannelModification                          [163] IMSDataChannelModification,
    iMSDataChannelTermination                           [164] IMSDataChannelTermination,

    -- MMS-related events continued from choice 35
    mMSConvertedFromEmail                               [165] MMSConvertedFromEmail,
    mMSConvertedToEmail                                 [166] MMSConvertedToEmail,

    -- NEF events, see clause 7.7.7.2
    nEF5GVNGroupCreation                                [167] NEF5GVNGroupCreation,
    nEF5GVNGroupUpdate                                  [168] NEF5GVNGroupUpdate,
    nEF5GVNGroupDeletion                                [169] NEF5GVNGroupDeletion,
    nEF5GVNGroupQuery                                   [170] NEF5GVNGroupQuery,

    -- HSS events, see clause 7.2.3.3
    hSSSubscriberRecordChange                           [171] HSSSubscriberRecordChange,

    -- IMS HSS events, see clause 7.2.4.3
    iMSHSSServingSystemMessage                          [172] IMSHSSServingSystemMessage,
    iMSHSSStartOfInterceptionWithRegisteredTarget       [173] IMSHSSStartOfInterceptionWithRegisteredTarget,
    iMSHSSSubscriberRecordChange                        [174] IMSHSSSubscriberRecordChange,

    -- AMF events, see clause 6.2.2.3, continued from tag 147
    aMFUEContextUpdate                                  [175] AMFUEContextUpdate,

    -- SGW events, see clause 6.3.3.2
    ePSPDNConnectionEstablishment                       [176] EPSPDNConnectionEstablishment,
    ePSPDNConnectionModification                        [177] EPSPDNConnectionModification,
    ePSPDNConnectionRelease                             [178] EPSPDNConnectionRelease,
    ePSStartOfInterceptionWithEstablishedPDNConnection  [179] EPSStartOfInterceptionWithEstablishedPDNConnection,
    ePSPDNUnsuccessfulProcedure                         [180] EPSPDNUnsuccessfulProcedure,

    -- IMS events, see clause 7.12.4.2, continued from tag 164
    startOfInterceptionWithEstablishedIMSDataChannel    [181] StartOfInterceptionWithEstablishedIMSDataChannel,

    -- SMF events, see clause 6.2.3.7 continued from tag 61
    sMFProSeRemoteUEReport                              [182] SMFProSeRemoteUEReport,
    sMFStartOfInterceptionWithConnectedProSeRemoteUE    [183] SMFStartOfInterceptionWithConnectedProSeRemoteUE,

    -- 5G ProSe Direct Communication events, see clause 7.17.3
    fiveGDDNMFProSeUNIDirectDiscovery                   [184] FiveGDDNMFProSeUNIDirectDiscovery,
    fiveGDDNMFProSeNNIDirectDiscovery                   [185] FiveGDDNMFProSeNNIDirectDiscovery,

    -- Additional Identifier Association events, see clauses 6.2.2.2.7 and 6.3.2.2.2
    aMFIdentifierDeassociation                          [186] AMFIdentifierDeassociation,
    mMEIdentifierDeassociation                          [187] MMEIdentifierDeassociation,

    -- 5G Personal IoT events, see clause 7.18.3
    fiveGPINAPPMessage                                  [188] FiveGPINAPPMessage,
    fiveGStartOfInterceptionWithPINClientInPIN          [189] FiveGStartOfInterceptionWithPINClientInPIN,

    -- Charging data event records, see clause 7.19
    chargingDataEvent                                   [190] ChargingDataEvent
}

IRITargetIdentifier ::= SEQUENCE
{
    identifier                                          [1] TargetIdentifier,
    provenance                                          [2] TargetIdentifierProvenance OPTIONAL
}

MediatedFromIndicator ::= CHOICE
{
    xIRIRelativeOID [1] RELATIVE-OID
}

-- ==============
-- HI3 CC payload
-- ==============

CCPayload ::= SEQUENCE
{
    cCPayloadOID         [1] RELATIVE-OID,
    pDU                  [2] CCPDU
}

CCPDU ::= CHOICE
{
    uPFCCPDU            [1] UPFCCPDU,
    extendedUPFCCPDU    [2] ExtendedUPFCCPDU,
    mMSCCPDU            [3] MMSCCPDU,

    -- In Rel-16 (threeGPP(4) ts33128(19) r16(16) version9(9)),
    -- tag 4 is pTCCCPDU and tag 5 is not used.
    -- Rel-17 or newer decoders should decode tag 4 contents as PTCCCPDU if
    -- r16 is used in cCPayloadOID.
    nIDDCCPDU           [4] NIDDCCPDU,
    pTCCCPDU            [5] PTCCCPDU,

    iMSCCPDU            [6] IMSCCPDU,
    rCSCCPDU            [7] RCSCCPDU
}

-- ===========================
-- HI4 LI notification payload
-- ===========================

LINotificationPayload ::= SEQUENCE
{
    lINotificationPayloadOID         [1] RELATIVE-OID,
    notification                     [2] LINotificationMessage
}

LINotificationMessage ::= CHOICE
{
    lINotification      [1] LINotification
}

-- =================
-- HR LI definitions
-- =================

N9HRPDUSessionInfo ::= SEQUENCE
{
    sUPI                            [1] SUPI,
    pEI                             [2] PEI OPTIONAL,
    pDUSessionID                    [3] PDUSessionID,
    location                        [4] Location OPTIONAL,
    sNSSAI                          [5] SNSSAI OPTIONAL,
    dNN                             [6] DNN OPTIONAL,
    messageCause                    [7] N9HRMessageCause
}

S8HRBearerInfo ::= SEQUENCE
{
    iMSI                            [1] IMSI,
    iMEI                            [2] IMEI OPTIONAL,
    bearerID                        [3] EPSBearerID,
    linkedBearerID                  [4] EPSBearerID OPTIONAL,
    location                        [5] Location OPTIONAL,
    aPN                             [6] APN OPTIONAL,
    sGWIPAddress                    [7] IPAddress OPTIONAL,
    messageCause                    [8] S8HRMessageCause
}

-- ================
-- HR LI parameters
-- ================

N9HRMessageCause ::= ENUMERATED
{
    pDUSessionEstablished(1),
    pDUSessionModified(2),
    pDUSessionReleased(3),
    updatedLocationAvailable(4),
    sMFChanged(5),
    other(6),
    hRLIEnabled(7)
}

S8HRMessageCause ::= ENUMERATED
{
    bearerActivated(1),
    bearerModified(2),
    bearerDeleted(3),
    pDNDisconnected(4),
    updatedLocationAvailable(5),
    sGWChanged(6),
    other(7),
    hRLIEnabled(8)
}

-- ==================
-- 5G NEF definitions
-- ==================

-- See clause 7.7.2.1.2 for details of this structure
NEFPDUSessionEstablishment ::= SEQUENCE
{
    sUPI                  [1] SUPI,
    gPSI                  [2] GPSI,
    pDUSessionID          [3] PDUSessionID,
    sNSSAI                [4] SNSSAI,
    nEFID                 [5] NEFID,
    dNN                   [6] DNN,
    rDSSupport            [7] RDSSupport,
    sMFID                 [8] SMFID,
    aFID                  [9] AFID
}

-- See clause 7.7.2.1.3 for details of this structure
NEFPDUSessionModification ::= SEQUENCE
{
    sUPI                         [1] SUPI,
    gPSI                         [2] GPSI,
    sNSSAI                       [3] SNSSAI,
    initiator                    [4] Initiator,
    rDSSourcePortNumber          [5] RDSPortNumber OPTIONAL,
    rDSDestinationPortNumber     [6] RDSPortNumber OPTIONAL,
    applicationID                [7] ApplicationID OPTIONAL,
    aFID                         [8] AFID OPTIONAL,
    rDSAction                    [9] RDSAction OPTIONAL,
    serializationFormat          [10] SerializationFormat OPTIONAL,
    pDUSessionID                 [11] PDUSessionID OPTIONAL
}

-- See clause 7.7.2.1.4 for details of this structure
NEFPDUSessionRelease ::= SEQUENCE
{
    sUPI                   [1] SUPI,
    gPSI                   [2] GPSI,
    pDUSessionID           [3] PDUSessionID,
    timeOfFirstPacket      [4] Timestamp OPTIONAL,
    timeOfLastPacket       [5] Timestamp OPTIONAL,
    uplinkVolume           [6] INTEGER OPTIONAL,
    downlinkVolume         [7] INTEGER OPTIONAL,
    releaseCause           [8] NEFReleaseCause
}

-- See clause 7.7.2.1.5 for details of this structure
NEFUnsuccessfulProcedure ::= SEQUENCE
{
    failureCause                 [1] NEFFailureCause,
    sUPI                         [2] SUPI,
    gPSI                         [3] GPSI OPTIONAL,
    pDUSessionID                 [4] PDUSessionID,
    dNN                          [5] DNN OPTIONAL,
    sNSSAI                       [6] SNSSAI OPTIONAL,
    rDSDestinationPortNumber     [7] RDSPortNumber,
    applicationID                [8] ApplicationID,
    aFID                         [9] AFID
}

-- See clause 7.7.2.1.6 for details of this structure
NEFStartOfInterceptionWithEstablishedPDUSession ::= SEQUENCE
{
    sUPI               [1] SUPI,
    gPSI               [2] GPSI,
    pDUSessionID       [3] PDUSessionID,
    dNN                [4] DNN,
    sNSSAI             [5] SNSSAI,
    nEFID              [6] NEFID,
    rDSSupport         [7] RDSSupport,
    sMFID              [8] SMFID,
    aFID               [9] AFID
}

-- See clause 7.7.3.1.1 for details of this structure
NEFDeviceTrigger ::= SEQUENCE
{
    sUPI                  [1] SUPI,
    gPSI                  [2] GPSI,
    triggerId             [3] TriggerID,
    aFID                  [4] AFID,
    triggerPayload        [5] TriggerPayload OPTIONAL,
    validityPeriod        [6] INTEGER OPTIONAL,
    priorityDT            [7] PriorityDT OPTIONAL,
    sourcePortId          [8] PortNumber OPTIONAL,
    destinationPortId     [9] PortNumber OPTIONAL
}

-- See clause 7.7.3.1.2 for details of this structure
NEFDeviceTriggerReplace ::= SEQUENCE
{
    sUPI                     [1] SUPI,
    gPSI                     [2] GPSI,
    triggerId                [3] TriggerID,
    aFID                     [4] AFID,
    triggerPayload           [5] TriggerPayload OPTIONAL,
    validityPeriod           [6] INTEGER OPTIONAL,
    priorityDT               [7] PriorityDT OPTIONAL,
    sourcePortId             [8] PortNumber OPTIONAL,
    destinationPortId        [9] PortNumber OPTIONAL
}

-- See clause 7.7.3.1.3 for details of this structure
NEFDeviceTriggerCancellation ::= SEQUENCE
{
    sUPI                  [1] SUPI,
    gPSI                  [2] GPSI,
    triggerId             [3] TriggerID
}

-- See clause 7.7.3.1.4 for details of this structure
NEFDeviceTriggerReportNotify ::= SEQUENCE
{
    sUPI                             [1] SUPI,
    gPSI                             [2] GPSI,
    triggerId                        [3] TriggerID,
    deviceTriggerDeliveryResult      [4] DeviceTriggerDeliveryResult
}

-- See clause 7.7.4.1.1 for details of this structure
NEFMSISDNLessMOSMS ::= SEQUENCE
{
    sUPI                      [1] SUPI,
    gPSI                      [2] GPSI,
    terminatingSMSParty       [3] AFID,
    sMS                       [4] SMSTPDUData OPTIONAL,
    sourcePort                [5] PortNumber OPTIONAL,
    destinationPort           [6] PortNumber OPTIONAL
}

-- See clause 7.7.5.1.1 for details of this structure
NEFExpectedUEBehaviourUpdate ::= SEQUENCE
{
    gPSI                                  [1] GPSI,
    expectedUEMovingTrajectory            [2] SEQUENCE OF UMTLocationArea5G OPTIONAL,
    stationaryIndication                  [3] StationaryIndication OPTIONAL,
    communicationDurationTime             [4] INTEGER OPTIONAL,
    periodicTime                          [5] INTEGER OPTIONAL,
    scheduledCommunicationTime            [6] ScheduledCommunicationTime OPTIONAL,
    scheduledCommunicationType            [7] ScheduledCommunicationType OPTIONAL,
    batteryIndication                     [8] BatteryIndication OPTIONAL,
    trafficProfile                        [9] TrafficProfile OPTIONAL,
    expectedTimeAndDayOfWeekInTrajectory  [10] SEQUENCE OF UMTLocationArea5G OPTIONAL,
    aFID                                  [11] AFID,
    validityTime                          [12] Timestamp OPTIONAL
}

-- See clause 7.7.6.1.2 for details of this structure
NEFAFSessionWithQoSProvision ::= SEQUENCE
{
    gPSI                                 [1] GPSI,
    aFID                                 [2] AFID,
    aFSessionWithQoSOpType               [3] AForASSessionWithQoSOpType,
    aFSessionWithQoSSubscription         [4] SBIType OPTIONAL,
    aFSessionWithQoSSubscriptionPatch    [5] SBIType OPTIONAL,
    aFSessionWithQoSResponseCode         [6] AForASSessionWithQoSResponseCode
}

-- See clause 7.7.6.1.3 for details of this structure
NEFAFSessionWithQoSNotification ::= SEQUENCE
{
    gPSI                                 [1] GPSI,
    aFID                                 [2] AFID,
    userPlaneNotificationData            [3] SBIType,
    aForASSessionWithQoSResponseCode     [4] AForASSessionWithQoSResponseCode
}

-- See clause 7.7.7.1.2 for details of this structure
NEF5GVNGroupCreation ::= SEQUENCE
{
    aFID                        [1] AFID,
    gPSI                        [2] GPSI,
    fiveGLanParametersProvision [3] SBIType
}

-- See clause 7.7.7.1.3 for details of this structure
NEF5GVNGroupUpdate ::= SEQUENCE
{
    aFID                             [1] AFID,
    gPSI                             [2] GPSI,
    fiveGLanParametersProvision      [3] SBIType OPTIONAL,
    fiveGLanParametersProvisionPatch [4] SBIType OPTIONAL
}

-- See clause 7.7.7.1.4 for details of this structure
NEF5GVNGroupDeletion ::= SEQUENCE
{
    aFID            [1] AFID,
    gPSI            [2] GPSI,
    externalGroupID [3] OCTET STRING
}

-- See clause 7.7.7.1.5 for details of this structure
NEF5GVNGroupQuery ::= SEQUENCE
{
    aFID                        [1] AFID,
    gPSI                        [2] GPSI,
    fiveGLanParametersProvision [3] SBIType
}

-- ==========================
-- Common SCEF/NEF parameters
-- ==========================

RDSSupport ::= BOOLEAN

RDSPortNumber ::= INTEGER (0..15)

RDSAction ::= ENUMERATED
{
    reservePort(1),
    releasePort(2)
}

SerializationFormat ::= ENUMERATED
{
    xml(1),
    json(2),
    cbor(3)
}

ApplicationID ::= OCTET STRING

NIDDCCPDU ::= OCTET STRING

TriggerID ::= UTF8String

PriorityDT ::= ENUMERATED
{
    noPriority(1),
    priority(2)
}

TriggerPayload ::= OCTET STRING

DeviceTriggerDeliveryResult ::= ENUMERATED
{
    success(1),
    unknown(2),
    failure(3),
    triggered(4),
    expired(5),
    unconfirmed(6),
    replaced(7),
    terminate(8)
}

StationaryIndication ::= ENUMERATED
{
    stationary(1),
    mobile(2)
}

BatteryIndication ::= ENUMERATED
{
    batteryRecharge(1),
    batteryReplace(2),
    batteryNoRecharge(3),
    batteryNoReplace(4),
    noBattery(5)
}

ScheduledCommunicationTime ::= SEQUENCE
{
    days [1] SEQUENCE OF Daytime
}

UMTLocationArea5G ::= SEQUENCE
{
    timeOfDay        [1] Daytime,
    durationSec      [2] INTEGER,
    location         [3] NRLocation
}

Daytime ::= SEQUENCE
{
    daysOfWeek       [1] Day OPTIONAL,
    timeOfDayStart   [2] Timestamp OPTIONAL,
    timeOfDayEnd     [3] Timestamp OPTIONAL
}

Day ::= ENUMERATED
{
    monday(1),
    tuesday(2),
    wednesday(3),
    thursday(4),
    friday(5),
    saturday(6),
    sunday(7)
}

TrafficProfile ::= ENUMERATED
{
    singleTransUL(1),
    singleTransDL(2),
    dualTransULFirst(3),
    dualTransDLFirst(4),
    multiTrans(5)
}

ScheduledCommunicationType ::= ENUMERATED
{
    downlinkOnly(1),
    uplinkOnly(2),
    bidirectional(3)
}

AForASSessionWithQoSResponseCode ::= ENUMERATED
{
    oK200(1),
    created201(2),
    noContent204(3),
    temporaryRedirect307(4),
    permanentRedirect308(5),
    badRequest400(6),
    unauthorized401(7),
    forbidden403(8),
    notFound404(9),
    notAcceptable406(10),
    lengthRequired411(11),
    unsupportedMediaType415(12),
    tooManyRequests429(13),
    internalServerError500(14),
    serviceUnavailable503(15)
}

AForASSessionWithQoSOpType ::= ENUMERATED
{
    pOST(1),
    pUT(2),
    pATCH(3),
    dELETE(4)
}

-- =================
-- 5G NEF parameters
-- =================

NEFFailureCause ::= ENUMERATED
{
    userUnknown(1),
    niddConfigurationNotAvailable(2),
    contextNotFound(3),
    portNotFree(4),
    portNotAssociatedWithSpecifiedApplication(5)
}

NEFReleaseCause ::= ENUMERATED
{
    sMFRelease(1),
    dNRelease(2),
    uDMRelease(3),
    cHFRelease(4),
    localConfigurationPolicy(5),
    unknownCause(6)
}

AFID ::= UTF8String

NEFID ::= UTF8String


-- ==================
-- SCEF definitions
-- ==================

-- See clause 7.8.2.1.2 for details of this structure
SCEFPDNConnectionEstablishment ::= SEQUENCE
{
    iMSI                  [1] IMSI OPTIONAL,
    mSISDN                [2] MSISDN OPTIONAL,
    externalIdentifier    [3] NAI OPTIONAL,
    iMEI                  [4] IMEI OPTIONAL,
    ePSBearerID           [5] EPSBearerID,
    sCEFID                [6] SCEFID,
    aPN                   [7] APN,
    rDSSupport            [8] RDSSupport,
    sCSASID               [9] SCSASID
}

-- See clause 7.8.2.1.3 for details of this structure
SCEFPDNConnectionUpdate ::= SEQUENCE
{
    iMSI                         [1] IMSI OPTIONAL,
    mSISDN                       [2] MSISDN OPTIONAL,
    externalIdentifier           [3] NAI OPTIONAL,
    initiator                    [4] Initiator,
    rDSSourcePortNumber          [5] RDSPortNumber OPTIONAL,
    rDSDestinationPortNumber     [6] RDSPortNumber OPTIONAL,
    applicationID                [7] ApplicationID OPTIONAL,
    sCSASID                      [8] SCSASID OPTIONAL,
    rDSAction                    [9] RDSAction OPTIONAL,
    serializationFormat          [10] SerializationFormat OPTIONAL,
    ePSBearerID                  [11] EPSBearerID OPTIONAL
}

-- See clause 7.8.2.1.4 for details of this structure
SCEFPDNConnectionRelease ::= SEQUENCE
{
    iMSI                   [1] IMSI OPTIONAL,
    mSISDN                 [2] MSISDN OPTIONAL,
    externalIdentifier     [3] NAI OPTIONAL,
    ePSBearerID            [4] EPSBearerID,
    timeOfFirstPacket      [5] Timestamp OPTIONAL,
    timeOfLastPacket       [6] Timestamp OPTIONAL,
    uplinkVolume           [7] INTEGER OPTIONAL,
    downlinkVolume         [8] INTEGER OPTIONAL,
    releaseCause           [9] SCEFReleaseCause
}

-- See clause 7.8.2.1.5 for details of this structure
SCEFUnsuccessfulProcedure ::= SEQUENCE
{
    failureCause                 [1] SCEFFailureCause,
    iMSI                         [2] IMSI OPTIONAL,
    mSISDN                       [3] MSISDN OPTIONAL,
    externalIdentifier           [4] NAI OPTIONAL,
    ePSBearerID                  [5] EPSBearerID,
    aPN                          [6] APN,
    rDSDestinationPortNumber     [7] RDSPortNumber OPTIONAL,
    applicationID                [8] ApplicationID OPTIONAL,
    sCSASID                      [9] SCSASID
}

-- See clause 7.8.2.1.6 for details of this structure
SCEFStartOfInterceptionWithEstablishedPDNConnection ::= SEQUENCE
{
    iMSI                  [1] IMSI OPTIONAL,
    mSISDN                [2] MSISDN OPTIONAL,
    externalIdentifier    [3] NAI OPTIONAL,
    iMEI                  [4] IMEI OPTIONAL,
    ePSBearerID           [5] EPSBearerID,
    sCEFID                [6] SCEFID,
    aPN                   [7] APN,
    rDSSupport            [8] RDSSupport,
    sCSASID               [9] SCSASID
}

-- See clause 7.8.3.1.1 for details of this structure
SCEFDeviceTrigger ::= SEQUENCE
{
    iMSI                  [1] IMSI,
    mSISDN                [2] MSISDN,
    externalIdentifier    [3] NAI,
    triggerId             [4] TriggerID,
    sCSASID               [5] SCSASID OPTIONAL,
    triggerPayload        [6] TriggerPayload OPTIONAL,
    validityPeriod        [7] INTEGER OPTIONAL,
    priorityDT            [8] PriorityDT OPTIONAL,
    sourcePortId          [9] PortNumber OPTIONAL,
    destinationPortId     [10] PortNumber OPTIONAL
}

-- See clause 7.8.3.1.2 for details of this structure
SCEFDeviceTriggerReplace ::= SEQUENCE
{
    iMSI                     [1] IMSI OPTIONAL,
    mSISDN                   [2] MSISDN OPTIONAL,
    externalIdentifier       [3] NAI OPTIONAL,
    triggerId                [4] TriggerID,
    sCSASID                  [5] SCSASID OPTIONAL,
    triggerPayload           [6] TriggerPayload OPTIONAL,
    validityPeriod           [7] INTEGER OPTIONAL,
    priorityDT               [8] PriorityDT OPTIONAL,
    sourcePortId             [9] PortNumber OPTIONAL,
    destinationPortId        [10] PortNumber OPTIONAL
}

-- See clause 7.8.3.1.3 for details of this structure
SCEFDeviceTriggerCancellation ::= SEQUENCE
{
    iMSI                     [1] IMSI OPTIONAL,
    mSISDN                   [2] MSISDN OPTIONAL,
    externalIdentifier       [3] NAI OPTIONAL,
    triggerId                [4] TriggerID
}

-- See clause 7.8.3.1.4 for details of this structure
SCEFDeviceTriggerReportNotify ::= SEQUENCE
{
    iMSI                             [1] IMSI OPTIONAL,
    mSISDN                           [2] MSISDN OPTIONAL,
    externalIdentifier               [3] NAI OPTIONAL,
    triggerId                        [4] TriggerID,
    deviceTriggerDeliveryResult      [5] DeviceTriggerDeliveryResult
}

-- See clause 7.8.4.1.1 for details of this structure
SCEFMSISDNLessMOSMS ::= SEQUENCE
{
    iMSI                      [1] IMSI OPTIONAL,
    mSISDN                    [2] MSISDN OPTIONAL,
    externalIdentifie         [3] NAI OPTIONAL,
    terminatingSMSParty       [4] SCSASID,
    sMS                       [5] SMSTPDUData OPTIONAL,
    sourcePort                [6] PortNumber OPTIONAL,
    destinationPort           [7] PortNumber OPTIONAL
}

-- See clause 7.8.5.1.1 for details of this structure
SCEFCommunicationPatternUpdate ::= SEQUENCE
{
    mSISDN                                [1] MSISDN OPTIONAL,
    externalIdentifier                    [2] NAI OPTIONAL,
    periodicCommunicationIndicator        [3] PeriodicCommunicationIndicator OPTIONAL,
    communicationDurationTime             [4] INTEGER OPTIONAL,
    periodicTime                          [5] INTEGER OPTIONAL,
    scheduledCommunicationTime            [6] ScheduledCommunicationTime OPTIONAL,
    scheduledCommunicationType            [7] ScheduledCommunicationType OPTIONAL,
    stationaryIndication                  [8] StationaryIndication OPTIONAL,
    batteryIndication                     [9] BatteryIndication OPTIONAL,
    trafficProfile                        [10] TrafficProfile OPTIONAL,
    expectedUEMovingTrajectory            [11] SEQUENCE OF UMTLocationArea5G OPTIONAL,
    sCSASID                               [13] SCSASID,
    validityTime                          [14] Timestamp OPTIONAL
}

-- See clause 7.8.6.1.2 for details of this structure
SCEFASSessionWithQoSProvision ::= SEQUENCE
{
    mSISDN                               [1] MSISDN OPTIONAL,
    externalIdentifier                   [2] NAI OPTIONAL,
    sCSASID                              [3] SCSASID,
    aSSessionWithQoSOpType               [4] AForASSessionWithQoSOpType,
    aSSessionWithQoSSubscription         [5] SBIType OPTIONAL,
    aSSessionWithQoSSubscriptionPatch    [6] SBIType OPTIONAL,
    aSSessionWithQoSResponseCode         [7] AForASSessionWithQoSResponseCode
}

-- See clause 7.8.6.1.3 for details of this structure
SCEFASSessionWithQoSNotification ::= SEQUENCE
{
    mSISDN                               [1] MSISDN OPTIONAL,
    externalIdentifier                   [2] NAI OPTIONAL,
    sCSASID                              [3] SCSASID,
    userPlaneNotificationData            [4] SBIType,
    aSSessionWithQoSResponseCode         [5] AForASSessionWithQoSResponseCode
}

-- =================
-- SCEF parameters
-- =================

SCEFFailureCause ::= ENUMERATED
{
    userUnknown(1),
    niddConfigurationNotAvailable(2),
    invalidEPSBearer(3),
    operationNotAllowed(4),
    portNotFree(5),
    portNotAssociatedWithSpecifiedApplication(6)
}

SCEFReleaseCause ::= ENUMERATED
{
    mMERelease(1),
    dNRelease(2),
    hSSRelease(3),
    localConfigurationPolicy(4),
    unknownCause(5)
}

SCSASID ::= UTF8String

SCEFID ::= UTF8String

EPSBearerID ::= INTEGER (0..255)

APN ::= UTF8String

-- =======================
-- AKMA AAnF definitions
-- =======================

AAnFAnchorKeyRegister ::= SEQUENCE
{
    aKID                  [1] NAI,
    sUPI                  [2] SUPI,
    kAKMA                 [3] KAKMA OPTIONAL
}

AAnFKAKMAApplicationKeyGet ::= SEQUENCE
{
    type                  [1] KeyGetType,
    aKID                  [2] NAI,
    keyInfo               [3] AFKeyInfo
}

AAnFStartOfInterceptWithEstablishedAKMAKeyMaterial ::= SEQUENCE
{
    aKID                  [1] NAI,
    kAKMA                 [2] KAKMA OPTIONAL,
    aFKeyList             [3] SEQUENCE OF AFKeyInfo OPTIONAL
}

AAnFAKMAContextRemovalRecord ::= SEQUENCE
{
    aKID                  [1] NAI,
    nFID                  [2] NFID
}

-- ======================
-- AKMA common parameters
-- ======================

FQDN ::= UTF8String

NFID ::= UTF8String

UAProtocolID ::= OCTET STRING (SIZE(5))

AKMAAFID ::= SEQUENCE
{
    aFFQDN                [1] FQDN,
    uaProtocolID          [2] UAProtocolID
}

UAStarParams ::= CHOICE
{
    tls12                 [1] TLS12UAStarParams,
    generic               [2] GenericUAStarParams,
    tls13                 [3] TLS13UAStarParams,
    dtls12                [4] DTLS12UAStarParams,
    dtls13                [5] DTLS13UAStarParams
}

GenericUAStarParams ::= SEQUENCE
{
    genericClientParams [1] OCTET STRING,
    genericServerParams [2] OCTET STRING
}

-- ===========================================
-- Specific UaStarParams for TLS 1.2 (RFC5246)
-- ===========================================

TLSCipherType ::= ENUMERATED
{
    stream(1),
    block(2),
    aead(3)
}

TLSCompressionAlgorithm ::= ENUMERATED
{
    null(1),
    deflate(2)
}

TLSPRFAlgorithm ::= ENUMERATED
{
    rfc5246(1)
}

TLSCipherSuite ::= SEQUENCE (SIZE(2)) OF INTEGER (0..255)

TLS12UAStarParams ::= SEQUENCE
{
    preMasterSecret       [1] OCTET STRING (SIZE(48)) OPTIONAL,
    masterSecret          [2] OCTET STRING (SIZE(48)),
    pRFAlgorithm          [3] TLSPRFAlgorithm,
    cipherSuite           [4] TLSCipherSuite,
    cipherType            [5] TLSCipherType,
    encKeyLength          [6] INTEGER (0..255),
    blockLength           [7] INTEGER (0..255),
    fixedIVLength         [8] INTEGER (0..255),
    recordIVLength        [9] INTEGER (0..255),
    macLength             [10] INTEGER (0..255),
    macKeyLength          [11] INTEGER (0..255),
    compressionAlgorithm  [12] TLSCompressionAlgorithm,
    clientRandom          [13] OCTET STRING (SIZE(32)),
    serverRandom          [14] OCTET STRING (SIZE(32)),
    clientSequenceNumber  [15] INTEGER,
    serverSequenceNumber  [16] INTEGER,
    sessionID             [17] OCTET STRING (SIZE(0..32)),
    tLSServerExtensions   [18] OCTET STRING (SIZE(0..65535)),
    tLSClientExtensions   [19] OCTET STRING (SIZE(0..65535)) OPTIONAL
}

-- ==================================================
-- Specific UaStarParams for DTLS 1.2 (RFC6347)
-- Inline references below are to clauses of RFC6347.
-- ==================================================

DTLS12UAStarParams ::= SEQUENCE
{
    tLS12CommonParams [1] TLS12UAStarParams,
    -- RFC 6347 [144] clause 4.1
    clientEpoch       [2] INTEGER,
    -- RFC 6347 [144] clause 4.1
    serverEpoch       [3] INTEGER,
    -- RFC 9146 [145]
    connectionID      [4] OCTET STRING (SIZE(0..255)) OPTIONAL
}

-- ==================================================
-- Specific UaStarParams for TLS 1.3 (RFC8446)
-- Inline references below are to clauses of RFC8446.
-- ==================================================

-- RFC8846, clause 4.2: Available handshake extension types.

TLS13ExtensionType ::= ENUMERATED
{
        serverName(1),
        maxFragmentLength(2),
        statusRequest(3),
        supportedGroups(4),
        signatureAlgorithms(5),
        useSRTP(6),
        heartbeat(7),
        applicationLayerProtocolNegotiation(8),
        signedCertificateTimestamp(9),
        clientCertificateType(10),
        serverCertificateType(11),
        padding(12),
        presharedKey(13),
        earlyData(14),
        supportedVersions(15),
        cookie(16),
        pSKKeyExchangeModes(17),
        certificateAuthorities(18),
        oIDFilters(19),
        postHandshakeAuth(20),
        signatureAlgorithmsCert(21),
        keyShare(22)
}

-- RFC8846, clause 4.2: Extensions.
-- Carried as extension to the client's and server's
-- Hello, or, in the server's EncryptedExtensions message.
TLS13Extension ::= SEQUENCE
{
    extensionType [1] TLS13ExtensionType,
    extensionData [2] OCTET STRING (SIZE(0..65535))
}


-- RFC8446, clauses 4.1, 4.2, 7.1, and B.4: Cryptographic transforms

-- RFC8446, clauses 4.1.1 and 4.1.2: Ciphersuite
TLS13CipherSuite ::= CHOICE
{
    rfc8446               [1] TLSCipherSuite
    -- Extensible for possible future purposes
}

-- RFC8446, clause 7.1 and B.4: Key derivation function.
TLS13KDFAlgorithm ::= ENUMERATED
{
    rfc5869(1)     -- HKDF
}

-- RFC8846, clause 4.2.11 and B.4: Hash algorithm.
TLS13PSKHashAlgorithm ::= ENUMERATED
{
    sha256(1),
    sha384(2),
    sha512(3)
}


-- RFC8446, clause 4.4.2: Certificates.

TLS13CertificateType ::= ENUMERATED
{
    x509(1),
    rawPublicKey(2)
}

TLS13CerificateEntry ::= SEQUENCE
{
    tLSCertificateType [1] TLS13CertificateType,
    tLSCertificateData [2] OCTET STRING (SIZE(1..16777215)),
    extensions         [3] SEQUENCE OF TLS13Extension OPTIONAL
}

-- This will typically correspond to a certificate chain.
TLS13Certificate ::= SEQUENCE
{
    tLSCertificateRequestContext [1] OCTET STRING (SIZE(0..255)),
    tLSCertificateList           [2] SEQUENCE OF TLS13CerificateEntry
}


-- RFC 8446, clause 4.2.9: Preshared key exchange mode.
TLS13PSKKeyExchangeMode ::= ENUMERATED
{
    pSKKE(1),
    pSKDHEKE(2)
}

-- RFC8446, clause 4.2.11: Preshared keys (PSKs).
-- PSKs obtained from AKMA use a specific prefix as part
-- of the identity: 3GPP-AKMA, see TS 33.535 and 33.222.
TLS13PSKIdentity ::= SEQUENCE
{
    identity            [1] OCTET STRING (SIZE(1..65535)),
    obfuscatedTicketAge [2] INTEGER (0..4294967295)
}

TLS13OfferedPSK ::= SEQUENCE
{
    identity [1] TLS13PSKIdentity,
    binder   [2] OCTET STRING (SIZE(32..255))
}

-- Actual TLS PSK, either explicitly provisioned or derived from
-- an earlier issued TLS ticket and a resumptionMasterSecret.
-- For AKMA, the PSK is the AKMA key K_AF.
TLS13PSKInfo ::= SEQUENCE
{
    pSKIdentity        [1] TLS13PSKIdentity,
    pSKValue           [2] OCTET STRING,
    pSKKeyExchangeMode [3] TLS13PSKKeyExchangeMode,
    hashAlgorithm      [4] TLS13PSKHashAlgorithm
}



-- RFC 8446, clause 4.6.1: Tickets/resumption info.

TLS13NewSessionTicket ::= SEQUENCE
{
    ticketLifeTime [1] INTEGER (0..4294967295),
    ticketAgeAdd   [2] INTEGER (0..4294967295),
    ticketNonce    [3] OCTET STRING (SIZE(0..255)),
    ticket         [4] OCTET STRING (SIZE(1..65535)),
    extensions     [5] SEQUENCE OF TLS13Extension OPTIONAL
}



-- RFC8446, clause 7.1 and 4.2.8: TLS-internal keys
-- These keys/secrets are never directly used to encrypt
-- data, and are therefore optional to provide as part of
-- TLS13UAStarParams.

-- RFC8446, clause 4.2.8
-- Shared Diffie-Hellman secret: derived from client's
-- and server's key shares (as included in extensions).
-- Can later be extended by adding PQC-based secrets,
-- see e.g. draft-ietf-tls-hybrid-design-10.
TLS13EstablishedSecrets ::= SEQUENCE
{
    dHE           [1] OCTET STRING (SIZE(1..65535)) OPTIONAL
}


-- RFC8446, clause 7.1
-- The actual encryption keys are derived from the respective secret
-- values below and the provided hashed handshake-message-transcript.
TLS13EarlySecretInfo ::= SEQUENCE
{
    earlySecretValue [1] OCTET STRING (SIZE(1..65535)),
    transcriptHash   [2] OCTET STRING (SIZE(1..65535))
    -- Hash(ClientHello)
}

TLS13HandshakeSecretInfo ::= SEQUENCE
{
    handshakeSecretValue [1] OCTET STRING (SIZE(1..65535)),
    transcriptHash       [2] OCTET STRING (SIZE(1..65535))
    -- Hash(ClientHello..ServerHello)
}

TLS13MasterSecretInfo ::= SEQUENCE
{
    masterSecretValue [1] OCTET STRING (SIZE(1..65535)),
    transcriptHashS   [2] OCTET STRING (SIZE(1..65535)),
    -- Hash(ClientHello..server Finished)
    transcriptHashC   [3] OCTET STRING (SIZE(1..65535))
    -- Hash(ClientHello..client Finished)
}


-- Complete TLS 1.3 cryptographic context.

TLS13UAStarParams ::= SEQUENCE
{
    -- Basic cryptographic information.
    --
    -- The offeredPSKs, offeredPSKModes and selectedPSK
    -- parameters are also provided as part of client and
    -- server extensions below.
    --
    -- PSKs and key exchange modes offered by the client, see
    -- clause 4.2.9, 4.2.11. When AKMA (or other CSP-provided)
    -- keys are used, at least one offered PSK and key exchange mode
    -- will always be present in the client extensions
    offeredPSKs                      [1] SEQUENCE OF TLS13OfferedPSK,
    offeredPSKKeyExchangeModes       [2] SEQUENCE OF TLS13PSKKeyExchangeMode,
    -- The server-selected PSK, clause 4.2.11
    -- selectedPSKIdentity = j means the server selects j:th offered PSK.
    selectedPSKIdentity              [3] INTEGER (0..65535),
    -- The actual TLS PSK. When AKMA is used, this key will typically also
    -- be provided as an associated AFKeyInfo IRI, see below.
    selectedPSK                      [4] TLS13PSKInfo,
    -- Cryptographic state: transforms and sequence numbers.
    kDFAlgorithm                     [5] TLS13KDFAlgorithm, -- clause 7.1.
    clientSupportedCipherSuites      [6] SEQUENCE OF TLS13CipherSuite OPTIONAL,
    selectedCipherSuite              [7] TLS13CipherSuite, -- clause 4.2 and B.4.
    clientSequenceNumber             [8] INTEGER, -- clause 5.3
    serverSequenceNumber             [9] INTEGER, -- clause 5.3
    -- Handshake parameters, clause 4.1.2 and 4.1.3.
    clientRandom                    [10] OCTET STRING (SIZE(32)),
    serverRandom                    [11] OCTET STRING (SIZE(32)),
    legacySessionID                 [12] OCTET STRING (SIZE(0..32)),
    -- Complete contents of handshake extensions, clause 4.2.
    tLSClientHelloExtensions        [13] SEQUENCE OF TLS13Extension,
    tLSServerHelloExtensions        [14] SEQUENCE OF TLS13Extension,
    -- Encrypted server extensions, clause 4.3.1 (here provided in plaintext).
    tLSPlaintextEncryptedExtensions [15] SEQUENCE OF TLS13Extension OPTIONAL,
    -- Authentication related parameters, clause 4.4
    -- Certificates are encrypted between client and server,
    -- these are the unencrypted certificate(s).
    tLSPlaintextClientCertificate   [16] TLS13Certificate OPTIONAL,
    tLSPlaintextServerCertificate   [17] TLS13Certificate OPTIONAL,
    -- Session key information fields, clause 7.1
    earlySecret                     [18] TLS13EarlySecretInfo OPTIONAL,
    binderKey                       [19] OCTET STRING (SIZE(1..65535)) OPTIONAL,
    -- The key used by the cipher suite to encrypt early data is
    -- derived from clientEarlyTrafficSecret as described in clause 7.3.
    clientEarlyTrafficSecret        [20] OCTET STRING (SIZE(1..65535)),
    earlyExporterMasterSecret       [21] OCTET STRING (SIZE(1..65535)),
    -- Established shared key (from Diffie-Hellman or similar).
    sharedKey                       [22] TLS13EstablishedSecrets OPTIONAL,
    handshakeSecret                 [23] TLS13HandshakeSecretInfo OPTIONAL,
    -- The keys used by the cipher suite to encrypt the handshake are
    -- derived from client- and serverHandshakeTrafficSecret as
    -- described in clause 7.3.
    clientHandshakeTrafficSecret    [24] OCTET STRING (SIZE(1..65535)),
    serverHandshakeTrafficSecret    [25] OCTET STRING (SIZE(1..65535)),
    masterSecret                    [26] TLS13MasterSecretInfo OPTIONAL,
    -- The client and server application traffic secrets
    -- can change value during an ongoing session due to
    -- KeyUdpateRequest messages. The values to be provided below
    -- refer to the currently valid ones when the IRI message is
    -- generated.
    -- The keys used by the cipher suite to encrypt the application
    -- traffic are derived from client- and serverApplicationTrafficSecret
    -- as described in clause 7.3.
    clientApplicationTrafficSecret  [27] OCTET STRING (SIZE(1..65535)),
    serverApplicationTrafficSecret  [28] OCTET STRING (SIZE(1..65535)),
    -- Other session-specific keys.
    exporterMasterSecret            [29] OCTET STRING (SIZE(1..65535)),
    resumptionMasterSecret          [30] OCTET STRING (SIZE(1..65535)),
    -- Tickets for resumption (issued during current session), clause 4.6.2.
    tLSResumptionTickets            [31] SEQUENCE OF TLS13NewSessionTicket OPTIONAL
}

-- =====================================================
-- Specific UaStarParams for DTLS 1.3 (RFC9147)
-- Inline references below are to clauses of RFC9147.
-- The client/server SnKey can alternatively be
-- derived from information carried in tLS13CommonParams
-- =====================================================

DTLS13UAStarParams ::= SEQUENCE
{
    tLS13CommonParams [1] TLS13UAStarParams,
    -- RFC9147 [146] clause 4.2
    clientEpoch       [2] INTEGER,
    -- RFC9147 [146] clause 4.2
    serverEpoch       [3] INTEGER,
    -- RFC9147 [146] clause 4.2.3
    clientSnKey       [4] OCTET STRING (SIZE(1..65535)) OPTIONAL,
    -- RFC9147 [146] clause 4.2.3
    serverSnKey       [5] OCTET STRING (SIZE(1..65535)) OPTIONAL,
    -- RFC9146 [145]
    connectionID      [6] OCTET STRING (SIZE(0..255)) OPTIONAL
}

KAF ::= OCTET STRING

KAKMA ::= OCTET STRING

-- ====================
-- AKMA AAnF parameters
-- ====================

KeyGetType ::= ENUMERATED
{
    internal(1),
    external(2)
}

AFKeyInfo ::= SEQUENCE
{
    aFID                 [1] AKMAAFID,
    kAF                  [2] KAF,
    kAFExpTime           [3] KAFExpiryTime
}

-- =======================
-- AKMA AF definitions
-- =======================

AFAKMAApplicationKeyRefresh ::= SEQUENCE
{
    aFID                  [1] AFID,
    aKID                  [2] NAI,
    kAF                   [3] KAF,
    uaStarParams          [4] UAStarParams OPTIONAL
}

AFStartOfInterceptWithEstablishedAKMAApplicationKey ::= SEQUENCE
{
    aFID                  [1] FQDN,
    aKID                  [2] NAI,
    kAFParamList          [3] SEQUENCE OF AFSecurityParams
}

AFAuxiliarySecurityParameterEstablishment ::= SEQUENCE
{
    aFSecurityParams      [1] AFSecurityParams
}

AFSecurityParams ::= SEQUENCE
{
    aFID                  [1] AFID,
    aKID                  [2] NAI,
    kAF                   [3] KAF,
    uaStarParams          [4] UAStarParams
}

AFApplicationKeyRemoval ::= SEQUENCE
{
    aFID                  [1] AFID,
    aKID                  [2] NAI,
    removalCause          [3] AFKeyRemovalCause
}

-- ===================
-- AKMA AF parameters
-- ===================

KAFParams ::= SEQUENCE
{
    aKID                 [1] NAI,
    kAF                  [2] KAF,
    kAFExpTime           [3] KAFExpiryTime,
    uaStarParams         [4] UAStarParams
}

KAFExpiryTime ::= GeneralizedTime

AFKeyRemovalCause ::= ENUMERATED
{
    unknown(1),
    keyExpiry(2),
    applicationSpecific(3)
}

-- ==================
-- 5G AMF definitions
-- ==================

-- See clause 6.2.2.2.2 for details of this structure
AMFRegistration ::= SEQUENCE
{
    registrationType                [1] AMFRegistrationType,
    registrationResult              [2] AMFRegistrationResult,
    slice                           [3] Slice OPTIONAL,
    sUPI                            [4] SUPI,
    sUCI                            [5] SUCI OPTIONAL,
    pEI                             [6] PEI OPTIONAL,
    gPSI                            [7] GPSI OPTIONAL,
    gUTI                            [8] FiveGGUTI,
    location                        [9] Location OPTIONAL,
    non3GPPAccessEndpoint           [10] UEEndpointAddress OPTIONAL,
    fiveGSTAIList                   [11] TAIList OPTIONAL,
    sMSOverNasIndicator             [12] SMSOverNASIndicator OPTIONAL,
    oldGUTI                         [13] EPS5GGUTI OPTIONAL,
    eMM5GRegStatus                  [14] EMM5GMMStatus OPTIONAL,
    nonIMEISVPEI                    [15] NonIMEISVPEI OPTIONAL,
    mACRestIndicator                [16] MACRestrictionIndicator OPTIONAL,
    pagingRestrictionIndicator      [17] PagingRestrictionIndicator OPTIONAL,
    rATType                         [18] RATType OPTIONAL,
    rRCEstablishmentCause           [19] RRCEstablishmentCause OPTIONAL,
    deprecatedNGInformation         [20] NGInformation OPTIONAL,
    nASTransportInitialInformation  [21] NASTransportInitialInformation OPTIONAL,
    sORTransparentContainer         [22] SORTransparentContainer OPTIONAL,
    equivalentPLMNList              [23] PLMNList OPTIONAL,
    fiveGMMCapability               [24] FiveGMMCapability OPTIONAL,
    initialRANUEContextSetup        [25] InitialRANUEContextSetup OPTIONAL,
    mUSIMUERequestType              [26] MUSIMUERequestType OPTIONAL,
    unavailabilityPeriodDuration    [27] UnavailabilityPeriodDuration OPTIONAL,
    fiveGSUpdateType                [28] FiveGSUpdateType OPTIONAL,
    uEAreaIndication                [29] UEAreaIndication OPTIONAL,
    establishmentCauseNon3GPPAccess [30] EstablishmentCauseNon3GPPAccess OPTIONAL,
    additionalUserIdentifiers       [31] UserIdentifiers OPTIONAL
}

-- See clause 6.2.2.2.3 for details of this structure
AMFDeregistration ::= SEQUENCE
{
    deregistrationDirection       [1] AMFDirection,
    accessType                    [2] AccessType,
    sUPI                          [3] SUPI OPTIONAL,
    sUCI                          [4] SUCI OPTIONAL,
    pEI                           [5] PEI OPTIONAL,
    gPSI                          [6] GPSI OPTIONAL,
    gUTI                          [7] FiveGGUTI OPTIONAL,
    cause                         [8] FiveGMMCause OPTIONAL,
    location                      [9] Location OPTIONAL,
    switchOffIndicator            [10] SwitchOffIndicator OPTIONAL,
    reRegRequiredIndicator        [11] ReRegRequiredIndicator OPTIONAL,
    unavailabilityPeriodDuration  [12] UnavailabilityPeriodDuration OPTIONAL,
    additionalUserIdentifiers     [13] UserIdentifiers OPTIONAL
}

-- See clause 6.2.2.2.4 for details of this structure
AMFLocationUpdate ::= SEQUENCE
{
    sUPI                            [1] SUPI,
    sUCI                            [2] SUCI OPTIONAL,
    pEI                             [3] PEI OPTIONAL,
    gPSI                            [4] GPSI OPTIONAL,
    gUTI                            [5] FiveGGUTI OPTIONAL,
    location                        [6] Location,
    deprecatedSMSOverNASIndicator   [7] SMSOverNASIndicator OPTIONAL,
    deprecatedOldGUTI               [8] EPS5GGUTI OPTIONAL,
    uEAreaIndication                [9] UEAreaIndication OPTIONAL,
    additionalUserIdentifiers       [10] UserIdentifiers OPTIONAL
}

-- See clause 6.2.2.2.5 for details of this structure
AMFStartOfInterceptionWithRegisteredUE ::= SEQUENCE
{
    registrationResult            [1] AMFRegistrationResult,
    registrationType              [2] AMFRegistrationType OPTIONAL,
    slice                         [3] Slice OPTIONAL,
    sUPI                          [4] SUPI,
    sUCI                          [5] SUCI OPTIONAL,
    pEI                           [6] PEI OPTIONAL,
    gPSI                          [7] GPSI OPTIONAL,
    gUTI                          [8] FiveGGUTI,
    location                      [9] Location OPTIONAL,
    non3GPPAccessEndpoint         [10] UEEndpointAddress OPTIONAL,
    timeOfRegistration            [11] Timestamp OPTIONAL,
    fiveGSTAIList                 [12] TAIList OPTIONAL,
    sMSOverNASIndicator           [13] SMSOverNASIndicator OPTIONAL,
    oldGUTI                       [14] EPS5GGUTI OPTIONAL,
    eMM5GRegStatus                [15] EMM5GMMStatus OPTIONAL,
    sORTransparentContainer       [16] SORTransparentContainer OPTIONAL,
    uEPolicy                      [17] UEPolicy OPTIONAL,
    unavailabilityPeriodDuration  [18] UnavailabilityPeriodDuration OPTIONAL,
    fiveGSUpdateType              [19] FiveGSUpdateType OPTIONAL,
    uEAreaIndication              [20] UEAreaIndication OPTIONAL,
    additionalUserIdentifiers     [21] UserIdentifiers OPTIONAL
}

-- See clause 6.2.2.2.6 for details of this structure
AMFUnsuccessfulProcedure ::= SEQUENCE
{
    failedProcedureType         [1] AMFFailedProcedureType,
    failureCause                [2] AMFFailureCause,
    requestedSlice              [3] NSSAI OPTIONAL,
    sUPI                        [4] SUPI OPTIONAL,
    sUCI                        [5] SUCI OPTIONAL,
    pEI                         [6] PEI OPTIONAL,
    gPSI                        [7] GPSI OPTIONAL,
    gUTI                        [8] FiveGGUTI OPTIONAL,
    location                    [9] Location OPTIONAL,
    additionalUserIdentifiers   [10] UserIdentifiers OPTIONAL
}

-- See clause 6.2.2.2.8 on for details of this structure
AMFPositioningInfoTransfer ::= SEQUENCE
{
    sUPI                        [1] SUPI,
    sUCI                        [2] SUCI OPTIONAL,
    pEI                         [3] PEI OPTIONAL,
    gPSI                        [4] GPSI OPTIONAL,
    gUTI                        [5] FiveGGUTI OPTIONAL,
    nRPPaMessage                [6] OCTET STRING OPTIONAL,
    lPPMessage                  [7] OCTET STRING OPTIONAL,
    lcsCorrelationId            [8] UTF8String (SIZE(1..255)),
    additionalUserIdentifiers   [9] UserIdentifiers OPTIONAL
}

-- See clause 6.2.2.2.9.2 for details of this structure
AMFRANHandoverCommand ::= SEQUENCE
{
    userIdentifiers              [1] UserIdentifiers,
    aMFUENGAPID                  [2] AMFUENGAPID,
    rANUENGAPID                  [3] RANUENGAPID,
    handoverType                 [4] HandoverType,
    targetToSourceContainer      [5] RANTargetToSourceContainer
}

-- See clause 6.2.2.2.9.3 for details of this structure
AMFRANHandoverRequest ::= SEQUENCE
{
    userIdentifiers                     [1] UserIdentifiers,
    aMFUENGAPID                         [2] AMFUENGAPID,
    rANUENGAPID                         [3] RANUENGAPID,
    handoverType                        [4] HandoverType,
    handoverCause                       [5] HandoverCause,
    pDUSessionResourceInformation       [6] PDUSessionResourceInformation,
    mobilityRestrictionList             [7] MobilityRestrictionList OPTIONAL,
    locationReportingRequestType        [8] LocationReportingRequestType OPTIONAL,
    targetToSourceContainer             [9] RANTargetToSourceContainer,
    nPNAccessInformation                [10] NPNAccessInformation OPTIONAL,
    sourceToTargetContainer             [11] RANSourceToTargetContainer
}

-- See clause 6.2.2.2.10 on for details of this structure
AMFUEConfigurationUpdate ::= SEQUENCE
{
    userIdentifiers     [1] UserIdentifiers,
    gUTI                [2] GUTI,
    oldGUTI             [3] EPS5GGUTI OPTIONAL,
    fiveGSTAIList       [4] TAIList OPTIONAL,
    slice               [5] Slice OPTIONAL,
    serviceAreaList     [6] ServiceAreaList OPTIONAL,
    registrationResult  [7] AMFRegistrationResult OPTIONAL,
    sMSOverNASIndicator [8] SMSOverNASIndicator OPTIONAL
}

-- See clause 6.2.2.2.10.2 for details of this structure
AMFRANTraceReport ::= SEQUENCE
{
    userIdentifiers               [1] UserIdentifiers,
    aMFUENGAPID                   [2] AMFUENGAPID,
    rANUENGAPID                   [3] RANUENGAPID,
    traceRecordType               [4] TraceRecordType,
    traceDirection                [5] TraceDirection,
    -- deprecatedTraceActivationInfo was deprecated in r18(18) version6(6) and shall not be reused.
    deprecatedTraceActivationInfo [6] TraceActivationInfo OPTIONAL,
    nGRANCGI                      [7] NCGI,
    globalRANNodeID               [8] GlobalRANNodeID,
    traceCollectionEntityInfo     [9] TraceCollectionEntityInfo OPTIONAL,
    aMFTraceData                  [10] XMLType,
    location                      [11] Location OPTIONAL,
    traceActivation               [12] TraceActivation OPTIONAL
}

-- See clause 6.2.2.2.12 for details of this Structure
AMFUEPolicyTransfer ::= SEQUENCE
{
    sUPI                            [1] SUPI,
    sUCI                            [2] SUCI OPTIONAL,
    pEI                             [3] PEI OPTIONAL,
    gPSI                            [4] GPSI OPTIONAL,
    gUTI                            [5] FiveGGUTI OPTIONAL,
    uEPolicy                        [6] UEPolicy
}

-- See clause 6.2.2.2.13 for details of this structure
AMFUEServiceAccept ::= SEQUENCE
{
    userIdentifiers                [1] UserIdentifiers,
    serviceMessageIdentity         [2] ServiceMessageIdentity,
    serviceType                    [3] OCTET STRING (SIZE(1)) OPTIONAL,
    fiveGTMSI                      [4] FiveGTMSI OPTIONAL,
    uplinkDataStatus               [5] OCTET STRING (SIZE(2..32)) OPTIONAL,
    pDUSessionStatus               [6] OCTET STRING (SIZE(2..32)) OPTIONAL,
    -- deprecatedUERequestType was deprecated in r18(18) version6(6) and shall not be reused.
    deprecatedUERequestType        [7] FiveGSMRequestType OPTIONAL,
    pagingRestriction              [8] PagingRestrictionIndicator OPTIONAL,
    forbiddenTAIList               [9] TAIList OPTIONAL,
    uERequestType                  [10] MUSIMUERequestType OPTIONAL
}

-- See clause 6.2.2.2.14 for details of this structure
AMFUEContextUpdate ::= SEQUENCE
{
    userIdentifiers          [1] UserIdentifiers,
    rANUEContextModification [2] RANUEContextModification OPTIONAL,
    rANDownlinkNASTransport  [3] RANDownlinkNASTransport OPTIONAL
}

-- =================
-- 5G AMF parameters
-- =================

AMFID ::= SEQUENCE
{
    aMFRegionID [1] AMFRegionID,
    aMFSetID    [2] AMFSetID,
    aMFPointer  [3] AMFPointer
}

AMFDirection ::= ENUMERATED
{
    networkInitiated(1),
    uEInitiated(2)
}

AMFFailedProcedureType ::= ENUMERATED
{
    registration(1),
    sMS(2),
    pDUSessionEstablishment(3)
}

AMFFailureCause ::= CHOICE
{
    fiveGMMCause        [1] FiveGMMCause,
    fiveGSMCause        [2] FiveGSMCause
}

AMFPointer ::= INTEGER (0..63)

AMFRegistrationResult ::= ENUMERATED
{
    threeGPPAccess(1),
    nonThreeGPPAccess(2),
    threeGPPAndNonThreeGPPAccess(3)
}

AMFRegionID ::= INTEGER (0..255)

AMFRegistrationType ::= ENUMERATED
{
    initial(1),
    mobility(2),
    periodic(3),
    emergency(4),
    sNPNOnboarding(5),
    disasterMobility(6),
    disasterInitial(7)
}

AMFSetID ::= INTEGER (0..1023)

AMFUENGAPID ::= INTEGER (0..1099511627775)

AreaScopeOfMDT ::= CHOICE
{
    cellBased         [1] SEQUENCE (SIZE(1..MAX)) OF CellID,
    tABased           [2] SEQUENCE (SIZE(1..MAX)) OF TAC,
    pLMNWide          [3] PLMNID,
    tAIBased          [4] SEQUENCE (SIZE(1..MAX)) OF TAI
}

-- TS 24.502 clause 9.2.2, omitting the first octet
EstablishmentCauseNon3GPPAccess ::= OCTET STRING

MDTActivation ::= ENUMERATED
{
    immediateMDTOnly(1),
    loggedMDTOnly(2),
    immediateMDTandTrace(3)
}

MDTConfiguration ::= ENUMERATED
{
    mDTConfigurationNR(1),
    mDTConfigurationEUTRA(2)
}

MDTConfigurationEUTRA ::= SEQUENCE
{
    mDTActivation                [1] MDTActivation,
    areaScopeofMDT               [2] AreaScopeOfMDT,
    mDTMode                      [3] MDTMode,
    signallingBasedMDTPLMNList   [4] PLMNList
}

MDTConfigurationNR ::= SEQUENCE
{
    mDTActivation                 [1] MDTActivation,
    areaScopeofMDT                [2] AreaScopeOfMDT,
    mDTModeNR                     [3] MDTMode,
    signallingBasedMDTPLMNList    [4] PLMNList
}

-- TS 38.413 [23], clause 9.3.1.169
MDTMode ::= CHOICE
{
    immediateMDT      [1] OCTET STRING,
    loggedMDT         [2] OCTET STRING
}

-- TS 24.501 [13], clause 9.11.3.49
ServiceAreaList ::= OCTET STRING (SIZE(4..112))

ServiceMessageIdentity ::= CHOICE
{
    serviceRequest    [1] OCTET STRING,
    serviceAccept     [2] OCTET STRING
}

TraceActivation ::= ExternalASNType

-- The TraceActivationInfo type was deprecated in r18(18) version6(6) and shall not be reused.
-- The TraceActivation type shall be used instead.
TraceActivationInfo ::= SEQUENCE
{
    nGRANTraceID                     [1] OCTET STRING (SIZE(8)),
    interfacestoTrace                [2] BIT STRING (SIZE(8)),
    traceDepth                       [3] TraceDepth,
    traceCollectionEntityIPAddress   [4] IPAddress,
    mDTConfiguration                 [5] MDTConfiguration OPTIONAL
}

TraceCollectionEntityInfo ::= SEQUENCE
{
    traceCollectionEntityIPAddress   [1] BIT STRING (SIZE(1..160, ...)),
    traceCollectionEntityURI         [2] UTF8String
}

-- TS 32.423 [112], clause 5.3
TraceDepth ::= ENUMERATED
{
    minimum(1),
    medium(2),
    maximum(3),
    minimumWithoutVendorSpecificExtension(4),
    mediumWithoutVendorSpecificExtension(5),
    maximumWithoutVendorSpecificExtension(6)
}

TraceDirection ::= ENUMERATED
{
    toAMF(1),
    fromAMF(2),
    toMME(3),
    fromMME(4)
}

TraceRecordType ::= ENUMERATED
{
    traceStart(1),
    cellTrafficTrace(2),
    traceDataDelivery(3),
    traceDeactivation(4)
}

NASTransportInitialInformation ::= SEQUENCE
{
    rANUENGAPID             [1] RANUENGAPID,
    iABNodeIndication       [2] BOOLEAN OPTIONAL,
    eDTSession              [3] BOOLEAN OPTIONAL,
    authenticatedIndication [4] BOOLEAN OPTIONAL,
    nPNAccessInformation    [5] CellCAGList OPTIONAL,
    rEDCAPIndication        [6] REDCAPIndication OPTIONAL,
    mobileIABNodeIndication [7] BOOLEAN OPTIONAL
}

NGInformation ::= SEQUENCE
{
    globalRANNodeID        [1] GlobalRANNodeID,
    rANNodeName            [2] RANNodeName OPTIONAL,
    supportedTAList        [3] SupportedTAList OPTIONAL,
    extendedRANNodeName    [4] RANNodeName OPTIONAL,
    pLMNSupportList        [5] PLMNSupportList,
    iABSupported           [6] BOOLEAN OPTIONAL
}

PLMNSupportList ::= SEQUENCE (SIZE(1..MAX)) OF PLMNSupportItem

PLMNSupportItem ::= SEQUENCE
{
    pLMNIdentity        [1] PLMNID,
    nPNSupport          [2] NID OPTIONAL,
    onboardingSupport   [3] BOOLEAN OPTIONAL
}

F1Information ::= SEQUENCE
{
    gNBDUID            [1] INTEGER (0..68719476735),
    gNBDUName          [2] UTF8String OPTIONAL,
    gNBCUName          [3] UTF8String OPTIONAL,
    gNBDUServedCells   [4] SEQUENCE (SIZE(1..MAX)) OF RANCGI,
    extendedGNBDUName  [5] UTF8String OPTIONAL,
    extendedGNBCUName  [6] UTF8String OPTIONAL
}

REDCAPIndication ::= ENUMERATED
{
    redCAP(1)
}

RRCEstablishmentCause ::= CHOICE
{
    ePCEstablishmentCause    [1] EstablishmentCause,
    fiveGCEstablishmentCause [2] EstablishmentCause
}

EstablishmentCause ::= ENUMERATED
{
    emergency(1),
    highPriorityAccess(2),
    mtAccess(3),
    moSignalling(4),
    moData(5),
    moVoiceCall(6),
    moVideoCall(7),
    moSMS(8),
    mpsPriorityAccess(9),
    mcsPriorityAccess(10),
    notAvailable(11),
    exceptionData(12)
}

SORTransparentContainer ::= OCTET STRING (SIZE (17..65535))

UEPolicy ::= OCTET STRING (SIZE(16..65540))

InitialRANUEContextSetup ::= SEQUENCE
{
    aMFUENGAPID                          [1] AMFUENGAPID,
    rANUENGAPID                          [2] RANUENGAPID,
    oldAMF                               [3] GUAMI OPTIONAL,
    pDUSessionSetupRequest               [4] SEQUENCE (SIZE(1..MAX)) OF PDUSessionSetupRequestItem,
    allowedNSSAI                         [5] AllowedNSSAI,
    mobilityRestrictionList              [6] MobilityRestrictionList OPTIONAL,
    uERadioCapability                    [7] UERadioCapability OPTIONAL,
    rATFrequencySelectionPriority        [8] RATFrequencySelectionPriority OPTIONAL,
    uERadioCapabilityForPaging           [9] UERadioCapabilityForPaging OPTIONAL,
    iABAuthorizedIndicator               [10] IABAuthorizedIndicator OPTIONAL,
    nRV2XServicesAuthorization           [11] NRV2XServicesAuthorization OPTIONAL,
    lTEV2XServiceAuthorization           [12] LTEV2XServiceAuthorization OPTIONAL,
    rGLevelWirelineAccessCharacteristics [13] OCTET STRING OPTIONAL,
    uERadioCapabilityID                  [14] OCTET STRING OPTIONAL,
    targetNSSAIInfo                      [15] TargetNSSAIInfo OPTIONAL,
    fiveGProSeAuthorizationIndication    [16] FiveGProSeAuthorizationIndication OPTIONAL,
    uEDifferentiationInfo                [17] UEDifferentiationInfo OPTIONAL,
    mobileIABAuthorizedIndicator         [18] MobileIABAuthorizedIndicator OPTIONAL
}

PDUSessionSetupRequestItem ::= SEQUENCE
{
    pDUSessionID [1] PDUSessionID,
    sNSSAI       [2] SNSSAI
}

UERadioCapability ::= SEQUENCE
{
    uERadioCapibilityNR    [1] OCTET STRING OPTIONAL,
    uERadioCapabilityEUTRA [2] OCTET STRING OPTIONAL
}

UERadioCapabilityForPaging ::= SEQUENCE
{
    uERadioCapabilityForPagingOfNR    [1] OCTET STRING OPTIONAL,
    uERadioCapabilityForPagingOfEUTRA [2] OCTET STRING OPTIONAL,
    uERadioCapabilityForPagingOfNBIoT [3] OCTET STRING OPTIONAL
}

NRV2XServicesAuthorization ::= SEQUENCE
{
    v2XVehicleUEAuthorizationIndicator    [1] V2XUEAuthorizationIndicator OPTIONAL,
    v2XPedestrianUEAuthorizationIndicator [2] V2XUEAuthorizationIndicator OPTIONAL
}

LTEV2XServiceAuthorization ::= SEQUENCE
{
    v2XVehicleUEAuthorizationIndicator    [1] V2XUEAuthorizationIndicator OPTIONAL,
    v2XPedestrianUEAuthorizationIndicator [2] V2XUEAuthorizationIndicator OPTIONAL
}

TargetNSSAIInfo ::= SEQUENCE
{
    targetSNSSAIList              [1] NSSAI,
    rATFrequencySelectionPriority [2] RATFrequencySelectionPriority
}

FiveGProSeAuthorizationIndication ::= SEQUENCE
{
    fiveGProSeDirectDiscovery     [1] FiveGProSeAuthorizationIndicator OPTIONAL,
    fiveGProSeDirectCommunication [2] FiveGProSeAuthorizationIndicator OPTIONAL,
    fiveGProSeL2UEToNetworkRelay  [3] FiveGProSeAuthorizationIndicator OPTIONAL,
    fiveGProSeL3UEToNetworkRelay  [4] FiveGProSeAuthorizationIndicator OPTIONAL,
    fiveGProSeL2RemoteUE          [5] FiveGProSeAuthorizationIndicator OPTIONAL
}

IABAuthorizedIndicator ::= ENUMERATED
{
    authorized(1),
    notAuthorized(2)
}

V2XUEAuthorizationIndicator ::= ENUMERATED
{
    authorized(1),
    notAuthorized(2)
}

FiveGProSeAuthorizationIndicator ::= ENUMERATED
{
    authorized(1),
    notAuthorized(2)
}

MUSIMUERequestType ::= OCTET STRING (SIZE(1))

RATFrequencySelectionPriority ::= INTEGER (1..256)

FiveGMMCapability ::= OCTET STRING (SIZE(1..13))

-- TS 29.171 [54], clause 7.4.48 and TS 29.572 [24], clause 6.1.6.2.42
UEAreaIndication ::= SEQUENCE
{
    country                      [1] UTF8String (SIZE(2)) OPTIONAL,
    internationalAreaIndication  [2] BOOLEAN OPTIONAL
}

FiveGSUpdateType ::= OCTET STRING (SIZE(1))

UnavailabilityPeriodDuration ::= OCTET STRING (SIZE(1))

RANUEContextModification ::= SEQUENCE
{
    aMFUENGAPID                          [1] AMFUENGAPID,
    rANUENGAPID                          [2] RANUENGAPID,
    rATFrequencySelectionPriority        [3] RATFrequencySelectionPriority OPTIONAL,
    newAMFUENGAPID                       [4] AMFUENGAPID OPTIONAL,
    newGUAMI                             [5] GUAMI OPTIONAL,
    iABAuthorizedIndicator               [6] IABAuthorizedIndicator OPTIONAL,
    nRV2XServicesAuthorization           [7] NRV2XServicesAuthorization OPTIONAL,
    lTEV2XServiceAuthorization           [8] LTEV2XServiceAuthorization OPTIONAL,
    rGLevelWirelineAccessCharacteristics [9] OCTET STRING OPTIONAL,
    uERadioCapabilityID                  [10] OCTET STRING OPTIONAL,
    fiveGProSeAuthorizationIndication    [11] FiveGProSeAuthorizationIndication OPTIONAL,
    mobileIABAuthorizedIndicator         [12] MobileIABAuthorizedIndicator OPTIONAL
}

RANDownlinkNASTransport ::= SEQUENCE
{
    aMFUENGAPID                   [1] AMFUENGAPID,
    rANUENGAPID                   [2] RANUENGAPID,
    oldAMF                        [3] GUAMI OPTIONAL,
    allowedNSSAI                  [4] AllowedNSSAI OPTIONAL,
    mobilityRestrictionList       [5] MobilityRestrictionList OPTIONAL,
    rATFrequencySelectionPriority [6] RATFrequencySelectionPriority OPTIONAL,
    uEDifferentiationInfo         [7] UEDifferentiationInfo OPTIONAL,
    uERadioCapability             [8] UERadioCapability OPTIONAL,
    uERadioCapabilityID           [9] OCTET STRING OPTIONAL,
    targetNSSAIInfo               [10] TargetNSSAIInfo OPTIONAL,
    mobileIABAuthorizedIndicator  [11] MobileIABAuthorizedIndicator OPTIONAL
}

UEDifferentiationInfo ::= SEQUENCE
{
    periodicCommunicationIndicator [1] PeriodicCommunicationIndicator OPTIONAL,
    periodicTime                   [2] INTEGER OPTIONAL,
    scheduledCommunicationTime     [3] SBIType OPTIONAL,
    stationaryIndication           [4] SBIType OPTIONAL,
    trafficProfile                 [5] SBIType OPTIONAL,
    batteryIndication              [6] SBIType OPTIONAL
}

MobileIABAuthorizedIndicator ::= ENUMERATED
{
    authorized(1),
    notAuthorized(2)
}

-- ==================
-- 5G SMF definitions
-- ==================

-- See clause 6.2.3.2.2 for details of this structure
SMFPDUSessionEstablishment ::= SEQUENCE
{
    sUPI                          [1] SUPI OPTIONAL,
    sUPIUnauthenticated           [2] SUPIUnauthenticatedIndication OPTIONAL,
    pEI                           [3] PEI OPTIONAL,
    gPSI                          [4] GPSI OPTIONAL,
    pDUSessionID                  [5] PDUSessionID,
    gTPTunnelID                   [6] FTEID,
    pDUSessionType                [7] PDUSessionType,
    sNSSAI                        [8] SNSSAI OPTIONAL,
    uEEndpoint                    [9] SEQUENCE OF UEEndpointAddress OPTIONAL,
    non3GPPAccessEndpoint         [10] UEEndpointAddress OPTIONAL,
    location                      [11] Location OPTIONAL,
    dNN                           [12] DNN,
    aMFID                         [13] AMFID OPTIONAL,
    hSMFURI                       [14] HSMFURI OPTIONAL,
    requestType                   [15] FiveGSMRequestType,
    accessType                    [16] AccessType OPTIONAL,
    rATType                       [17] RATType OPTIONAL,
    sMPDUDNRequest                [18] SMPDUDNRequest OPTIONAL,
    uEEPSPDNConnection            [19] UEEPSPDNConnection OPTIONAL,
    ePS5GSComboInfo               [20] EPS5GSComboInfo OPTIONAL,
    selectedDNN                   [21] DNN OPTIONAL,
    servingNetwork                [22] SMFServingNetwork OPTIONAL,
    oldPDUSessionID               [23] PDUSessionID OPTIONAL,
    handoverState                 [24] HandoverState OPTIONAL,
    gTPTunnelInfo                 [25] GTPTunnelInfo OPTIONAL,
    pCCRules                      [26] PCCRuleSet OPTIONAL,
    ePSPDNConnectionEstablishment [27] EPSPDNConnectionEstablishment OPTIONAL,
    satelliteBackhaulCategory     [28] SBIType OPTIONAL,
    gEOSatelliteID                [29] GEOSatelliteID OPTIONAL
}

-- See clause 6.2.3.2.3 for details of this structure
SMFPDUSessionModification ::= SEQUENCE
{
    sUPI                        [1] SUPI OPTIONAL,
    sUPIUnauthenticated         [2] SUPIUnauthenticatedIndication OPTIONAL,
    pEI                         [3] PEI OPTIONAL,
    gPSI                        [4] GPSI OPTIONAL,
    sNSSAI                      [5] SNSSAI OPTIONAL,
    non3GPPAccessEndpoint       [6] UEEndpointAddress OPTIONAL,
    location                    [7] Location OPTIONAL,
    requestType                 [8] FiveGSMRequestType,
    accessType                  [9] AccessType OPTIONAL,
    rATType                     [10] RATType OPTIONAL,
    pDUSessionID                [11] PDUSessionID OPTIONAL,
    ePS5GSComboInfo             [12] EPS5GSComboInfo OPTIONAL,
    uEEndpoint                  [13] UEEndpointAddress OPTIONAL,
    servingNetwork              [14] SMFServingNetwork OPTIONAL,
    handoverState               [15] HandoverState OPTIONAL,
    gTPTunnelInfo               [16] GTPTunnelInfo OPTIONAL,
    pCCRules                    [17] PCCRuleSet OPTIONAL,
    ePSPDNConnectionModification[18] EPSPDNConnectionModification OPTIONAL,
    uPPathChange                [19] UPPathChange OPTIONAL,
    pFDDataForApp               [20] PFDDataForApp OPTIONAL,
    satelliteBackhaulCategory   [21] SBIType OPTIONAL,
    gEOSatelliteID              [22] GEOSatelliteID OPTIONAL,
    proSeRemoteUEsReport        [23] ProSeRemoteUEsReport OPTIONAL
}

-- See clause 6.2.3.2.4 for details of this structure
SMFPDUSessionRelease ::= SEQUENCE
{
    sUPI                        [1] SUPI,
    pEI                         [2] PEI OPTIONAL,
    gPSI                        [3] GPSI OPTIONAL,
    pDUSessionID                [4] PDUSessionID,
    timeOfFirstPacket           [5] Timestamp OPTIONAL,
    timeOfLastPacket            [6] Timestamp OPTIONAL,
    uplinkVolume                [7] INTEGER OPTIONAL,
    downlinkVolume              [8] INTEGER OPTIONAL,
    location                    [9] Location OPTIONAL,
    cause                       [10] SMFErrorCodes OPTIONAL,
    ePS5GSComboInfo             [11] EPS5GSComboInfo OPTIONAL,
    nGAPCause                   [12] NGAPCauseInt OPTIONAL,
    fiveGMMCause                [13] FiveGMMCause OPTIONAL,
    pCCRuleIDs                  [14] PCCRuleIDSet OPTIONAL,
    ePSPDNConnectionRelease     [15] EPSPDNConnectionRelease OPTIONAL
}

-- See clause 6.2.3.2.5 for details of this structure
SMFStartOfInterceptionWithEstablishedPDUSession ::= SEQUENCE
{
    sUPI                                               [1] SUPI OPTIONAL,
    sUPIUnauthenticated                                [2] SUPIUnauthenticatedIndication OPTIONAL,
    pEI                                                [3] PEI OPTIONAL,
    gPSI                                               [4] GPSI OPTIONAL,
    pDUSessionID                                       [5] PDUSessionID,
    gTPTunnelID                                        [6] FTEID,
    pDUSessionType                                     [7] PDUSessionType,
    sNSSAI                                             [8] SNSSAI OPTIONAL,
    uEEndpoint                                         [9] SEQUENCE OF UEEndpointAddress,
    non3GPPAccessEndpoint                              [10] UEEndpointAddress OPTIONAL,
    location                                           [11] Location OPTIONAL,
    dNN                                                [12] DNN,
    aMFID                                              [13] AMFID OPTIONAL,
    hSMFURI                                            [14] HSMFURI OPTIONAL,
    requestType                                        [15] FiveGSMRequestType,
    accessType                                         [16] AccessType OPTIONAL,
    rATType                                            [17] RATType OPTIONAL,
    sMPDUDNRequest                                     [18] SMPDUDNRequest OPTIONAL,
    timeOfSessionEstablishment                         [19] Timestamp OPTIONAL,
    ePS5GSComboInfo                                    [20] EPS5GSComboInfo OPTIONAL,
    uEEPSPDNConnection                                 [21] UEEPSPDNConnection OPTIONAL,
    servingNetwork                                     [22] SMFServingNetwork OPTIONAL,
    gTPTunnelInfo                                      [23] GTPTunnelInfo OPTIONAL,
    pCCRules                                           [24] PCCRuleSet OPTIONAL,
    ePSStartOfInterceptionWithEstablishedPDNConnection [25] EPSStartOfInterceptionWithEstablishedPDNConnection OPTIONAL,
    pFDDataForApps                                     [26] PFDDataForApps OPTIONAL,
    satelliteBackhaulCategory                          [27] SBIType OPTIONAL,
    gEOSatelliteID                                     [28] GEOSatelliteID OPTIONAL,
    remoteUEsContextConnected                          [29] RemoteUEContextList OPTIONAL
}

-- See clause 6.2.3.2.6 for details of this structure
SMFUnsuccessfulProcedure ::= SEQUENCE
{
    failedProcedureType         [1] SMFFailedProcedureType,
    failureCause                [2] FiveGSMCause,
    initiator                   [3] Initiator,
    requestedSlice              [4] NSSAI OPTIONAL,
    sUPI                        [5] SUPI OPTIONAL,
    sUPIUnauthenticated         [6] SUPIUnauthenticatedIndication OPTIONAL,
    pEI                         [7] PEI OPTIONAL,
    gPSI                        [8] GPSI OPTIONAL,
    pDUSessionID                [9] PDUSessionID OPTIONAL,
    uEEndpoint                  [10] SEQUENCE OF UEEndpointAddress OPTIONAL,
    non3GPPAccessEndpoint       [11] UEEndpointAddress OPTIONAL,
    dNN                         [12] DNN OPTIONAL,
    aMFID                       [13] AMFID OPTIONAL,
    hSMFURI                     [14] HSMFURI OPTIONAL,
    requestType                 [15] FiveGSMRequestType OPTIONAL,
    accessType                  [16] AccessType OPTIONAL,
    rATType                     [17] RATType OPTIONAL,
    sMPDUDNRequest              [18] SMPDUDNRequest OPTIONAL,
    location                    [19] Location OPTIONAL,
    ePSPDNUnsuccessfulProcedure [20] EPSPDNUnsuccessfulProcedure OPTIONAL
}

-- See clause 6.2.3.2.8 for details of this structure
SMFPDUtoMAPDUSessionModification ::= SEQUENCE
{
    sUPI                         [1] SUPI OPTIONAL,
    sUPIUnauthenticated          [2] SUPIUnauthenticatedIndication OPTIONAL,
    pEI                          [3] PEI OPTIONAL,
    gPSI                         [4] GPSI OPTIONAL,
    sNSSAI                       [5] SNSSAI OPTIONAL,
    non3GPPAccessEndpoint        [6] UEEndpointAddress OPTIONAL,
    location                     [7] Location OPTIONAL,
    requestType                  [8] FiveGSMRequestType,
    accessType                   [9] AccessType OPTIONAL,
    rATType                      [10] RATType OPTIONAL,
    pDUSessionID                 [11] PDUSessionID,
    requestIndication            [12] RequestIndication,
    aTSSSContainer               [13] ATSSSContainer,
    uEEndpoint                   [14] UEEndpointAddress OPTIONAL,
    servingNetwork               [15] SMFServingNetwork OPTIONAL,
    handoverState                [16] HandoverState OPTIONAL,
    gTPTunnelInfo                [17] GTPTunnelInfo OPTIONAL,
    ePSPDNConnectionModification [18] EPSPDNConnectionModification OPTIONAL
}

-- See clause 6.2.3.2.7.1 for details of this structure
SMFMAPDUSessionEstablishment ::= SEQUENCE
{
    sUPI                          [1] SUPI OPTIONAL,
    sUPIUnauthenticated           [2] SUPIUnauthenticatedIndication OPTIONAL,
    pEI                           [3] PEI OPTIONAL,
    gPSI                          [4] GPSI OPTIONAL,
    pDUSessionID                  [5] PDUSessionID,
    pDUSessionType                [6] PDUSessionType,
    accessInfo                    [7] SEQUENCE OF AccessInfo,
    sNSSAI                        [8] SNSSAI OPTIONAL,
    uEEndpoint                    [9] SEQUENCE OF UEEndpointAddress OPTIONAL,
    location                      [10] Location OPTIONAL,
    dNN                           [11] DNN,
    aMFID                         [12] AMFID OPTIONAL,
    hSMFURI                       [13] HSMFURI OPTIONAL,
    requestType                   [14] FiveGSMRequestType,
    sMPDUDNRequest                [15] SMPDUDNRequest OPTIONAL,
    servingNetwork                [16] SMFServingNetwork,
    oldPDUSessionID               [17] PDUSessionID OPTIONAL,
    mAUpgradeIndication           [18] SMFMAUpgradeIndication OPTIONAL,
    ePSPDNCnxInfo                 [19] SMFEPSPDNCnxInfo OPTIONAL,
    mAAcceptedIndication          [20] SMFMAAcceptedIndication,
    aTSSSContainer                [21] ATSSSContainer OPTIONAL,
    uEEPSPDNConnection            [22] UEEPSPDNConnection OPTIONAL,
    ePS5GSComboInfo               [23] EPS5GSComboInfo OPTIONAL,
    selectedDNN                   [24] DNN OPTIONAL,
    handoverState                 [25] HandoverState OPTIONAL,
    pCCRules                      [26] PCCRuleSet OPTIONAL,
    ePSPDNConnectionEstablishment [27] EPSPDNConnectionEstablishment OPTIONAL
}

-- See clause 6.2.3.2.7.2 for details of this structure
SMFMAPDUSessionModification ::= SEQUENCE
{
    sUPI                         [1] SUPI OPTIONAL,
    sUPIUnauthenticated          [2] SUPIUnauthenticatedIndication OPTIONAL,
    pEI                          [3] PEI OPTIONAL,
    gPSI                         [4] GPSI OPTIONAL,
    pDUSessionID                 [5] PDUSessionID,
    accessInfo                   [6] SEQUENCE OF AccessInfo OPTIONAL,
    sNSSAI                       [7] SNSSAI OPTIONAL,
    location                     [8] Location OPTIONAL,
    requestType                  [9] FiveGSMRequestType OPTIONAL,
    servingNetwork               [10] SMFServingNetwork,
    oldPDUSessionID              [11] PDUSessionID OPTIONAL,
    mAUpgradeIndication          [12] SMFMAUpgradeIndication OPTIONAL,
    ePSPDNCnxInfo                [13] SMFEPSPDNCnxInfo OPTIONAL,
    mAAcceptedIndication         [14] SMFMAAcceptedIndication,
    aTSSSContainer               [15] ATSSSContainer OPTIONAL,
    uEEPSPDNConnection           [16] UEEPSPDNConnection OPTIONAL,
    ePS5GSComboInfo              [17] EPS5GSComboInfo OPTIONAL,
    handoverState                [18] HandoverState OPTIONAL,
    pCCRules                     [19] PCCRuleSet OPTIONAL,
    uPPathChange                 [20] UPPathChange OPTIONAL,
    pFDDataForApp                [21] PFDDataForApp OPTIONAL,
    ePSPDNConnectionModification [22] EPSPDNConnectionModification OPTIONAL
}

-- See clause 6.2.3.2.7.3 for details of this structure
SMFMAPDUSessionRelease ::= SEQUENCE
{
    sUPI                        [1] SUPI,
    pEI                         [2] PEI OPTIONAL,
    gPSI                        [3] GPSI OPTIONAL,
    pDUSessionID                [4] PDUSessionID,
    timeOfFirstPacket           [5] Timestamp OPTIONAL,
    timeOfLastPacket            [6] Timestamp OPTIONAL,
    uplinkVolume                [7] INTEGER OPTIONAL,
    downlinkVolume              [8] INTEGER OPTIONAL,
    location                    [9] Location OPTIONAL,
    cause                       [10] SMFErrorCodes OPTIONAL,
    nGAPCause                   [11] NGAPCauseInt OPTIONAL,
    fiveGMMCause                [12] FiveGMMCause OPTIONAL,
    pCCRuleIDs                  [13] PCCRuleIDSet OPTIONAL,
    ePSPDNConnectionRelease     [14] EPSPDNConnectionRelease OPTIONAL
}

-- See clause 6.2.3.2.7.4 for details of this structure
SMFStartOfInterceptionWithEstablishedMAPDUSession ::= SEQUENCE
{
    sUPI                                               [1] SUPI OPTIONAL,
    sUPIUnauthenticated                                [2] SUPIUnauthenticatedIndication OPTIONAL,
    pEI                                                [3] PEI OPTIONAL,
    gPSI                                               [4] GPSI OPTIONAL,
    pDUSessionID                                       [5] PDUSessionID,
    pDUSessionType                                     [6] PDUSessionType,
    accessInfo                                         [7] SEQUENCE OF AccessInfo,
    sNSSAI                                             [8] SNSSAI OPTIONAL,
    uEEndpoint                                         [9] SEQUENCE OF UEEndpointAddress OPTIONAL,
    location                                           [10] Location OPTIONAL,
    dNN                                                [11] DNN,
    aMFID                                              [12] AMFID OPTIONAL,
    hSMFURI                                            [13] HSMFURI OPTIONAL,
    requestType                                        [14] FiveGSMRequestType OPTIONAL,
    sMPDUDNRequest                                     [15] SMPDUDNRequest OPTIONAL,
    servingNetwork                                     [16] SMFServingNetwork,
    oldPDUSessionID                                    [17] PDUSessionID OPTIONAL,
    mAUpgradeIndication                                [18] SMFMAUpgradeIndication OPTIONAL,
    ePSPDNCnxInfo                                      [19] SMFEPSPDNCnxInfo OPTIONAL,
    mAAcceptedIndication                               [20] SMFMAAcceptedIndication,
    aTSSSContainer                                     [21] ATSSSContainer OPTIONAL,
    ePS5GSComboInfo                                    [22] EPS5GSComboInfo OPTIONAL,
    uEEPSPDNConnection                                 [23] UEEPSPDNConnection OPTIONAL,
    pCCRules                                           [24] PCCRuleSet OPTIONAL,
    pFDDataForApps                                     [25] PFDDataForApps OPTIONAL,
    ePSStartOfInterceptionWithEstablishedPDNConnection [26] EPSStartOfInterceptionWithEstablishedPDNConnection OPTIONAL
}

-- See clause 6.2.3.2.7.5 for details of this structure
SMFMAUnsuccessfulProcedure ::= SEQUENCE
{
    failedProcedureType         [1] SMFFailedProcedureType,
    failureCause                [2] FiveGSMCause,
    requestedSlice              [3] NSSAI OPTIONAL,
    initiator                   [4] Initiator,
    sUPI                        [5] SUPI OPTIONAL,
    sUPIUnauthenticated         [6] SUPIUnauthenticatedIndication OPTIONAL,
    pEI                         [7] PEI OPTIONAL,
    gPSI                        [8] GPSI OPTIONAL,
    pDUSessionID                [9] PDUSessionID OPTIONAL,
    accessInfo                  [10] SEQUENCE OF AccessInfo,
    uEEndpoint                  [11] SEQUENCE OF UEEndpointAddress OPTIONAL,
    location                    [12] Location OPTIONAL,
    dNN                         [13] DNN OPTIONAL,
    aMFID                       [14] AMFID OPTIONAL,
    hSMFURI                     [15] HSMFURI OPTIONAL,
    requestType                 [16] FiveGSMRequestType OPTIONAL,
    sMPDUDNRequest              [17] SMPDUDNRequest OPTIONAL
}

SMFProSeRemoteUEReport ::= SEQUENCE
{
    sUPI                        [1] SUPI,
    gPSI                        [2] GPSI OPTIONAL,
    pEI                         [3] PEI OPTIONAL,
    pDUSessionID                [4] PDUSessionID,
    remoteUEContextConnected    [5] RemoteUEContext OPTIONAL,
    remoteUEContextDisconnected [6] RemoteUEContext OPTIONAL,
    location                    [7] Location OPTIONAL
}

SMFStartOfInterceptionWithConnectedProSeRemoteUE ::= SEQUENCE
{
    sUPI                     [1] SUPI,
    gPSI                     [2] GPSI OPTIONAL,
    pEI                      [3] PEI OPTIONAL,
    pDUSessionID             [4] PDUSessionID,
    remoteUEContextConnected [5] RemoteUEContextList OPTIONAL,
    location                 [6] Location OPTIONAL
}

-- =================
-- 5G SMF parameters
-- =================

SMFID ::= UTF8String

SMFFailedProcedureType ::= ENUMERATED
{
    pDUSessionEstablishment(1),
    pDUSessionModification(2),
    pDUSessionRelease(3)
}

SMFServingNetwork ::= SEQUENCE
{
    pLMNID  [1] PLMNID,
    nID     [2] NID OPTIONAL
}

AccessInfo ::= SEQUENCE
{
    accessType                [1] AccessType,
    rATType                   [2] RATType OPTIONAL,
    gTPTunnelID               [3] FTEID,
    non3GPPAccessEndpoint     [4] UEEndpointAddress OPTIONAL,
    establishmentStatus       [5] EstablishmentStatus,
    aNTypeToReactivate        [6] AccessType OPTIONAL,
    gTPTunnelInfo             [7] GTPTunnelInfo OPTIONAL,
    satelliteBackhaulCategory [8] SBIType OPTIONAL,
    gEOSatelliteID            [9] GEOSatelliteID OPTIONAL
}

-- see Clause 6.1.2 of TS 24.193[44] for the details of the ATSSS container contents.
ATSSSContainer ::= OCTET STRING

DLRANTunnelInformation ::= SEQUENCE
{
    dLQOSFlowTunnelInformation                    [1] QOSFlowTunnelInformation OPTIONAL,
    additionalDLQOSFlowTunnelInformation          [2] QOSFlowTunnelInformationList OPTIONAL,
    redundantDLQOSFlowTunnelInformation           [3] QOSFlowTunnelInformationList OPTIONAL,
    additionalredundantDLQOSFlowTunnelInformation [4] QOSFlowTunnelInformationList OPTIONAL
}

EstablishmentStatus ::= ENUMERATED
{
    established(0),
    released(1)
}

FiveGSGTPTunnels ::= SEQUENCE
{
    uLNGUUPTunnelInformation           [1] FTEID OPTIONAL,
    additionalULNGUUPTunnelInformation [2] FTEIDList OPTIONAL,
    dLRANTunnelInformation             [3] DLRANTunnelInformation OPTIONAL
}

FiveQI ::= INTEGER (0..255)

HandoverState ::= ENUMERATED
{
    none(1),
    preparing(2),
    prepared(3),
    completed(4),
    cancelled(5)
}

NGAPCauseInt ::= SEQUENCE
{
    group [1] NGAPCauseGroupInt,
    value [2] NGAPCauseValueInt
}

-- Derived as described in TS 29.571 [17] clause 5.4.4.12
NGAPCauseGroupInt ::= INTEGER

NGAPCauseValueInt ::= INTEGER

SMFMAUpgradeIndication ::= BOOLEAN

-- Given in YAML encoding as defined in clause 6.1.6.2.31 of TS 29.502[16]
SMFEPSPDNCnxInfo ::= UTF8String

SMFMAAcceptedIndication ::= BOOLEAN

-- see Clause 6.1.6.3.8 of TS 29.502[16] for the details of this structure.
SMFErrorCodes ::= UTF8String

-- see Clause 6.1.6.3.2 of TS 29.502[16] for details of this structure.
UEEPSPDNConnection ::= OCTET STRING

-- see Clause 6.1.6.3.6 of TS 29.502[16] for the details of this structure.
RequestIndication ::= ENUMERATED
{
    uEREQPDUSESMOD(0),
    uEREQPDUSESREL(1),
    pDUSESMOB(2),
    nWREQPDUSESAUTH(3),
    nWREQPDUSESMOD(4),
    nWREQPDUSESREL(5),
    eBIASSIGNMENTREQ(6),
    rELDUETO5GANREQUEST(7)
}

QOSFlowTunnelInformation ::= SEQUENCE
{
    uPTunnelInformation   [1] FTEID,
    associatedQOSFlowList [2] QOSFlowLists
}

QOSFlowTunnelInformationList ::= SEQUENCE OF QOSFlowTunnelInformation

QOSFlowDescription ::= OCTET STRING

QOSFlowLists ::= SEQUENCE OF QOSFlowList

QOSFlowList ::= SEQUENCE
{
    qFI                      [1] QFI,
    qOSRules                 [2] QOSRules OPTIONAL,
    eBI                      [3] EPSBearerID OPTIONAL,
    qOSFlowDescription       [4] QOSFlowDescription OPTIONAL,
    qOSFlowProfile           [5] QOSFlowProfile OPTIONAL,
    associatedANType         [6] AccessType OPTIONAL,
    defaultQOSRuleIndication [7] BOOLEAN OPTIONAL
}

QOSFlowProfile ::= SEQUENCE
{
    fiveQI [1] FiveQI
}

QOSRules ::= OCTET STRING

-- See clauses 5.6.2.6-1 and 5.6.2.9-1 of TS 29.512 [89], clause table 5.6.2.5-1 of TS 29.508 [90] for the details of this structure
PCCRule ::= SEQUENCE
{
    pCCRuleID                     [1] PCCRuleID OPTIONAL,
    appId                         [2] UTF8String OPTIONAL,
    flowInfos                     [3] FlowInformationSet OPTIONAL,
    appReloc                      [4] BOOLEAN OPTIONAL,
    simConnInd                    [5] BOOLEAN OPTIONAL,
    simConnTerm                   [6] INTEGER OPTIONAL,
    maxAllowedUpLat               [7] INTEGER OPTIONAL,
    trafficRoutes                 [8] RouteToLocationSet,
    trafficSteeringPolIdDl        [9] UTF8String OPTIONAL,
    trafficSteeringPolIdUl        [10] UTF8String OPTIONAL,
    deprecatedSourceDNAI          [11] DNAI OPTIONAL,
    deprecatedTargetDNAI          [12] DNAI OPTIONAL,
    deprecatedDNAIChangeType      [13] DNAIChangeType OPTIONAL,
    deprecatedSourceUEIPAddr      [14] IPAddress OPTIONAL,
    deprecatedTargetUEIPAddr      [15] IPAddress OPTIONAL,
    sourceTrafficRouting          [16] RouteToLocation OPTIONAL,
    targetTrafficRouting          [17] RouteToLocation OPTIONAL,
    eASIPReplaceInfos             [18] EASIPReplaceInfos OPTIONAL
}

-- See clause table 5.6.2.5-1 of TS 29.508 [90] for the details of this structure.
UPPathChange ::= SEQUENCE
{
    sourceDNAI                    [1] DNAI OPTIONAL,
    targetDNAI                    [2] DNAI OPTIONAL,
    dNAIChangeType                [3] DNAIChangeType OPTIONAL,
    sourceUEIPAddr                [4] IPAddress OPTIONAL,
    targetUEIPAddr                [5] IPAddress OPTIONAL,
    sourceTrafficRouting          [6] RouteToLocation OPTIONAL,
    targetTrafficRouting          [7] RouteToLocation OPTIONAL,
    mACAddress                    [8] MACAddress OPTIONAL
}

-- See table 5.6.2.14-1 of TS 29.512 [89]
PCCRuleID ::= UTF8String

PCCRuleSet ::= SET OF PCCRule

PCCRuleIDSet ::= SET OF PCCRuleID

FlowInformationSet ::= SET OF FlowInformation

RouteToLocationSet ::= SET OF RouteToLocation

-- See table 5.6.2.14 of TS 29.512 [89]
FlowInformation ::= SEQUENCE
{
    flowDescription    [1] FlowDescription OPTIONAL,
    ethFlowDescription [2] EthFlowDescription OPTIONAL,
    tosTrafficClass    [3] OCTET STRING (SIZE(2)) OPTIONAL,
    spi                [4] OCTET STRING (SIZE(4)) OPTIONAL,
    flowLabel          [5] OCTET STRING (SIZE(3)) OPTIONAL,
    flowDirection      [6] FlowDirection OPTIONAL
}

-- See table 5.6.2.14 of TS 29.512 [89]
FlowDescription ::= SEQUENCE
{
    sourceIPAddress       [1] IPAddressOrRangeOrAny,
    destinationIPAddress  [2] IPAddressOrRangeOrAny,
    sourcePortNumber      [3] PortNumber OPTIONAL,
    destinationPortNumber [4] PortNumber OPTIONAL,
    protocol              [5] NextLayerProtocolOrAny
}

IPAddressOrRangeOrAny ::= CHOICE
{
    iPAddress      [1] IPAddress,
    ipAddressRange [2] IPMask,
    anyIPAddress   [3] AnyIPAddress
}

IPMask ::= SEQUENCE
{
    fromIPAddress [1] IPAddress,
    toIPAddress   [2] IPAddress
}

AnyIPAddress ::= ENUMERATED
{
    any(1)
}

NextLayerProtocolOrAny ::= CHOICE
{
    nextLayerProtocol    [1] NextLayerProtocol,
    anyNextLayerProtocol [2] AnyNextLayerProtocol
}

AnyNextLayerProtocol ::= ENUMERATED
{
    ip(1)
}

-- See table 5.6.2.17-1 of TS 29.514 [91]
EthFlowDescription ::= SEQUENCE
{
    destMacAddress    [1] MACAddress OPTIONAL,
    ethType           [2] OCTET STRING (SIZE(2)),
    fDesc             [3] FlowDescription OPTIONAL,
    fDir              [4] FDir OPTIONAL,
    sourceMacAddress  [5] MACAddress OPTIONAL,
    vlanTags          [6] SET OF VLANTag,
    srcMacAddrEnd     [7] MACAddress OPTIONAL,
    destMacAddrEnd    [8] MACAddress OPTIONAL
}

-- See table 5.6.2.17-1 of TS 29.514 [91]
FDir ::= ENUMERATED
{
    downlink(1)
}

-- See table 5.6.2.17-1 of TS 29.514 [91]
VLANTag ::= SEQUENCE
{
    priority [1] BIT STRING (SIZE(3)),
    cFI      [2] BIT STRING (SIZE(1)),
    vLANID   [3] BIT STRING (SIZE(12))
}

-- See table 5.6.2.14 of TS 29.512 [89]
FlowDirection ::= ENUMERATED
{
    downlinkOnly(1),
    uplinkOnly(2),
    dowlinkAndUplink(3)
}

-- See table 5.4.2.1 of TS 29.571 [17]
DNAIChangeType ::= ENUMERATED
{
    early(1),
    earlyAndLate(2),
    late(3)
}

-- See table 5.6.2.15 of TS 29.571 [17]
RouteToLocation ::= SEQUENCE
{
    dNAI            [1] DNAI,
    routeInfo       [2] RouteInfo
}

-- See table 5.4.2.1 of TS 29.571 [17]
DNAI ::= UTF8String

-- See table 5.4.4.16 of TS 29.571 [17]
RouteInfo ::= SEQUENCE
{
    iPAddressTunnelEndpoint       [1] IPAddress,
    uDPPortNumberTunnelEndpoint   [2] PortNumber
}

-- See clause 4.1.4.2 of TS 29.512 [89]
EASIPReplaceInfos ::= SEQUENCE
{
    sourceEASAddress [1] EASServerAddress,
    targetEASAddress [2] EASServerAddress
}

-- See clause 4.1.4.2 of TS 29.512 [89]
EASServerAddress ::= SEQUENCE
{
    iPAddress        [1]  IPAddress,
    port             [2]  PortNumber
}

-- See table 5.4.2.1 of TS 29.571 [17]
GEOSatelliteID ::= UTF8String

ProSeRemoteUEsReport ::= SEQUENCE
{
    remoteUEsContextConnected    [1] RemoteUEContextList OPTIONAL,
    remoteUEsContextDisconnected [2] RemoteUEContextList OPTIONAL
}

RemoteUEContextList ::= SEQUENCE
{
    numberOfRemoteUEContexts [1] INTEGER,
    remoteUEContexts         [2] SET OF RemoteUEContext
}

RemoteUEContext ::= SEQUENCE
{
    remoteUEIDFormat       [1] RemoteUEIDFormat,
    remoteUEIDType         [2] RemoteUEIDType,
    remoteUEID             [3] RemoteUEID,
    uDPPortRangeIndicator  [4] BOOLEAN,
    tCPPortRangeIndicator  [5] BOOLEAN,
    protocolUsedByRemoteUE [6] ProtocolUsedByRemoteUE,
    addressInformation     [7] AddressInformation OPTIONAL,
    hPLMNID                [8] PLMNID OPTIONAL
}

ProtocolUsedByRemoteUE ::= ENUMERATED
{
    noIPInfo(1),
    iPv4(2),
    iPv6(3),
    unstructured(4),
    ethernet(5)
}

RemoteUEIDFormat ::= ENUMERATED
{
    nAI(1),
    sixtyFourBitString(2)
}

RemoteUEIDType ::= ENUMERATED
{
    uPPRUKID(1),
    cPPRUKID(2),
    iMEI(3),
    iMEISV(4)
}

RemoteUEID ::= CHOICE
{
    uPPRUKIDNAI         [1] NAI,
    uPPRUKID64BitString [2] BIT STRING (SIZE(64)),
    cPPRUKIDNAI         [3] NAI,
    cPPRUKID64BitString [4] BIT STRING (SIZE(64)),
    iMEI                [5] IMEI,
    iMEISV              [6] IMEISV
}

AddressInformation ::= CHOICE
{
    iPv4Address                [1] IPv4Address,
    iPv4AddressUDPPortRange    [2] IPv4AddressUDPPortRange,
    iPv4AddressTCPPortRange    [3] IPv4AddressTCPPortRange,
    iPv4AddressUDPTCPPortRange [4] IPv4AddressUDPTCPPortRange,
    iPv6Address                [5] IPv6Address,
    ethernetAddress            [6] MACAddress
}

IPv4AddressUDPPortRange ::= SEQUENCE
{
    iPv4Address         [1] IPv4Address,
    uDPPortRange        [2] PortRange
}

IPv4AddressTCPPortRange ::= SEQUENCE
{
    iPv4Address         [1] IPv4Address,
    tCPPortRange        [2] PortRange
}

IPv4AddressUDPTCPPortRange ::= SEQUENCE
{
    iPv4Address         [1] IPv4Address,
    uDPPortRange        [2] PortRange,
    tCPPortRange        [2] PortRange
}

PortRange ::= SEQUENCE
{
    portStart [1] INTEGER (0..65535),
    portEnd   [2] INTEGER (0..65535)
}

-- ================================
-- PGW-C + SMF PDNConnection Events
-- ================================

EPSPDNConnectionEstablishment ::= SEQUENCE
{
    ePSSubscriberIDs                   [1] EPSSubscriberIDs,
    iMSIUnauthenticated                [2] IMSIUnauthenticatedIndication OPTIONAL,
    defaultBearerID                    [3] EPSBearerID,
    gTPTunnelInfo                      [4] GTPTunnelInfo OPTIONAL,
    pDNConnectionType                  [5] PDNConnectionType,
    uEEndpoints                        [6] SEQUENCE OF UEEndpointAddress OPTIONAL,
    non3GPPAccessEndpoint              [7] UEEndpointAddress OPTIONAL,
    location                           [8] Location OPTIONAL,
    additionalLocation                 [9] Location OPTIONAL,
    aPN                                [10] APN,
    requestType                        [11] EPSPDNConnectionRequestType OPTIONAL,
    accessType                         [12] AccessType OPTIONAL,
    rATType                            [13] RATType OPTIONAL,
    protocolConfigurationOptions       [14] PDNProtocolConfigurationOptions OPTIONAL,
    servingNetwork                     [15] SMFServingNetwork OPTIONAL,
    sMPDUDNRequest                     [16] SMPDUDNRequest OPTIONAL,
    bearerContextsCreated              [17] SEQUENCE OF EPSBearerContextCreated,
    bearerContextsMarkedForRemoval     [18] SEQUENCE OF EPSBearerContextForRemoval OPTIONAL,
    indicationFlags                    [19] PDNConnectionIndicationFlags OPTIONAL,
    handoverIndication                 [20] PDNHandoverIndication OPTIONAL,
    nBIFOMSupport                      [21] PDNNBIFOMSupport OPTIONAL,
    fiveGSInterworkingInfo             [22] FiveGSInterworkingInfo OPTIONAL,
    cSRMFI                             [23] CSRMFI OPTIONAL,
    restorationOfPDNConnectionsSupport [24] RestorationOfPDNConnectionsSupport OPTIONAL,
    pGWChangeIndication                [25] PGWChangeIndication OPTIONAL,
    pGWRNSI                            [26] PGWRNSI OPTIONAL
}

EPSPDNConnectionModification ::= SEQUENCE
{
    ePSSubscriberIDs                   [1] EPSSubscriberIDs,
    iMSIUnauthenticated                [2] IMSIUnauthenticatedIndication OPTIONAL,
    defaultBearerID                    [3] EPSBearerID,
    gTPTunnelInfo                      [4] GTPTunnelInfo OPTIONAL,
    pDNConnectionType                  [5] PDNConnectionType,
    uEEndpoints                        [6] SEQUENCE OF UEEndpointAddress OPTIONAL,
    non3GPPAccessEndpoint              [7] UEEndpointAddress OPTIONAL,
    location                           [8] Location OPTIONAL,
    additionalLocation                 [9] Location OPTIONAL,
    aPN                                [10] APN,
    requestType                        [11] EPSPDNConnectionRequestType OPTIONAL,
    accessType                         [12] AccessType OPTIONAL,
    rATType                            [13] RATType OPTIONAL,
    protocolConfigurationOptions       [14] PDNProtocolConfigurationOptions OPTIONAL,
    servingNetwork                     [15] SMFServingNetwork OPTIONAL,
    sMPDUDNRequest                     [16] SMPDUDNRequest OPTIONAL,
    bearerContextsCreated              [17] SEQUENCE OF EPSBearerContextCreated OPTIONAL,
    bearerContextsModified             [18] SEQUENCE OF EPSBearerContextModified,
    bearerContextsMarkedForRemoval     [19] SEQUENCE OF EPSBearerContextForRemoval OPTIONAL,
    bearersDeleted                     [20] SEQUENCE OF EPSBearersDeleted OPTIONAL,
    indicationFlags                    [21] PDNConnectionIndicationFlags OPTIONAL,
    handoverIndication                 [22] PDNHandoverIndication OPTIONAL,
    nBIFOMSupport                      [23] PDNNBIFOMSupport OPTIONAL,
    fiveGSInterworkingInfo             [24] FiveGSInterworkingInfo OPTIONAL,
    cSRMFI                             [25] CSRMFI OPTIONAL,
    restorationOfPDNConnectionsSupport [26] RestorationOfPDNConnectionsSupport OPTIONAL,
    pGWChangeIndication                [27] PGWChangeIndication OPTIONAL,
    pGWRNSI                            [28] PGWRNSI OPTIONAL
}

EPSPDNConnectionRelease ::= SEQUENCE
{
    ePSSubscriberIDs    [1] EPSSubscriberIDs,
    iMSIUnauthenticated [2] IMSIUnauthenticatedIndication OPTIONAL,
    defaultBearerID     [3] EPSBearerID,
    location            [4] Location OPTIONAL,
    gTPTunnelInfo       [5] GTPTunnelInfo OPTIONAL,
    rANNASCause         [6] EPSRANNASCause OPTIONAL,
    pDNConnectionType   [7] PDNConnectionType,
    indicationFlags     [8] PDNConnectionIndicationFlags OPTIONAL,
    scopeIndication     [9] EPSPDNConnectionReleaseScopeIndication OPTIONAL,
    bearersDeleted      [10] SEQUENCE OF EPSBearersDeleted OPTIONAL
}

EPSStartOfInterceptionWithEstablishedPDNConnection ::= SEQUENCE
{
    ePSSubscriberIDs                   [1] EPSSubscriberIDs,
    iMSIUnauthenticated                [2] IMSIUnauthenticatedIndication OPTIONAL,
    defaultBearerID                    [3] EPSBearerID,
    gTPTunnelInfo                      [4] GTPTunnelInfo OPTIONAL,
    pDNConnectionType                  [5] PDNConnectionType,
    uEEndpoints                        [6] SEQUENCE OF UEEndpointAddress OPTIONAL,
    non3GPPAccessEndpoint              [7] UEEndpointAddress OPTIONAL,
    location                           [8] Location OPTIONAL,
    additionalLocation                 [9] Location OPTIONAL,
    aPN                                [10] APN,
    requestType                        [11] EPSPDNConnectionRequestType OPTIONAL,
    accessType                         [12] AccessType OPTIONAL,
    rATType                            [13] RATType OPTIONAL,
    protocolConfigurationOptions       [14] PDNProtocolConfigurationOptions OPTIONAL,
    servingNetwork                     [15] SMFServingNetwork OPTIONAL,
    sMPDUDNRequest                     [16] SMPDUDNRequest OPTIONAL,
    bearerContexts                     [17] SEQUENCE OF EPSBearerContext
}

EPSPDNUnsuccessfulProcedure ::= SEQUENCE
{
    failureCause        [1] ESMCause,
    initiator           [2] Initiator,
    ePSSubscriberIDs    [3] EPSSubscriberIDs,
    iMSIUnauthenticated [4] IMSIUnauthenticatedIndication OPTIONAL,
    failedProcedure     [5] EPSPDNFailedProcedure
}


PFDDataForApps ::= SET OF PFDDataForApp

PFDDataForApp ::= SEQUENCE
{
    aPPId [1] UTF8String,
    pFDs  [2] PFDs
}

PFDs ::= SET OF PFD

-- See clause 5.6.2.5 of TS 29.551 [96]
PFD ::= SEQUENCE
{
    pFDId                [1] UTF8String,
    pFDFlowDescriptions  [2] PFDFlowDescriptions,
    urls                 [3] PFDURLs,
    domainNames          [4] DomainNames,
    dnProtocol           [5] DnProtocol
}

PFDURLs ::= SET OF UTF8String

PFDFlowDescriptions ::= SET OF PFDFlowDescription

DomainNames ::= SET OF UTF8String

PFDFlowDescription ::= SEQUENCE
{
    nextLayerProtocol [1] NextLayerProtocol,
    serverIPAddress   [2] IPAddress,
    serverPortNumber  [3] PortNumber
}

-- See clause 5.14.2.2.4 of TS 29.122 [63]
DnProtocol ::= ENUMERATED
{
    dnsQname(1),
    tlsSni(2),
    tlsSan(3),
    tlsScn(4)
}

-- ======================
-- PGW-C + SMF Parameters
-- ======================

CSRMFI ::= BOOLEAN

EPS5GSComboInfo ::= SEQUENCE
{
    ePSInterworkingIndication [1] EPSInterworkingIndication,
    ePSSubscriberIDs          [2] EPSSubscriberIDs,
    ePSPDNCnxInfo             [3] EPSPDNCnxInfo OPTIONAL,
    ePSBearerInfo             [4] EPSBearerInfo OPTIONAL
}

EPSInterworkingIndication ::= ENUMERATED
{
    none(1),
    withN26(2),
    withoutN26(3),
    iwkNon3GPP(4)
}

EPSSubscriberIDs ::= SEQUENCE
{
    iMSI   [1] IMSI OPTIONAL,
    mSISDN [2] MSISDN OPTIONAL,
    iMEI   [3] IMEI OPTIONAL
}

EPSPDNCnxInfo ::= SEQUENCE
{
    pGWS8ControlPlaneFTEID [1] FTEID,
    linkedBearerID         [2] EPSBearerID OPTIONAL
}

EPSBearerInfo ::= SEQUENCE OF EPSBearers

EPSBearers ::= SEQUENCE
{
    ePSBearerID         [1] EPSBearerID,
    pGWS8UserPlaneFTEID [2] FTEID,
    qCI                 [3] QCI
}

EPSBearerContext ::= SEQUENCE
{
    ePSBearerID     [1] EPSBearerID,
    uPGTPTunnelInfo [2] GTPTunnelInfo,
    bearerQOS       [3] EPSBearerQOS
}

EPSBearerContextCreated ::= SEQUENCE
{
    ePSBearerID                  [1] EPSBearerID,
    cause                        [2] EPSBearerCreationCauseValue,
    gTPTunnelInfo                [3] GTPTunnelInfo OPTIONAL,
    bearerQOS                    [4] EPSBearerQOS OPTIONAL,
    protocolConfigurationOptions [5] PDNProtocolConfigurationOptions OPTIONAL
}

EPSBearerContextModified ::= SEQUENCE
{
    ePSBearerID                  [1] EPSBearerID,
    cause                        [2] EPSBearerModificationCauseValue,
    gTPTunnelInfo                [3] GTPTunnelInfo OPTIONAL,
    bearerQOS                    [4] EPSBearerQOS OPTIONAL,
    protocolConfigurationOptions [5] PDNProtocolConfigurationOptions OPTIONAL,
    linkedBearerIDs              [6] SEQUENCE OF EPSBearerID OPTIONAL
}

EPSBearersDeleted ::= SEQUENCE
{
    linkedEPSBearerID            [1] EPSBearerID OPTIONAL,
    ePSBearerIDs                 [2] SEQUENCE OF EPSBearerID OPTIONAL,
    protocolConfigurationOptions [3] PDNProtocolConfigurationOptions OPTIONAL,
    cause                        [4] EPSBearerDeletionCauseValue OPTIONAL,
    deleteBearerResponse         [5] EPSDeleteBearerResponse
}

EPSDeleteBearerResponse ::= SEQUENCE
{
    cause                        [1] EPSBearerDeletionCauseValue,
    linkedEPSBearerID            [2] EPSBearerID OPTIONAL,
    bearerContexts               [3] SEQUENCE OF EPSDeleteBearerContext OPTIONAL,
    protocolConfigurationOptions [4] PDNProtocolConfigurationOptions OPTIONAL
}

EPSDeleteBearerContext ::= SEQUENCE
{
    cause                        [1] EPSBearerDeletionCauseValue,
    ePSBearerID                  [2] EPSBearerID,
    protocolConfigurationOptions [3] PDNProtocolConfigurationOptions OPTIONAL,
    rANNASCause                  [4] EPSRANNASCause OPTIONAL
}

EPSBearerContextForRemoval ::= SEQUENCE
{
    ePSBearerID [1] EPSBearerID,
    cause       [2] EPSBearerRemovalCauseValue
}

EPSBearerCreationCauseValue ::= INTEGER (0..255)

EPSBearerDeletionCauseValue ::= INTEGER (0..255)

EPSBearerModificationCauseValue ::= INTEGER (0..255)

EPSBearerRemovalCauseValue ::= INTEGER (0..255)

EPSBearerQOS ::= SEQUENCE
{
    qCI                       [1] QCI OPTIONAL,
    maximumUplinkBitRate      [2] BitrateBinKBPS OPTIONAL,
    maximumDownlinkBitRate    [3] BitrateBinKBPS OPTIONAL,
    guaranteedUplinkBitRate   [4] BitrateBinKBPS OPTIONAL,
    guaranteedDownlinkBitRate [5] BitrateBinKBPS OPTIONAL,
    priorityLevel             [6] EPSQOSPriority OPTIONAL
}

EPSRANNASCause ::= OCTET STRING

EPSQOSPriority ::= INTEGER (1..15)

BitrateBinKBPS ::= OCTET STRING

EPSGTPTunnels ::= SEQUENCE
{
    controlPlaneSenderFTEID  [1] FTEID OPTIONAL,
    controlPlanePGWS5S8FTEID [2] FTEID OPTIONAL,
    s1UeNodeBFTEID           [3] FTEID OPTIONAL,
    s5S8SGWFTEID             [4] FTEID OPTIONAL,
    s5S8PGWFTEID             [5] FTEID OPTIONAL,
    s2bUePDGFTEID            [6] FTEID OPTIONAL,
    s2aUePDGFTEID            [7] FTEID OPTIONAL
}

EPSPDNConnectionRequestType ::= ENUMERATED
{
    initialRequest(1),
    handover(2),
    rLOS(3),
    emergency(4),
    handoverOfEmergencyBearerServices(5),
    reserved(6)
}

EPSPDNConnectionReleaseScopeIndication ::= BOOLEAN

EPSPDNFailedProcedure ::= CHOICE
{
    ePSPDNConnectionEstablishment [1] EPSPDNConnectionEstablishment,
    ePSPDNConnectionModification  [2] EPSPDNConnectionModification,
    ePSPDNConnectionRelease       [3] EPSPDNConnectionRelease
}

FiveGSInterworkingInfo ::= SEQUENCE
{
    fiveGSInterworkingIndicator  [1] FiveGSInterworkingIndicator,
    fiveGSInterworkingWithoutN26 [2] FiveGSInterworkingWithoutN26,
    fiveGCNotRestrictedSupport   [3] FiveGCNotRestrictedSupport
}

FiveGSInterworkingIndicator ::= BOOLEAN

FiveGSInterworkingWithoutN26 ::= BOOLEAN

FiveGCNotRestrictedSupport ::= BOOLEAN

PDNConnectionIndicationFlags ::= OCTET STRING

PDNHandoverIndication ::= BOOLEAN

PDNNBIFOMSupport ::= BOOLEAN

PDNProtocolConfigurationOptions ::= SEQUENCE
{
    requestPCO   [1] PDNPCO OPTIONAL,
    requestAPCO  [2] PDNPCO OPTIONAL,
    requestEPCO  [3] PDNPCO OPTIONAL,
    responsePCO  [4] PDNPCO OPTIONAL,
    responseAPCO [5] PDNPCO OPTIONAL,
    responseEPCO [6] PDNPCO OPTIONAL
}

PDNPCO ::= OCTET STRING

PGWChangeIndication ::= BOOLEAN

PGWRNSI ::= BOOLEAN

QCI ::= INTEGER (0..255)

GTPTunnelInfo ::= SEQUENCE
{
    fiveGSGTPTunnels [1] FiveGSGTPTunnels OPTIONAL,
    ePSGTPTunnels    [2] EPSGTPTunnels OPTIONAL
}

RestorationOfPDNConnectionsSupport ::= BOOLEAN

-- ==================
-- 5G UPF definitions
-- ==================

UPFCCPDU ::= OCTET STRING

-- See clause 6.2.3.8 for the details of this structure
ExtendedUPFCCPDU ::= SEQUENCE
{
    payload [1] UPFCCPDUPayload,
    qFI     [2] QFI OPTIONAL
}

-- =================
-- 5G UPF parameters
-- =================

UPFCCPDUPayload ::= CHOICE
{
    uPFIPCC           [1] OCTET STRING,
    uPFEthernetCC     [2] OCTET STRING,
    uPFUnstructuredCC [3] OCTET STRING
}

QFI ::= INTEGER (0..63)

-- ==================
-- 5G UDM definitions
-- ==================

UDMServingSystemMessage ::= SEQUENCE
{
    sUPI                        [1] SUPI,
    pEI                         [2] PEI OPTIONAL,
    gPSI                        [3] GPSI OPTIONAL,
    gUAMI                       [4] GUAMI OPTIONAL,
    gUMMEI                      [5] GUMMEI OPTIONAL,
    pLMNID                      [6] PLMNID OPTIONAL,
    servingSystemMethod         [7] UDMServingSystemMethod,
    serviceID                   [8] ServiceID OPTIONAL,
    roamingIndicator            [9] RoamingIndicator OPTIONAL
}

UDMSubscriberRecordChangeMessage ::= SEQUENCE
{
    sUPI                           [1] SUPI OPTIONAL,
    pEI                            [2] PEI OPTIONAL,
    gPSI                           [3] GPSI OPTIONAL,
    oldPEI                         [4] PEI OPTIONAL,
    oldSUPI                        [5] SUPI OPTIONAL,
    oldGPSI                        [6] GPSI OPTIONAL,
    oldserviceID                   [7] ServiceID OPTIONAL,
    subscriberRecordChangeMethod   [8] UDMSubscriberRecordChangeMethod,
    serviceID                      [9] ServiceID OPTIONAL
}

UDMCancelLocationMessage ::= SEQUENCE
{
    sUPI                        [1] SUPI,
    pEI                         [2] PEI OPTIONAL,
    gPSI                        [3] GPSI OPTIONAL,
    gUAMI                       [4] GUAMI OPTIONAL,
    pLMNID                      [5] PLMNID OPTIONAL,
    cancelLocationMethod        [6] UDMCancelLocationMethod,
    aMFDeregistrationInfo       [7] UDMAMFDeregistrationInfo OPTIONAL,
    deregistrationData          [8] UDMDeregistrationData OPTIONAL
}

UDMLocationInformationResult ::= SEQUENCE
{
    sUPI                     [1] SUPI,
    pEI                      [2] PEI OPTIONAL,
    gPSI                     [3] GPSI OPTIONAL,
    locationInfoRequest      [4] UDMLocationInfoRequest,
    vPLMNID                  [5] PLMNID OPTIONAL,
    currentLocationIndicator [6] BOOLEAN OPTIONAL,
    aMFInstanceID            [7] NFID OPTIONAL,
    sMSFInstanceID           [8] NFID OPTIONAL,
    location                 [9] Location OPTIONAL,
    rATType                  [10] RATType OPTIONAL,
    problemDetails           [11] UDMProblemDetails OPTIONAL
}

UDMUEInformationResponse ::= SEQUENCE
{
    sUPI                        [1] SUPI,
    tADSInfo                    [2] UEContextInfo OPTIONAL,
    fiveGSUserStateInfo         [3] FiveGSUserStateInfo OPTIONAL,
    fiveGSRVCCInfo              [4] FiveGSRVCCInfo OPTIONAL,
    problemDetails              [5] UDMProblemDetails OPTIONAL
}

UDMUEAuthenticationResponse ::= SEQUENCE
{
    sUPI                        [1] SUPI,
    authenticationInfoRequest   [2] UDMAuthenticationInfoRequest,
    aKMAIndicator               [3] BOOLEAN OPTIONAL,
    problemDetails              [4] UDMProblemDetails OPTIONAL,
    authAAA                     [5] BOOLEAN OPTIONAL,
    pvsInfo                     [6] ServerAddressingInfoList OPTIONAL
}

UDMStartOfInterceptionWithRegisteredTarget ::= SEQUENCE
{
    sUPI                        [1] SUPI,
    gPSI                        [2] GPSI OPTIONAL,
    uDMSubscriptionDataSets     [3] SBIType
}

UDMProSeTargetIdentifierDeconcealment ::= SEQUENCE
{
    sUPI                        [1] SUPI,
    sUCI                        [2] SUCI
}

UDMProSeTargetAuthentication ::= SEQUENCE
{
    servingNetworkName           [1] UTF8String,
    relayServiceCode             [2] INTEGER,
    authenticationType           [3] PrimaryAuthenticationType,
    sUPI                         [4] SUPI
}

ServerAddressingInfoList ::= SEQUENCE (SIZE(1..MAX)) OF ServerAddressingInfo

ServerAddressingInfo ::= SEQUENCE
{
    iPv4Address [1] IPv4Address OPTIONAL,
    iPv6Address [2] IPv6Address OPTIONAL,
    fQDNList    [3] FQDNList OPTIONAL
}

FQDNList ::= SEQUENCE (SIZE(1..MAX)) OF FQDN

-- =================
-- 5G UDM parameters
-- =================

UDMServingSystemMethod ::= ENUMERATED
{
    amf3GPPAccessRegistration(0),
    amfNon3GPPAccessRegistration(1),
    unknown(2)
}

UDMSubscriberRecordChangeMethod ::= ENUMERATED
{
    pEIChange(1),
    sUPIChange(2),
    gPSIChange(3),
    uEDeprovisioning(4),
    unknown(5),
    serviceIDChange(6),
    multipleIDChanges(7)
}

UDMCancelLocationMethod ::= ENUMERATED
{
    aMF3GPPAccessDeregistration(1),
    aMFNon3GPPAccessDeregistration(2),
    uDMDeregistration(3),
    unknown(4)
}

ServiceID ::= SEQUENCE
{
    nSSAI                     [1] NSSAI OPTIONAL,
    cAGID                     [2] SEQUENCE OF CAGID OPTIONAL
}

CAGID ::= UTF8String

UDMAuthenticationInfoRequest ::= SEQUENCE
{
    infoRequestType    [1] UDMInfoRequestType,
    rGAuthCtx          [2] SEQUENCE SIZE(1..MAX) OF SubscriberIdentifier,
    authType           [3] PrimaryAuthenticationType,
    servingNetworkName [4] PLMNID,
    aUSFInstanceID     [5] NFID OPTIONAL,
    cellCAGInfo        [6] CAGID OPTIONAL,
    n5GCIndicator      [7] BOOLEAN OPTIONAL
}

UDMLocationInfoRequest ::= SEQUENCE
{
    requested5GSLocation     [1] BOOLEAN OPTIONAL,
    requestedCurrentLocation [2] BOOLEAN OPTIONAL,
    requestedRATType         [3] BOOLEAN OPTIONAL,
    requestedTimeZone        [4] BOOLEAN OPTIONAL,
    requestedServingNode     [5] BOOLEAN OPTIONAL
}

UDMProblemDetails ::= SEQUENCE
{
    cause        [1] UDMProblemDetailsCause OPTIONAL
}

UDMProblemDetailsCause ::= CHOICE
{
    uDMDefinedCause       [1] UDMDefinedCause,
    otherCause            [2] UDMProblemDetailsOtherCause
}

UDMDefinedCause ::= ENUMERATED
{
    userNotFound(1),
    dataNotFound(2),
    contextNotFound(3),
    subscriptionNotFound(4),
    other(5)
}

UDMInfoRequestType ::= ENUMERATED
{
    hSS(1),
    aUSF(2),
    other(3)
}

UDMProblemDetailsOtherCause ::= SEQUENCE
{
    problemDetailsType   [1] UTF8String OPTIONAL,
    title                [2] UTF8String OPTIONAL,
    status               [3] INTEGER OPTIONAL,
    detail               [4] UTF8String OPTIONAL,
    instance             [5] UTF8String OPTIONAL,
    cause                [6] UTF8String OPTIONAL,
    uDMInvalidParameters [7] UDMInvalidParameters,
    uDMSupportedFeatures [8] UTF8String
}

UDMInvalidParameters ::= SEQUENCE
{
    parameter    [1] UTF8String OPTIONAL,
    reason       [2] UTF8String OPTIONAL
}

RoamingIndicator ::= BOOLEAN

UDMAMFDeregistrationInfo ::= SEQUENCE
{
    gUAMI                   [1] GUAMI,
    purgeFlag               [2] BOOLEAN
}

UDMDeregistrationData ::= SEQUENCE
{
    deregReason             [1] UDMDeregReason OPTIONAL,
    accessType              [2] AccessType OPTIONAL,
    pDUSessionID            [3] PDUSessionID OPTIONAL
}

UDMDeregReason ::= ENUMERATED
{
    uEInitialRegistration(1),
    uERegistrationAreaChange(2),
    subscriptionWithdrawn(3),
    fiveGSToEPSMobility(4),
    fiveGSToEPSMobilityUeInitialRegistration(5),
    reregistrationRequired(6),
    sMFContextTransferred(7),
    duplicatePDUSession(8),
    fiveGSRVCCToUTRANMobility(9),
    pDUSessionReactivationRequired(10),
    disasterConditionTerminated(11)
}
-- ===================
-- 5G SMSF definitions
-- ===================

-- See clause 6.2.5.3 for details of this structure
SMSMessage ::= SEQUENCE
{
    originatingSMSParty         [1] SMSParty,
    terminatingSMSParty         [2] SMSParty,
    direction                   [3] Direction,
    linkTransferStatus          [4] SMSTransferStatus,
    otherMessage                [5] SMSOtherMessageIndication OPTIONAL,
    location                    [6] Location OPTIONAL,
    peerNFAddress               [7] SMSNFAddress OPTIONAL,
    peerNFType                  [8] SMSNFType OPTIONAL,
    sMSTPDUData                 [9] SMSTPDUData OPTIONAL,
    messageType                 [10] SMSMessageType OPTIONAL,
    rPMessageReference          [11] SMSRPMessageReference OPTIONAL
}

SMSReport ::= SEQUENCE
{
    location           [1] Location OPTIONAL,
    sMSTPDUData        [2] SMSTPDUData,
    messageType        [3] SMSMessageType,
    rPMessageReference [4] SMSRPMessageReference
}

-- ==================
-- 5G SMSF parameters
-- ==================

SMSAddress ::= OCTET STRING(SIZE(2..12))

SMSMessageType ::= ENUMERATED
{
    deliver(1),
    deliverReportAck(2),
    deliverReportError(3),
    statusReport(4),
    command(5),
    submit(6),
    submitReportAck(7),
    submitReportError(8),
    reserved(9)
}

SMSParty ::= SEQUENCE
{
    sUPI        [1] SUPI OPTIONAL,
    pEI         [2] PEI OPTIONAL,
    gPSI        [3] GPSI OPTIONAL,
    sMSAddress  [4] SMSAddress OPTIONAL
}

SMSTransferStatus ::= ENUMERATED
{
    transferSucceeded(1),
    transferFailed(2),
    undefined(3)
}

SMSOtherMessageIndication ::= BOOLEAN

SMSNFAddress ::= CHOICE
{
    iPAddress   [1] IPAddress,
    e164Number  [2] E164Number
}

SMSNFType ::= ENUMERATED
{
    sMSGMSC(1),
    iWMSC(2),
    sMSRouter(3)
}

SMSRPMessageReference ::= INTEGER (0..255)

SMSTPDUData ::= CHOICE
{
    sMSTPDU              [1] SMSTPDU,
    truncatedSMSTPDU     [2] TruncatedSMSTPDU,
    redactedSMSTPDU      [3] SMSTPDU,
    threeGPP2SMSTPDU     [4] ThreeGPP2SMSTPDU,
    redacted3GPP2SMSTPDU [5] ThreeGPP2SMSTPDU
}

SMSTPDU ::= OCTET STRING (SIZE(1..270))

ThreeGPP2SMSTPDU ::= OCTET STRING

TruncatedSMSTPDU ::= OCTET STRING (SIZE(1..130))

-- ===============
-- MMS definitions
-- ===============

MMSSend ::= SEQUENCE
{
    transactionID       [1]  UTF8String,
    version             [2]  MMSVersion,
    dateTime            [3]  Timestamp,
    originatingMMSParty [4]  MMSParty,
    terminatingMMSParty [5]  SEQUENCE OF MMSParty OPTIONAL,
    cCRecipients        [6]  SEQUENCE OF MMSParty OPTIONAL,
    bCCRecipients       [7]  SEQUENCE OF MMSParty OPTIONAL,
    direction           [8]  MMSDirection,
    subject             [9]  MMSSubject OPTIONAL,
    messageClass        [10]  MMSMessageClass OPTIONAL,
    expiry              [11] MMSExpiry,
    desiredDeliveryTime [12] Timestamp OPTIONAL,
    priority            [13] MMSPriority OPTIONAL,
    senderVisibility    [14] BOOLEAN OPTIONAL,
    deliveryReport      [15] BOOLEAN OPTIONAL,
    readReport          [16] BOOLEAN OPTIONAL,
    store               [17] BOOLEAN OPTIONAL,
    state               [18] MMState OPTIONAL,
    flags               [19] MMFlags OPTIONAL,
    replyCharging       [20] MMSReplyCharging OPTIONAL,
    applicID            [21] UTF8String OPTIONAL,
    replyApplicID       [22] UTF8String OPTIONAL,
    auxApplicInfo       [23] UTF8String OPTIONAL,
    contentClass        [24] MMSContentClass OPTIONAL,
    dRMContent          [25] BOOLEAN OPTIONAL,
    adaptationAllowed   [26] MMSAdaptation OPTIONAL,
    contentType         [27] MMSContentType,
    responseStatus      [28] MMSResponseStatus,
    responseStatusText  [29] UTF8String OPTIONAL,
    messageID           [30] UTF8String
}

MMSSendByNonLocalTarget ::= SEQUENCE
{
    version             [1]  MMSVersion,
    transactionID       [2]  UTF8String,
    messageID           [3]  UTF8String,
    terminatingMMSParty [4]  SEQUENCE OF MMSParty,
    originatingMMSParty [5]  MMSParty,
    direction           [6]  MMSDirection,
    contentType         [7]  MMSContentType,
    messageClass        [8]  MMSMessageClass OPTIONAL,
    dateTime            [9]  Timestamp,
    expiry              [10] MMSExpiry OPTIONAL,
    deliveryReport      [11] BOOLEAN OPTIONAL,
    priority            [12] MMSPriority OPTIONAL,
    senderVisibility    [13] BOOLEAN OPTIONAL,
    readReport          [14] BOOLEAN OPTIONAL,
    subject             [15] MMSSubject OPTIONAL,
    forwardCount        [16] INTEGER OPTIONAL,
    previouslySentBy    [17] MMSPreviouslySentBy OPTIONAL,
    prevSentByDateTime  [18] Timestamp OPTIONAL,
    applicID            [19] UTF8String OPTIONAL,
    replyApplicID       [20] UTF8String OPTIONAL,
    auxApplicInfo       [21] UTF8String OPTIONAL,
    contentClass        [22] MMSContentClass OPTIONAL,
    dRMContent          [23] BOOLEAN OPTIONAL,
    adaptationAllowed   [24] MMSAdaptation OPTIONAL
}

MMSNotification ::= SEQUENCE
{
    transactionID           [1]  UTF8String,
    version                 [2]  MMSVersion,
    originatingMMSParty     [3]  MMSParty OPTIONAL,
    direction               [4]  MMSDirection,
    subject                 [5]  MMSSubject OPTIONAL,
    deliveryReportRequested [6]  BOOLEAN OPTIONAL,
    stored                  [7]  BOOLEAN OPTIONAL,
    messageClass            [8]  MMSMessageClass,
    priority                [9]  MMSPriority OPTIONAL,
    messageSize             [10]  INTEGER,
    expiry                  [11] MMSExpiry,
    replyCharging           [12] MMSReplyCharging OPTIONAL
}

MMSSendToNonLocalTarget ::= SEQUENCE
{
    version             [1]  MMSVersion,
    transactionID       [2]  UTF8String,
    messageID           [3]  UTF8String,
    terminatingMMSParty [4]  SEQUENCE OF MMSParty,
    originatingMMSParty [5]  MMSParty,
    direction           [6]  MMSDirection,
    contentType         [7]  MMSContentType,
    messageClass        [8]  MMSMessageClass OPTIONAL,
    dateTime            [9]  Timestamp,
    expiry              [10] MMSExpiry OPTIONAL,
    deliveryReport      [11] BOOLEAN OPTIONAL,
    priority            [12] MMSPriority OPTIONAL,
    senderVisibility    [13] BOOLEAN OPTIONAL,
    readReport          [14] BOOLEAN OPTIONAL,
    subject             [15] MMSSubject OPTIONAL,
    forwardCount        [16] INTEGER OPTIONAL,
    previouslySentBy    [17] MMSPreviouslySentBy OPTIONAL,
    prevSentByDateTime  [18] Timestamp OPTIONAL,
    applicID            [19] UTF8String OPTIONAL,
    replyApplicID       [20] UTF8String OPTIONAL,
    auxApplicInfo       [21] UTF8String OPTIONAL,
    contentClass        [22] MMSContentClass OPTIONAL,
    dRMContent          [23] BOOLEAN OPTIONAL,
    adaptationAllowed   [24] MMSAdaptation OPTIONAL
}

MMSNotificationResponse ::= SEQUENCE
{
    transactionID [1] UTF8String,
    version       [2] MMSVersion,
    direction     [3] MMSDirection,
    status        [4] MMStatus,
    reportAllowed [5] BOOLEAN OPTIONAL
}

MMSRetrieval ::= SEQUENCE
{
    transactionID       [1]  UTF8String,
    version             [2]  MMSVersion,
    messageID           [3]  UTF8String,
    dateTime            [4]  Timestamp,
    originatingMMSParty [5]  MMSParty OPTIONAL,
    previouslySentBy    [6]  MMSPreviouslySentBy OPTIONAL,
    prevSentByDateTime  [7]  Timestamp OPTIONAL,
    terminatingMMSParty [8]  SEQUENCE OF MMSParty OPTIONAL,
    cCRecipients        [9]  SEQUENCE OF MMSParty OPTIONAL,
    direction           [10] MMSDirection,
    subject             [11] MMSSubject OPTIONAL,
    state               [12] MMState OPTIONAL,
    flags               [13] MMFlags OPTIONAL,
    messageClass        [14] MMSMessageClass OPTIONAL,
    priority            [15] MMSPriority,
    deliveryReport      [16] BOOLEAN OPTIONAL,
    readReport          [17] BOOLEAN OPTIONAL,
    replyCharging       [18] MMSReplyCharging OPTIONAL,
    retrieveStatus      [19] MMSRetrieveStatus OPTIONAL,
    retrieveStatusText  [20] UTF8String OPTIONAL,
    applicID            [21] UTF8String OPTIONAL,
    replyApplicID       [22] UTF8String OPTIONAL,
    auxApplicInfo       [23] UTF8String OPTIONAL,
    contentClass        [24] MMSContentClass OPTIONAL,
    dRMContent          [25] BOOLEAN OPTIONAL,
    replaceID           [26] UTF8String OPTIONAL,
    contentType         [27] UTF8String OPTIONAL
}

MMSDeliveryAck ::= SEQUENCE
{
    transactionID [1] UTF8String,
    version       [2] MMSVersion,
    reportAllowed [3] BOOLEAN OPTIONAL,
    status        [4] MMStatus,
    direction     [5] MMSDirection
}

MMSForward ::= SEQUENCE
{
    transactionID         [1]  UTF8String,
    version               [2]  MMSVersion,
    dateTime              [3]  Timestamp OPTIONAL,
    originatingMMSParty   [4]  MMSParty,
    terminatingMMSParty   [5]  SEQUENCE OF MMSParty OPTIONAL,
    cCRecipients          [6]  SEQUENCE OF MMSParty OPTIONAL,
    bCCRecipients         [7]  SEQUENCE OF MMSParty OPTIONAL,
    direction             [8]  MMSDirection,
    expiry                [9]  MMSExpiry OPTIONAL,
    desiredDeliveryTime   [10] Timestamp OPTIONAL,
    deliveryReportAllowed [11] BOOLEAN OPTIONAL,
    deliveryReport        [12] BOOLEAN OPTIONAL,
    store                 [13] BOOLEAN OPTIONAL,
    state                 [14] MMState OPTIONAL,
    flags                 [15] MMFlags OPTIONAL,
    contentLocationReq    [16] UTF8String,
    replyCharging         [17] MMSReplyCharging OPTIONAL,
    responseStatus        [18] MMSResponseStatus,
    responseStatusText    [19] UTF8String  OPTIONAL,
    messageID             [20] UTF8String OPTIONAL,
    contentLocationConf   [21] UTF8String OPTIONAL,
    storeStatus           [22] MMSStoreStatus OPTIONAL,
    storeStatusText       [23] UTF8String OPTIONAL
}

MMSDeleteFromRelay ::= SEQUENCE
{
    transactionID        [1] UTF8String,
    version              [2] MMSVersion,
    direction            [3] MMSDirection,
    contentLocationReq   [4] SEQUENCE OF UTF8String,
    contentLocationConf  [5] SEQUENCE OF UTF8String,
    deleteResponseStatus [6] MMSDeleteResponseStatus,
    deleteResponseText   [7] SEQUENCE OF UTF8String
}

MMSMBoxStore ::= SEQUENCE
{
    transactionID       [1] UTF8String,
    version             [2] MMSVersion,
    direction           [3] MMSDirection,
    contentLocationReq  [4] UTF8String,
    state               [5] MMState OPTIONAL,
    flags               [6] MMFlags OPTIONAL,
    contentLocationConf [7] UTF8String OPTIONAL,
    storeStatus         [8] MMSStoreStatus,
    storeStatusText     [9] UTF8String OPTIONAL
}

MMSMBoxUpload ::= SEQUENCE
{
    transactionID       [1]  UTF8String,
    version             [2]  MMSVersion,
    direction           [3]  MMSDirection,
    state               [4]  MMState OPTIONAL,
    flags               [5]  MMFlags OPTIONAL,
    contentType         [6]  UTF8String,
    contentLocation     [7]  UTF8String OPTIONAL,
    storeStatus         [8]  MMSStoreStatus,
    storeStatusText     [9]  UTF8String OPTIONAL,
    mMessages           [10] SEQUENCE OF MMBoxDescription
}

MMSMBoxDelete ::= SEQUENCE
{
    transactionID       [1] UTF8String,
    version             [2] MMSVersion,
    direction           [3] MMSDirection,
    contentLocationReq  [4] SEQUENCE OF UTF8String,
    contentLocationConf [5] SEQUENCE OF UTF8String OPTIONAL,
    responseStatus      [6] MMSDeleteResponseStatus,
    responseStatusText  [7] UTF8String OPTIONAL
}

MMSDeliveryReport ::= SEQUENCE
{
    version             [1] MMSVersion,
    messageID           [2] UTF8String,
    terminatingMMSParty [3] SEQUENCE OF MMSParty,
    mMSDateTime         [4] Timestamp,
    responseStatus      [5] MMSResponseStatus,
    responseStatusText  [6] UTF8String OPTIONAL,
    applicID            [7] UTF8String OPTIONAL,
    replyApplicID       [8] UTF8String OPTIONAL,
    auxApplicInfo       [9] UTF8String OPTIONAL
}

MMSDeliveryReportNonLocalTarget ::= SEQUENCE
{
    version             [1]  MMSVersion,
    transactionID       [2]  UTF8String,
    messageID           [3]  UTF8String,
    terminatingMMSParty [4]  SEQUENCE OF MMSParty,
    originatingMMSParty [5]  MMSParty,
    direction           [6]  MMSDirection,
    mMSDateTime         [7]  Timestamp,
    forwardToOriginator [8]  BOOLEAN OPTIONAL,
    status              [9]  MMStatus,
    statusExtension     [10] MMStatusExtension,
    statusText          [11] MMStatusText,
    applicID            [12] UTF8String OPTIONAL,
    replyApplicID       [13] UTF8String OPTIONAL,
    auxApplicInfo       [14] UTF8String OPTIONAL
}

MMSReadReport ::= SEQUENCE
{
    version             [1] MMSVersion,
    messageID           [2] UTF8String,
    terminatingMMSParty [3] SEQUENCE OF MMSParty,
    originatingMMSParty [4] SEQUENCE OF MMSParty,
    direction           [5] MMSDirection,
    mMSDateTime         [6] Timestamp,
    readStatus          [7] MMSReadStatus,
    applicID            [8] UTF8String OPTIONAL,
    replyApplicID       [9] UTF8String OPTIONAL,
    auxApplicInfo       [10] UTF8String OPTIONAL
}

MMSReadReportNonLocalTarget ::= SEQUENCE
{
    version             [1] MMSVersion,
    transactionID       [2] UTF8String,
    terminatingMMSParty [3] SEQUENCE OF MMSParty,
    originatingMMSParty [4] SEQUENCE OF MMSParty,
    direction           [5] MMSDirection,
    messageID           [6] UTF8String,
    mMSDateTime         [7] Timestamp,
    readStatus          [8] MMSReadStatus,
    readStatusText      [9] MMSReadStatusText OPTIONAL,
    applicID            [10] UTF8String OPTIONAL,
    replyApplicID       [11] UTF8String OPTIONAL,
    auxApplicInfo       [12] UTF8String OPTIONAL
}

MMSCancel ::= SEQUENCE
{
    transactionID [1] UTF8String,
    version       [2] MMSVersion,
    cancelID      [3] UTF8String,
    direction     [4] MMSDirection
}

MMSMBoxViewRequest ::= SEQUENCE
{
    transactionID   [1]  UTF8String,
    version         [2]  MMSVersion,
    contentLocation [3]  UTF8String OPTIONAL,
    state           [4]  SEQUENCE OF MMState OPTIONAL,
    flags           [5]  SEQUENCE OF MMFlags OPTIONAL,
    start           [6]  INTEGER OPTIONAL,
    limit           [7]  INTEGER OPTIONAL,
    attributes      [8]  SEQUENCE OF UTF8String OPTIONAL,
    totals          [9]  INTEGER OPTIONAL,
    quotas          [10] MMSQuota OPTIONAL
}

MMSMBoxViewResponse ::= SEQUENCE
{
    transactionID   [1]  UTF8String,
    version         [2]  MMSVersion,
    contentLocation [3]  UTF8String OPTIONAL,
    state           [4]  SEQUENCE OF MMState OPTIONAL,
    flags           [5]  SEQUENCE OF MMFlags OPTIONAL,
    start           [6]  INTEGER OPTIONAL,
    limit           [7]  INTEGER OPTIONAL,
    attributes      [8]  SEQUENCE OF UTF8String OPTIONAL,
    mMSTotals       [9]  BOOLEAN OPTIONAL,
    mMSQuotas       [10] BOOLEAN OPTIONAL,
    mMessages       [11] SEQUENCE OF MMBoxDescription
}

MMBoxDescription ::= SEQUENCE
{
    contentLocation          [1]  UTF8String OPTIONAL,
    messageID                [2]  UTF8String OPTIONAL,
    state                    [3]  MMState OPTIONAL,
    flags                    [4]  SEQUENCE OF MMFlags OPTIONAL,
    dateTime                 [5]  Timestamp OPTIONAL,
    originatingMMSParty      [6]  MMSParty OPTIONAL,
    terminatingMMSParty      [7]  SEQUENCE OF MMSParty OPTIONAL,
    cCRecipients             [8]  SEQUENCE OF MMSParty OPTIONAL,
    bCCRecipients            [9]  SEQUENCE OF MMSParty OPTIONAL,
    messageClass             [10] MMSMessageClass OPTIONAL,
    subject                  [11] MMSSubject OPTIONAL,
    priority                 [12] MMSPriority OPTIONAL,
    deliveryTime             [13] Timestamp OPTIONAL,
    readReport               [14] BOOLEAN OPTIONAL,
    messageSize              [15] INTEGER OPTIONAL,
    replyCharging            [16] MMSReplyCharging OPTIONAL,
    previouslySentBy         [17] MMSPreviouslySentBy OPTIONAL,
    previouslySentByDateTime [18] Timestamp OPTIONAL,
    contentType              [19] UTF8String OPTIONAL
}

MMSConvertedFromEmail ::= SEQUENCE
{
    version             [1]  MMSVersion,
    transactionID       [2]  UTF8String,
    terminatingMMSParty [3]  SEQUENCE OF MMSParty,
    contentType         [4]  MMSContentType,
    originatingMMSParty [5]  MMSParty,
    messageClass        [6]  MMSMessageClass OPTIONAL,
    dateTime            [7]  Timestamp,
    expiry              [8]  MMSExpiry OPTIONAL,
    deliveryReport      [9]  BOOLEAN OPTIONAL,
    priority            [10] MMSPriority OPTIONAL,
    readReport          [11] BOOLEAN OPTIONAL,
    subject             [12] MMSSubject OPTIONAL,
    messageID           [13] UTF8String OPTIONAL
}

MMSConvertedToEmail ::= SEQUENCE
{
    version             [1]  MMSVersion,
    transactionID       [2]  UTF8String,
    terminatingMMSParty [3]  SEQUENCE OF MMSParty,
    contentType         [4]  MMSContentType,
    originatingMMSParty [5]  MMSParty,
    messageClass        [6]  MMSMessageClass OPTIONAL,
    dateTime            [7]  Timestamp,
    expiry              [8]  MMSExpiry OPTIONAL,
    desiredDeliveryTime [9]  Timestamp OPTIONAL,
    deliveryReport      [10] BOOLEAN OPTIONAL,
    priority            [11] MMSPriority OPTIONAL,
    senderVisibility    [12] BOOLEAN OPTIONAL,
    store               [13] BOOLEAN OPTIONAL,
    state               [14] MMState OPTIONAL,
    flags               [15] MMFlags OPTIONAL,
    readReport          [16] BOOLEAN OPTIONAL,
    subject             [17] MMSSubject OPTIONAL,
    messageID           [18] UTF8String OPTIONAL
}

-- =========
-- MMS CCPDU
-- =========

MMSCCPDU ::= SEQUENCE
{
    version    [1] MMSVersion,
    transactionID [2] UTF8String,
    mMSContent    [3] OCTET STRING
}

-- ==============
-- MMS parameters
-- ==============

MMSAdaptation ::= SEQUENCE
{
    allowed   [1] BOOLEAN,
    overriden [2] BOOLEAN
}

MMSCancelStatus ::= ENUMERATED
{
    cancelRequestSuccessfullyReceived(1),
    cancelRequestCorrupted(2)
}

MMSContentClass ::= ENUMERATED
{
    text(1),
    imageBasic(2),
    imageRich(3),
    videoBasic(4),
    videoRich(5),
    megaPixel(6),
    contentBasic(7),
    contentRich(8)
}

MMSContentType ::= UTF8String

MMSDeleteResponseStatus ::= ENUMERATED
{
    ok(1),
    errorUnspecified(2),
    errorServiceDenied(3),
    errorMessageFormatCorrupt(4),
    errorSendingAddressUnresolved(5),
    errorMessageNotFound(6),
    errorNetworkProblem(7),
    errorContentNotAccepted(8),
    errorUnsupportedMessage(9),
    errorTransientFailure(10),
    errorTransientSendingAddressUnresolved(11),
    errorTransientMessageNotFound(12),
    errorTransientNetworkProblem(13),
    errorTransientPartialSuccess(14),
    errorPermanentFailure(15),
    errorPermanentServiceDenied(16),
    errorPermanentMessageFormatCorrupt(17),
    errorPermanentSendingAddressUnresolved(18),
    errorPermanentMessageNotFound(19),
    errorPermanentContentNotAccepted(20),
    errorPermanentReplyChargingLimitationsNotMet(21),
    errorPermanentReplyChargingRequestNotAccepted(22),
    errorPermanentReplyChargingForwardingDenied(23),
    errorPermanentReplyChargingNotSupported(24),
    errorPermanentAddressHidingNotSupported(25),
    errorPermanentLackOfPrepaid(26)
}

MMSDirection ::= ENUMERATED
{
    fromTarget(0),
    toTarget(1)
}

MMSElementDescriptor ::= SEQUENCE
{
    reference [1] UTF8String,
    parameter [2] UTF8String     OPTIONAL,
    value     [3] UTF8String     OPTIONAL
}

MMSExpiry ::= SEQUENCE
{
    expiryPeriod [1] INTEGER,
    periodFormat [2] MMSPeriodFormat
}

MMFlags ::= SEQUENCE
{
    length     [1] INTEGER,
    flag       [2] MMStateFlag,
    flagString [3] UTF8String
}

MMSMessageClass ::= ENUMERATED
{
    personal(1),
    advertisement(2),
    informational(3),
    auto(4)
}

MMSParty ::= SEQUENCE
{
    mMSPartyIDs [1] SEQUENCE OF MMSPartyID,
    nonLocalID  [2] NonLocalID
}

MMSPartyID ::= CHOICE
{
    e164Number   [1] E164Number,
    emailAddress [2] EmailAddress,
    iMSI         [3] IMSI,
    iMPU         [4] IMPU,
    iMPI         [5] IMPI,
    sUPI         [6] SUPI,
    gPSI         [7] GPSI
}

MMSPeriodFormat ::= ENUMERATED
{
    absolute(1),
    relative(2)
}

MMSPreviouslySent ::= SEQUENCE
{
    previouslySentByParty [1] MMSParty,
    sequenceNumber        [2] INTEGER,
    previousSendDateTime  [3] Timestamp
}

MMSPreviouslySentBy ::= SEQUENCE OF MMSPreviouslySent

MMSPriority ::= ENUMERATED
{
    low(1),
    normal(2),
    high(3)
}

MMSQuota ::= SEQUENCE
{
    quota     [1] INTEGER,
    quotaUnit [2] MMSQuotaUnit
}

MMSQuotaUnit ::= ENUMERATED
{
    numMessages(1),
    bytes(2)
}

MMSReadStatus ::= ENUMERATED
{
    read(1),
    deletedWithoutBeingRead(2)
}

MMSReadStatusText ::= UTF8String

MMSReplyCharging ::= ENUMERATED
{
    requested(0),
    requestedTextOnly(1),
    accepted(2),
    acceptedTextOnly(3)
}

MMSResponseStatus ::= ENUMERATED
{
    ok(1),
    errorUnspecified(2),
    errorServiceDenied(3),
    errorMessageFormatCorrupt(4),
    errorSendingAddressUnresolved(5),
    errorMessageNotFound(6),
    errorNetworkProblem(7),
    errorContentNotAccepted(8),
    errorUnsupportedMessage(9),
    errorTransientFailure(10),
    errorTransientSendingAddressUnresolved(11),
    errorTransientMessageNotFound(12),
    errorTransientNetworkProblem(13),
    errorTransientPartialSuccess(14),
    errorPermanentFailure(15),
    errorPermanentServiceDenied(16),
    errorPermanentMessageFormatCorrupt(17),
    errorPermanentSendingAddressUnresolved(18),
    errorPermanentMessageNotFound(19),
    errorPermanentContentNotAccepted(20),
    errorPermanentReplyChargingLimitationsNotMet(21),
    errorPermanentReplyChargingRequestNotAccepted(22),
    errorPermanentReplyChargingForwardingDenied(23),
    errorPermanentReplyChargingNotSupported(24),
    errorPermanentAddressHidingNotSupported(25),
    errorPermanentLackOfPrepaid(26)
}

MMSRetrieveStatus ::= ENUMERATED
{
    success(1),
    errorTransientFailure(2),
    errorTransientMessageNotFound(3),
    errorTransientNetworkProblem(4),
    errorPermanentFailure(5),
    errorPermanentServiceDenied(6),
    errorPermanentMessageNotFound(7),
    errorPermanentContentUnsupported(8)
}

MMSStoreStatus ::= ENUMERATED
{
    success(1),
    errorTransientFailure(2),
    errorTransientNetworkProblem(3),
    errorPermanentFailure(4),
    errorPermanentServiceDenied(5),
    errorPermanentMessageFormatCorrupt(6),
    errorPermanentMessageNotFound(7),
    errorMMBoxFull(8)
}

MMState ::= ENUMERATED
{
    draft(1),
    sent(2),
    new(3),
    retrieved(4),
    forwarded(5)
}

MMStateFlag ::= ENUMERATED
{
    add(1),
    remove(2),
    filter(3)
}

MMStatus ::= ENUMERATED
{
    expired(1),
    retrieved(2),
    rejected(3),
    deferred(4),
    unrecognized(5),
    indeterminate(6),
    forwarded(7),
    unreachable(8)
}

MMStatusExtension ::= ENUMERATED
{
    rejectionByMMSRecipient(0),
    rejectionByOtherRS(1)
}

MMStatusText ::= UTF8String

MMSSubject ::= UTF8String

MMSVersion ::= SEQUENCE
{
    majorVersion [1] INTEGER,
    minorVersion [2] INTEGER
}

-- ==================
-- 5G PTC definitions
-- ==================

PTCRegistration  ::= SEQUENCE
{
    pTCTargetInformation          [1] PTCTargetInformation,
    pTCServerURI                  [2] UTF8String,
    pTCRegistrationRequest        [3] PTCRegistrationRequest,
    pTCRegistrationOutcome        [4] PTCRegistrationOutcome
}

PTCSessionInitiation  ::= SEQUENCE
{
    pTCTargetInformation          [1] PTCTargetInformation,
    pTCDirection                  [2] Direction,
    pTCServerURI                  [3] UTF8String,
    pTCSessionInfo                [4] PTCSessionInfo,
    pTCOriginatingID              [5] PTCTargetInformation,
    pTCParticipants               [6] SEQUENCE OF PTCTargetInformation OPTIONAL,
    pTCParticipantPresenceStatus  [7] MultipleParticipantPresenceStatus OPTIONAL,
    location                      [8] Location OPTIONAL,
    pTCBearerCapability           [9] UTF8String OPTIONAL,
    pTCHost                       [10] PTCTargetInformation OPTIONAL
}

PTCSessionAbandon  ::= SEQUENCE
{
    pTCTargetInformation          [1] PTCTargetInformation,
    pTCDirection                  [2] Direction,
    pTCSessionInfo                [3] PTCSessionInfo,
    location                      [4] Location OPTIONAL,
    pTCAbandonCause               [5] INTEGER
}

PTCSessionStart  ::= SEQUENCE
{
    pTCTargetInformation          [1] PTCTargetInformation,
    pTCDirection                  [2] Direction,
    pTCServerURI                  [3] UTF8String,
    pTCSessionInfo                [4] PTCSessionInfo,
    pTCOriginatingID              [5] PTCTargetInformation,
    pTCParticipants               [6] SEQUENCE OF PTCTargetInformation OPTIONAL,
    pTCParticipantPresenceStatus  [7] MultipleParticipantPresenceStatus OPTIONAL,
    location                      [8] Location OPTIONAL,
    pTCHost                       [9] PTCTargetInformation OPTIONAL,
    pTCBearerCapability           [10] UTF8String OPTIONAL
}

PTCSessionEnd  ::= SEQUENCE
{
    pTCTargetInformation          [1] PTCTargetInformation,
    pTCDirection                  [2] Direction,
    pTCServerURI                  [3] UTF8String,
    pTCSessionInfo                [4] PTCSessionInfo,
    pTCParticipants               [5] SEQUENCE OF PTCTargetInformation OPTIONAL,
    location                      [6] Location OPTIONAL,
    pTCSessionEndCause            [7] PTCSessionEndCause
}

PTCStartOfInterception  ::= SEQUENCE
{
    pTCTargetInformation          [1] PTCTargetInformation,
    pTCDirection                  [2] Direction,
    preEstSessionID               [3] PTCSessionInfo OPTIONAL,
    pTCOriginatingID              [4] PTCTargetInformation,
    pTCSessionInfo                [5] PTCSessionInfo OPTIONAL,
    pTCHost                       [6] PTCTargetInformation OPTIONAL,
    pTCParticipants               [7] SEQUENCE OF PTCTargetInformation OPTIONAL,
    pTCMediaStreamAvail           [8] BOOLEAN OPTIONAL,
    pTCBearerCapability           [9] UTF8String OPTIONAL
}

PTCPreEstablishedSession  ::= SEQUENCE
{
    pTCTargetInformation          [1] PTCTargetInformation,
    pTCServerURI                  [2] UTF8String,
    rTPSetting                    [3] RTPSetting,
    pTCMediaCapability            [4] UTF8String,
    pTCPreEstSessionID            [5] PTCSessionInfo,
    pTCPreEstStatus               [6] PTCPreEstStatus,
    pTCMediaStreamAvail           [7] BOOLEAN OPTIONAL,
    location                      [8] Location OPTIONAL,
    pTCFailureCode                [9] PTCFailureCode OPTIONAL
}

PTCInstantPersonalAlert  ::= SEQUENCE
{
    pTCTargetInformation          [1] PTCTargetInformation,
    pTCIPAPartyID                 [2] PTCTargetInformation,
    pTCIPADirection               [3] Direction
}

PTCPartyJoin  ::= SEQUENCE
{
    pTCTargetInformation          [1] PTCTargetInformation,
    pTCDirection                  [2] Direction,
    pTCSessionInfo                [3] PTCSessionInfo,
    pTCParticipants               [4] SEQUENCE OF PTCTargetInformation OPTIONAL,
    pTCParticipantPresenceStatus  [5] MultipleParticipantPresenceStatus OPTIONAL,
    pTCMediaStreamAvail           [6] BOOLEAN OPTIONAL,
    pTCBearerCapability           [7] UTF8String OPTIONAL
}

PTCPartyDrop  ::= SEQUENCE
{
    pTCTargetInformation          [1] PTCTargetInformation,
    pTCDirection                  [2] Direction,
    pTCSessionInfo                [3] PTCSessionInfo,
    pTCPartyDrop                  [4] PTCTargetInformation,
    pTCParticipantPresenceStatus  [5] PTCParticipantPresenceStatus OPTIONAL
}

PTCPartyHold  ::= SEQUENCE
{
    pTCTargetInformation          [1] PTCTargetInformation,
    pTCDirection                  [2] Direction,
    pTCSessionInfo                [3] PTCSessionInfo,
    pTCParticipants               [4] SEQUENCE OF PTCTargetInformation OPTIONAL,
    pTCHoldID                     [5] SEQUENCE OF PTCTargetInformation,
    pTCHoldRetrieveInd            [6] BOOLEAN
}

PTCMediaModification  ::= SEQUENCE
{
    pTCTargetInformation          [1] PTCTargetInformation,
    pTCDirection                  [2] Direction,
    pTCSessionInfo                [3] PTCSessionInfo,
    pTCMediaStreamAvail           [4] BOOLEAN OPTIONAL,
    pTCBearerCapability           [5] UTF8String
}

PTCGroupAdvertisement  ::=SEQUENCE
{
    pTCTargetInformation          [1] PTCTargetInformation,
    pTCDirection                  [2] Direction,
    pTCIDList                     [3] SEQUENCE OF PTCTargetInformation OPTIONAL,
    pTCGroupAuthRule              [4] PTCGroupAuthRule OPTIONAL,
    pTCGroupAdSender              [5] PTCTargetInformation,
    pTCGroupNickname              [6] UTF8String OPTIONAL
}

PTCFloorControl  ::= SEQUENCE
{
    pTCTargetInformation          [1] PTCTargetInformation,
    pTCDirection                  [2] Direction,
    pTCSessioninfo                [3] PTCSessionInfo,
    pTCFloorActivity              [4] SEQUENCE OF PTCFloorActivity,
    pTCFloorSpeakerID             [5] PTCTargetInformation OPTIONAL,
    pTCMaxTBTime                  [6] INTEGER OPTIONAL,
    pTCQueuedFloorControl         [7] BOOLEAN OPTIONAL,
    pTCQueuedPosition             [8] INTEGER OPTIONAL,
    pTCTalkBurstPriority          [9] PTCTBPriorityLevel OPTIONAL,
    pTCTalkBurstReason            [10] PTCTBReasonCode OPTIONAL
}

PTCTargetPresence  ::= SEQUENCE
{
    pTCTargetInformation          [1] PTCTargetInformation,
    pTCTargetPresenceStatus       [2] PTCParticipantPresenceStatus
}

PTCParticipantPresence  ::= SEQUENCE
{
    pTCTargetInformation          [1] PTCTargetInformation,
    pTCParticipantPresenceStatus  [2] PTCParticipantPresenceStatus
}

PTCListManagement  ::= SEQUENCE
{
    pTCTargetInformation          [1] PTCTargetInformation,
    pTCDirection                  [2] Direction,
    pTCListManagementType         [3] PTCListManagementType OPTIONAL,
    pTCListManagementAction       [4] PTCListManagementAction OPTIONAL,
    pTCListManagementFailure      [5] PTCListManagementFailure OPTIONAL,
    pTCContactID                  [6] PTCTargetInformation OPTIONAL,
    pTCIDList                     [7] SEQUENCE OF PTCIDList OPTIONAL,
    pTCHost                       [8] PTCTargetInformation OPTIONAL
}

PTCAccessPolicy  ::= SEQUENCE
{
    pTCTargetInformation          [1] PTCTargetInformation,
    pTCDirection                  [2] Direction,
    pTCAccessPolicyType           [3] PTCAccessPolicyType OPTIONAL,
    pTCUserAccessPolicy           [4] PTCUserAccessPolicy OPTIONAL,
    pTCGroupAuthRule              [5] PTCGroupAuthRule OPTIONAL,
    pTCContactID                  [6] PTCTargetInformation OPTIONAL,
    pTCAccessPolicyFailure        [7] PTCAccessPolicyFailure OPTIONAL
}

-- =========
-- PTC CCPDU
-- =========

PTCCCPDU ::= OCTET STRING

-- =================
-- 5G PTC parameters
-- =================

PTCRegistrationRequest  ::= ENUMERATED
{
    register(1),
    reRegister(2),
    deRegister(3)
}

PTCRegistrationOutcome  ::= ENUMERATED
{
    success(1),
    failure(2)
}

PTCSessionEndCause  ::= ENUMERATED
{
    initiaterLeavesSession(1),
    definedParticipantLeaves(2),
    numberOfParticipants(3),
    sessionTimerExpired(4),
    pTCSpeechInactive(5),
    allMediaTypesInactive(6)
}

PTCTargetInformation  ::= SEQUENCE
{
    identifiers                [1] SEQUENCE SIZE(1..MAX) OF PTCIdentifiers
}

PTCIdentifiers  ::= CHOICE
{
    mCPTTID                    [1] UTF8String,
    instanceIdentifierURN      [2] UTF8String,
    pTCChatGroupID             [3] PTCChatGroupID,
    iMPU                       [4] IMPU,
    iMPI                       [5] IMPI
}

PTCSessionInfo  ::= SEQUENCE
{
    pTCSessionURI              [1] UTF8String,
    pTCSessionType             [2] PTCSessionType
}

PTCSessionType  ::= ENUMERATED
{
    ondemand(1),
    preEstablished(2),
    adhoc(3),
    prearranged(4),
    groupSession(5)
}

MultipleParticipantPresenceStatus  ::= SEQUENCE OF PTCParticipantPresenceStatus

PTCParticipantPresenceStatus  ::= SEQUENCE
{
    presenceID                 [1] PTCTargetInformation,
    presenceType               [2] PTCPresenceType,
    presenceStatus             [3] BOOLEAN
}

PTCPresenceType  ::= ENUMERATED
{
    pTCClient(1),
    pTCGroup(2)
}

PTCPreEstStatus  ::= ENUMERATED
{
    established(1),
    modified(2),
    released(3)
}

RTPSetting  ::= SEQUENCE
{
    iPAddress                  [1] IPAddress,
    portNumber                 [2] PortNumber
}

PTCIDList  ::= SEQUENCE
{
    pTCPartyID                 [1] PTCTargetInformation,
    pTCChatGroupID             [2] PTCChatGroupID
}

PTCChatGroupID  ::= SEQUENCE
{
    groupIdentity              [1] UTF8String
}

PTCFloorActivity  ::= ENUMERATED
{
    tBCPRequest(1),
    tBCPGranted(2),
    tBCPDeny(3),
    tBCPIdle(4),
    tBCPTaken(5),
    tBCPRevoke(6),
    tBCPQueued(7),
    tBCPRelease(8)
}

PTCTBPriorityLevel  ::= ENUMERATED
{
    preEmptive(1),
    highPriority(2),
    normalPriority(3),
    listenOnly(4)
}

PTCTBReasonCode  ::= ENUMERATED
{
    noQueuingAllowed(1),
    oneParticipantSession(2),
    listenOnly(3),
    exceededMaxDuration(4),
    tBPrevented(5)
}

PTCListManagementType  ::= ENUMERATED
{
    contactListManagementAttempt(1),
    groupListManagementAttempt(2),
    contactListManagementResult(3),
    groupListManagementResult(4),
    requestUnsuccessful(5)
}

PTCListManagementAction  ::= ENUMERATED
{
    create(1),
    modify(2),
    retrieve(3),
    delete(4),
    notify(5)
}

PTCAccessPolicyType  ::= ENUMERATED
{
    pTCUserAccessPolicyAttempt(1),
    groupAuthorizationRulesAttempt(2),
    pTCUserAccessPolicyQuery(3),
    groupAuthorizationRulesQuery(4),
    pTCUserAccessPolicyResult(5),
    groupAuthorizationRulesResult(6),
    requestUnsuccessful(7)
}

PTCUserAccessPolicy  ::= ENUMERATED
{
    allowIncomingPTCSessionRequest(1),
    blockIncomingPTCSessionRequest(2),
    allowAutoAnswerMode(3),
    allowOverrideManualAnswerMode(4)
}

PTCGroupAuthRule  ::= ENUMERATED
{
    allowInitiatingPTCSession(1),
    blockInitiatingPTCSession(2),
    allowJoiningPTCSession(3),
    blockJoiningPTCSession(4),
    allowAddParticipants(5),
    blockAddParticipants(6),
    allowSubscriptionPTCSessionState(7),
    blockSubscriptionPTCSessionState(8),
    allowAnonymity(9),
    forbidAnonymity(10)
}

PTCFailureCode  ::= ENUMERATED
{
    sessionCannotBeEstablished(1),
    sessionCannotBeModified(2)
}

PTCListManagementFailure  ::= ENUMERATED
{
    requestUnsuccessful(1),
    requestUnknown(2)
}

PTCAccessPolicyFailure  ::= ENUMERATED
{
    requestUnsuccessful(1),
    requestUnknown(2)
}

-- ===============
-- IMS definitions
-- ===============

-- See clause 7.12.4.2.1 for details of this structure
IMSMessage ::= SEQUENCE
{
    payload                      [1] IMSPayload,
    sessionDirection             [2] SessionDirection,
    voIPRoamingIndication        [3] VoIPRoamingIndication OPTIONAL,
    -- Tag [4] is not used.
    -- Tag [5] is not used.
    location                     [6] Location OPTIONAL,
    accessNetworkInformation     [7] SEQUENCE OF SIPAccessNetworkInformation OPTIONAL,
    cellularNetworkInformation   [8] SEQUENCE OF SIPCellularNetworkInformation OPTIONAL,
    numberTranslationInformation [9] SEQUENCE OF NumberTranslation OPTIONAL
}

-- See clause 7.12.4.2.2 for details of this structure
StartOfInterceptionForActiveIMSSession ::= SEQUENCE
{
    originatingId              [1] SEQUENCE OF IMPU,
    terminatingId              [2] IMPU,
    sDPState                   [3] SEQUENCE OF OCTET STRING OPTIONAL,
    diversionIdentity          [4] IMPU OPTIONAL,
    voIPRoamingIndication      [5] VoIPRoamingIndication OPTIONAL,
    -- Tag [6] is not used.
    location                   [7] Location OPTIONAL,
    accessNetworkInformation   [8] SEQUENCE OF SIPAccessNetworkInformation OPTIONAL,
    cellularNetworkInformation [9] SEQUENCE OF SIPCellularNetworkInformation OPTIONAL
}

-- See clause 7.12.4.2.3 for the details.
IMSCCUnavailable ::= SEQUENCE
{
    cCUnavailableReason   [1] UTF8String,
    sDPState              [2] OCTET STRING OPTIONAL
}

-- See clause 7.12.4.2.4 for details of this structure
IMSDataChannelSetup ::= SEQUENCE
{
    targetIdentity            [1] IMPU,
    callingIdentity           [2] IMPU OPTIONAL,
    calledIdentity            [3] SEQUENCE (SIZE (1..MAX)) OF IMPU OPTIONAL,
    sessionEventNotification  [4] SBIType OPTIONAL,
    mediaInstructionData      [5] SBIType OPTIONAL
}

-- See clause 7.12.4.2.5 for details of this structure
IMSDataChannelModification ::= SEQUENCE
{
    targetIdentity            [1] IMPU,
    callingIdentity           [2] IMPU OPTIONAL,
    calledIdentity            [3] SEQUENCE (SIZE (1..MAX)) OF IMPU OPTIONAL,
    sessionEventNotification  [4] SBIType OPTIONAL,
    mediaInstructions         [5] SBIType OPTIONAL
}

-- See clause 7.12.4.2.6 for details of this structure
IMSDataChannelTermination ::= SEQUENCE
{
    targetIdentity            [1] IMPU,
    callingIdentity           [2] IMPU OPTIONAL,
    calledIdentity            [3] SEQUENCE (SIZE (1..MAX)) OF IMPU OPTIONAL,
    sessionEventNotification  [4] SBIType OPTIONAL,
    mediaInstructionData      [5] SBIType OPTIONAL
}

-- See clause 7.12.4.2.7 for details of this structure
StartOfInterceptionWithEstablishedIMSDataChannel ::= SEQUENCE
{
    targetIdentity            [1] IMPU,
    callingIdentity           [2] IMPU OPTIONAL,
    calledIdentities          [3] SEQUENCE OF IMPU OPTIONAL,
    sessionEventNotification  [4] SBIType OPTIONAL,
    mediaInstructions         [5] SBIType OPTIONAL
}

-- =========
-- IMS CCPDU
-- =========

IMSCCPDU ::= SEQUENCE
{
    payload [1] IMSCCPDUPayload,
    sDPInfo [2] OCTET STRING OPTIONAL
}

IMSCCPDUPayload ::= OCTET STRING

-- ==============
-- IMS parameters
-- ==============

IMSPayload ::= CHOICE
{
    encapsulatedSIPMessage            [1] SIPMessage,
    modifiedSIPMessage                [2] ModifiedSIPMessage
}

ModifiedSIPMessage ::= SEQUENCE
{
    modifiedSIPContent [1] SIPMessage,
    modifications      [2] PayloadModifications
}

NumberTranslation ::= SEQUENCE
{
    partyIndication  [1] PartyIndication,
    translationInput [2] TranslationInput
}

PartyIndication ::= ENUMERATED
{
    callingParty(1),
    calledParty(2)
}

SIPMessage ::= SEQUENCE
{
    iPSourceAddress       [1] IPAddress,
    iPDestinationAddress  [2] IPAddress,
    sIPContent            [3] OCTET STRING
}

TranslationInput ::= CHOICE
{
    iMSIdentities [1] IMSSubscriberIDs
}

VoIPRoamingIndication ::= ENUMERATED
{
    roamingLBO(1),
    roamingS8HR(2),
    roamingN9HR(3)
}

SessionDirection ::= ENUMERATED
{
    fromTarget(1),
    toTarget(2),
    combined(3),
    indeterminate(4)
}

HeaderOnlyIndication ::= BOOLEAN

-- =================================
-- STIR/SHAKEN/RCD/eCNAM definitions
-- =================================

-- See clause 7.11.2.1.2 for details of this structure
STIRSHAKENSignatureGeneration ::= SEQUENCE
{
    pASSporTs                 [1] SEQUENCE OF PASSporT,
    encapsulatedSIPMessage    [2] SIPMessage OPTIONAL
}

-- See clause 7.11.2.1.3 for details of this structure
STIRSHAKENSignatureValidation ::= SEQUENCE
{
    pASSporTs                 [1] SEQUENCE OF PASSporT OPTIONAL,
    rCDTerminalDisplayInfo    [2] RCDDisplayInfo OPTIONAL,
    eCNAMTerminalDisplayInfo  [3] ECNAMDisplayInfo OPTIONAL,
    sHAKENValidationResult    [4] SHAKENValidationResult,
    sHAKENFailureStatusCode   [5] SHAKENFailureStatusCode OPTIONAL,
    encapsulatedSIPMessage    [6] SIPMessage OPTIONAL
}

-- ================================
-- STIR/SHAKEN/RCD/eCNAM parameters
-- ================================

PASSporT ::= SEQUENCE
{
    pASSporTHeader    [1] PASSporTHeader,
    pASSporTPayload   [2] PASSporTPayload,
    pASSporTSignature [3] OCTET STRING
}

PASSporTHeader ::= SEQUENCE
{
    type          [1] JWSTokenType,
    algorithm     [2] UTF8String,
    ppt           [3] UTF8String OPTIONAL,
    x5u           [4] UTF8String
}

JWSTokenType ::= ENUMERATED
{
    passport(1)
}

PASSporTPayload ::= SEQUENCE
{
    issuedAtTime    [1] GeneralizedTime,
    originator      [2] STIRSHAKENOriginator,
    destination     [3] STIRSHAKENDestinations,
    attestation     [4] Attestation,
    origId          [5] UTF8String,
    diversion       [6] STIRSHAKENDestination
}

STIRSHAKENOriginator ::= CHOICE
{
    telephoneNumber [1] STIRSHAKENTN,
    sTIRSHAKENURI   [2] UTF8String
}

STIRSHAKENDestinations ::= SEQUENCE OF STIRSHAKENDestination

STIRSHAKENDestination ::= CHOICE
{
    telephoneNumber [1] STIRSHAKENTN,
    sTIRSHAKENURI   [2] UTF8String
}


STIRSHAKENTN ::= CHOICE
{
    mSISDN [1] MSISDN
}

Attestation ::= ENUMERATED
{
    attestationA(1),
    attestationB(2),
    attestationC(3)
}

SHAKENValidationResult ::= ENUMERATED
{
    tNValidationPassed(1),
    tNValidationFailed(2),
    noTNValidation(3)
}

SHAKENFailureStatusCode ::= INTEGER

ECNAMDisplayInfo ::= SEQUENCE
{
    name           [1] UTF8String,
    additionalInfo [2] OCTET STRING OPTIONAL
}

RCDDisplayInfo ::= SEQUENCE
{
    name [1] UTF8String,
    jcd  [2] OCTET STRING OPTIONAL,
    jcl  [3] OCTET STRING OPTIONAL
}

-- =================
-- RCS Definitions
-- =================

-- See clause 7.13.3.2 for details of this structure
RCSRegistration ::= SEQUENCE
{
    rCSTargetIdentities              [1] SEQUENCE SIZE (1..MAX) OF RCSIdentity,
    rCSRegistrationType              [2] RCSRegistrationType,
    rCSRegistrationUpdateRequest     [3] IMSPayload,
    rCSRegistrationUpdateResponse    [4] IMSPayload,
    location                         [5] Location OPTIONAL
}

-- See clause 7.13.3.3 for details of this structure
RCSMessage ::= SEQUENCE
{
    rCSTargetIdentities     [1] SEQUENCE SIZE (1..MAX) OF RCSIdentity,
    groupChatSessionID      [2] RCSGroupChatSessionID OPTIONAL,
    originatingIdentity     [3] SEQUENCE SIZE (1..MAX) OF RCSIdentity,
    destinationIdentities   [4] RCSDestinations,
    direction               [5] Direction,
    messageType             [6] RCSMessageType,
    conversationID          [7] RCSConversationID,
    contributionID          [8] RCSContributionID,
    inReplyToContributionID [9] RCSContributionID OPTIONAL,
    messageID               [10] IMDNMessageID OPTIONAL,
    location                [11] Location OPTIONAL,
    messagePayload          [12] RCSPayload
}

-- See clause 7.13.3.4.2.1 for details of this structure
RCSSessionEstablishment ::= SEQUENCE
{
    rCSTargetIdentities     [1] SEQUENCE SIZE (1..MAX) OF RCSIdentity,
    conversationID          [2] RCSConversationID,
    contributionID          [3] RCSContributionID,
    inReplyToContributionID [4] RCSContributionID OPTIONAL,
    sessionReplaces         [5] RCSContributionID OPTIONAL,
    rCSSessionType          [6] RCSSessionType,
    sessionDirection        [7] Direction,
    rCSSessionMessage       [8] RCSSIPSessionMessage,
    location                [9] Location OPTIONAL
}

-- See clause 7.13.3.4.3.1 for details of this structure
RCSSessionModification ::= SEQUENCE
{
    rCSTargetIdentities     [1] SEQUENCE SIZE (1..MAX) OF RCSIdentity,
    conversationID          [2] RCSConversationID,
    contributionID          [3] RCSContributionID,
    inReplyToContributionID [4] RCSContributionID OPTIONAL,
    sessionReplaces         [5] RCSContributionID OPTIONAL,
    rCSSessionType          [6] RCSSessionType,
    sessionDirection        [7] Direction,
    sessionEndpoints        [8] RCSSessionEndpoints,
    rCSSIPSessionMessage    [9] RCSSIPSessionMessage,
    location                [10] Location OPTIONAL
}

-- See clause 7.13.3.4.4.1 for details of this structure
RCSSessionRelease ::= SEQUENCE
{
    rCSTargetIdentities     [1] SEQUENCE SIZE (1..MAX) OF RCSIdentity,
    conversationID          [2] RCSConversationID,
    contributionID          [3] RCSContributionID,
    rCSSessionType          [4] RCSSessionType,
    sessionDirection        [5] Direction,
    rCSSIPSessionMessage    [6] RCSSIPSessionMessage,
    location                [7] Location OPTIONAL
}

-- See clause 7.13.3.5 for details of this structure
RCSCapabilityDiscovery ::= SEQUENCE
{
    rCSTargetIdentities           [1] SEQUENCE SIZE (1..MAX) OF RCSIdentity,
    rCSTargetContactIdentities    [2] SEQUENCE SIZE (1..MAX) OF RCSIdentity OPTIONAL,
    sIPMessage                    [3] IMSPayload,
    direction                     [4] Direction,
    location                      [5] Location OPTIONAL
}

-- See clause 7.13.3.6.1.2 for details of this structure
StartOfInterceptForRegisteredRCSUser ::= SEQUENCE
{
    rCSTargetIdentities        [1] SEQUENCE SIZE (1..MAX) OF RCSIdentity,
    rCSRegistrationInformation [2] SEQUENCE SIZE (1..MAX) OF RCSRegistrationInformation,
    userOnline                 [3] BOOLEAN,
    location                   [4] Location OPTIONAL,
    additionalInstanceLocation [5] SEQUENCE SIZE (1..MAX) OF AdditionalInstanceLocation OPTIONAL
}

-- See clause 7.13.3.6.1.3 for details of this structure
StartOfInterceptWithEstablisedRCSSession ::= SEQUENCE
{
    rCSTargetIdentities        [1] SEQUENCE SIZE (1..MAX) OF RCSIdentity,
    participants               [2] SEQUENCE SIZE (1..MAX) OF RCSDestinations,
    conversationID             [3] RCSConversationID,
    contributionID             [4] RCSContributionID,
    rCSSessionType             [5] RCSSessionType,
    rCSSessionEndpoints        [6] RCSSessionEndpoints,
    rCSSessionLegs             [7] SEQUENCE SIZE (1..MAX) OF RCSSIPSessionExchange OPTIONAL,
    rCSSessionInformation      [8] SEQUENCE SIZE (1..MAX) OF RCSSessionContext,
    location                   [9] Location OPTIONAL,
    additionalInstanceLocation [10] SEQUENCE SIZE (1..MAX) OF AdditionalInstanceLocation OPTIONAL
}

RCSCCPDU ::= CHOICE
{
    encapsulatedRCSPayload [1] EncapsulatedRCSPayload
}

-- ==============
-- RCS Parameters
-- ==============

AdditionalInstanceLocation ::= SEQUENCE
{
    instance [1] SIPEndpoint,
    location [2] Location
}

IMDNMessageID ::= UTF8String

MSRPPath ::= SEQUENCE
{
    path [1] UTF8String
}

RCSConversationID ::= UUID

RCSContributionID ::= UUID

RCSDestinations ::= SEQUENCE SIZE (1..MAX) OF RCSDestination

RCSDestination ::= SEQUENCE SIZE (1..MAX) OF RCSIdentity

RCSGroupChatSessionID ::= SIPURI

RCSIdentity ::= CHOICE
{
    fiveGSIdentities [1] FiveGSSubscriberIDs,
    ePSIdentities    [2] EPSSubscriberIDs,
    iMSIdentities    [3] IMSSubscriberIDs
}

RCSMessageType ::= ENUMERATED
{
    messageWithUserContent(1),
    fileTransferMessage(2),
    geoLocationPUSHMessage(3),
    iMDNNotification(4)
}

RCSRegistrationInformation ::= CHOICE
{
    sIPRegistration  [1] RCSSIPRegistrationExchange,
    userProfile      [2] XMLType,
    multiDevice      [3] XMLType,
    presenceDocument [4] XMLType
}

RCSRegistrationType ::= ENUMERATED
{
    registration(1),
    reRegistration(2),
    uEDeregistration(3),
    networkDeregistration(4)
}

RCSServerURI ::= UTF8String

RCSSessionEndpoints ::= ENUMERATED
{
    remoteOnly(1),
    localOnly(2),
    localAndRemote(3)
}

RCSSessionLeg ::= ENUMERATED
{
    remoteLeg(1),
    localLeg(2)
}

RCSSessionContext ::= CHOICE
{
    cPMSessionInfo [1] MIMEEntity
}

RCSSessionType ::= ENUMERATED
{
    largeMessageStandalone(1),
    oneTo1Chat(2)
}

RCSSIPRegistrationExchange ::= SEQUENCE
{
    rCSRegistrationUpdateRequest  [1] IMSPayload,
    rCSRegistrationUpdateResponse [2] IMSPayload
}

RCSSIPSessionExchange ::= SEQUENCE
{
    sessionLeg       [1] RCSSessionLeg,
    sIPRequest       [2] IMSPayload,
    sIPResponse      [3] IMSPayload
}

RCSSIPSessionMessage ::= SEQUENCE
{
    sessionLeg       [1] RCSSessionLeg,
    sIPMessage       [2] IMSPayload,
    rCSSessionResult [3] RCSSessionResult,
    mSRPPathInfo     [4] MSRPPath
}

RCSSessionResult ::= ENUMERATED
{
    newLegRequested(1),
    newLegEstablished(2),
    legModificationRequested(3),
    legModificationComplete(4),
    legRemovalRequest(5),
    legRemovalComplete(6)
}

SIPEndpoint ::= UTF8String

-- =================
-- EES definitions
-- =================

-- See clause 7.14.2.2 for details of this structure
EESEECRegistration ::= SEQUENCE
{
    registrationType         [1] RegistrationType,
    eECID                    [2] UTF8String,
    gPSI                     [3] GPSI OPTIONAL,
    aCProfiles               [4] ACProfiles OPTIONAL,
    eECServiceContSupport    [5] ACRScenarios OPTIONAL,
    expirationTime           [6] Timestamp OPTIONAL,
    eECContextID             [7] UTF8String OPTIONAL,
    srcEESID                 [8] UTF8String OPTIONAL,
    unfulfilledACProfiles    [9] UnfulfilledACProfiles OPTIONAL,
    failureResponse          [10] FailureResponse OPTIONAL
}

-- See clause 7.14.2.3 for details of this structure
EESEASDiscovery ::= SEQUENCE
{
    eECID                    [1] UTF8String,
    gPSI                     [2] GPSI OPTIONAL,
    eASDiscoveryFilter       [3] EASDiscoveryFilter OPTIONAL,
    eECServiceContSupport    [4] ACRScenarios OPTIONAL,
    uELocation               [5] Location OPTIONAL,
    eASTargetDNAIs           [6] DNAIs OPTIONAL,
    discoveredEAS            [7] DiscoveredEAS OPTIONAL,
    failureResponse          [8] FailureResponse OPTIONAL
}

-- See clause 7.14.2.4 for details of this structure
EESEASDiscoverySubscription ::= SEQUENCE
{
    eECID                    [1] UTF8String,
    gPSI                     [2] GPSI OPTIONAL,
    subscriptionType         [3] SubscriptionType,
    eASEventType             [4] EASEventType,
    eASDiscoveryFilter       [5] EASDiscoveryFilter OPTIONAL,
    eASDynamicInfoFilter     [6] EASDynamicInfoFilter OPTIONAL,
    eECServiceContSupport    [7] ACRScenarios OPTIONAL,
    expirationTime           [8] Timestamp OPTIONAL,
    subscriptionId           [9] UTF8String OPTIONAL,
    failureResponse          [10] FailureResponse OPTIONAL
}

-- See clause 7.14.2.5 for details of this structure
EESEASDiscoveryNotification ::= SEQUENCE
{
    subscriptionID     [1] UTF8String,
    eventType          [2] EASEventType,
    discoveredEAS      [3] DiscoveredEAS,
    failureResponse    [4] FailureResponse OPTIONAL
}

-- See clause 7.14.2.6 for details of this structure
EESAppContextRelocation ::= SEQUENCE
{
    eECID              [1] UTF8String,
    gPSI               [2] GPSI OPTIONAL,
    eESACRDetOrInit    [3] EESACRDetOrInit
}

EESACRDetOrInit ::= CHOICE
{
    aCRDetermineReq    [1] ACRDetermineReq,
    aCRInitiateReq     [2] ACRInitiateReq
}

ACRDetermineReq ::= SEQUENCE
{
    eASID           [1] EASID OPTIONAL,
    aCID            [2] ACID OPTIONAL,
    sEASEndpoint    [3] EASEndpoint
}

ACRInitiateReq ::= SEQUENCE
{
    eASID                   [1] EASID OPTIONAL,
    aCID                    [2] ACID OPTIONAL,
    tEASEndpoint            [3] EASEndpoint,
    sEASEndpoint            [4] EASEndpoint OPTIONAL,
    previousTEASEndpoint    [5] EASEndpoint OPTIONAL,
    routeReq                [6] RouteToLocation OPTIONAL
}

-- See clause 7.14.2.7 for details of this structure
EESACRSubscription ::= SEQUENCE
{
    eECID               [1] UTF8String,
    gPSI                [2] GPSI OPTIONAL,
    subscriptionType    [3] SubscriptionType,
    expirationTime      [4] Timestamp OPTIONAL,
    eASIDs              [5] EASIDs,
    aCIDs               [6] ACIDs OPTIONAL,
    eventIDs            [7] ACREventIDs OPTIONAL,
    subscriptionId      [8] UTF8String OPTIONAL,
    failureResponse     [9] FailureResponse OPTIONAL
}

-- See clause 7.14.2.8 for details of this structure
EESACRNotification ::= SEQUENCE
{
    subscriptionID    [1] UTF8String,
    eASID             [2] EASID,
    eventID           [3] ACREventIDs,
    targetInfo        [4] TargetInfo OPTIONAL,
    aCRRes            [5] BOOLEAN OPTIONAL,
    failReason        [6] UTF8String OPTIONAL
}

-- See clause 7.14.2.9 for details of this structure
EESEECContextRelocation ::= SEQUENCE
{
    eECID           [1] UTF8String,
    eECContextID    [2] UTF8String,
    gPSI            [3] GPSI OPTIONAL,
    uELoc           [4] Location OPTIONAL,
    aCProfiles      [5] ACProfiles OPTIONAL
}

-- See clause 7.14.2.10 for details of this structure
EESStartOfInterceptionWithRegisteredEEC ::= SEQUENCE
{
    eECID                    [1] UTF8String,
    gPSI                     [2] GPSI OPTIONAL,
    aCProfiles               [3] ACProfiles OPTIONAL,
    eECServiceContSupport    [4] ACRScenarios OPTIONAL,
    expirationTime           [5] Timestamp OPTIONAL,
    eECContextID             [6] UTF8String OPTIONAL,
    srcEESID                 [7] UTF8String OPTIONAL,
    unfulfilledACProfiles    [8] UnfulfilledACProfiles OPTIONAL,
    timeOfRegistration       [9] Timestamp OPTIONAL
}

-- ==============
-- EES parameters
-- ==============

RegistrationType ::= ENUMERATED
{
    registration (1),
    registrationUpdate(2),
    deregistration(3)
}

ACProfiles ::= SET OF ACProfile

ACProfile ::= SEQUENCE
{
    aCID                  [1] ACID,
    aCType                [2] UTF8String OPTIONAL,
    aCSchedule            [3] Daytime OPTIONAL,
    expACGeoServArea      [4] Location OPTIONAL,
    eASsInfo              [5] EASsInfo OPTIONAL,
    aCServiceContSupport  [6] ACRScenarios OPTIONAL
}

ACID ::= UTF8String

ACRScenarios ::= SET OF ACRScenario

ACRScenario ::= ENUMERATED
{
    eECInitiated(1),
    eECExecutedViaSourceEES(2),
    eECExecutedViaTargetEES(3),
    sourceEASDecided(4),
    sourceEESExecuted(5),
    eELManagedACR(6)
}

UnfulfilledACProfiles ::= SET OF UnfulfilledACProfile

UnfulfilledACProfile ::= SEQUENCE
{
    aCID      [1] ACID,
    reason    [2] UnfulfilledACProfileReason
}

UnfulfilledACProfileReason ::= ENUMERATED
{
    eASNotAvailable(1),
    requirementsUnfulfilled(2)
}

EASID ::= UTF8String

EASsInfo ::= SET OF EASInfo

EASInfo ::= SEQUENCE
{
    eASID                 [1] EASID,
    expectedSvcKPIs       [2] ServiceKPIs OPTIONAL,
    minimumReqSvcKPIs     [3] ServiceKPIs OPTIONAL
}

ServiceKPIs ::= SEQUENCE
{
    connectionBandwidth      [1] INTEGER OPTIONAL,
    requestRate              [2] INTEGER OPTIONAL,
    responseTime             [3] INTEGER OPTIONAL,
    requestedAvailability    [4] INTEGER OPTIONAL,
    requestedCompute         [5] OCTET STRING OPTIONAL,
    requestedGraphCompute    [6] OCTET STRING OPTIONAL,
    requestedMemory          [7] OCTET STRING OPTIONAL,
    requestedStorage         [8] OCTET STRING OPTIONAL
}

FailureResponse ::= ENUMERATED
{
    error400(1),
    error401(2),
    error403(3),
    error404(4),
    error406(5),
    error411(6),
    error413(7),
    error415(8),
    error429(9),
    error500(10),
    error503(11)
}

EASDiscoveryFilter ::= CHOICE
{
    aCsCharacteristics     [1] ACProfiles,
    eASCharacteristics     [2] EASsCharacteristics
}

EASsCharacteristics ::= SET OF EASCharacteristics

EASCharacteristics ::= SEQUENCE
{
    eASID                  [1] EASID OPTIONAL,
    aSPID                  [2] UTF8String OPTIONAL,
    eASType                [3] UTF8String OPTIONAL,
    eASSchedule            [4] Daytime OPTIONAL,
    eASProfile             [5] EASProfile OPTIONAL,
    eASServiceArea         [6] Location OPTIONAL,
    eASServicePermLevel    [7] UTF8String OPTIONAL,
    eASServiceFeatures     [8] EASServiceFeatures OPTIONAL
}

DNAIs ::= SET OF DNAI

DiscoveredEAS ::= SEQUENCE
{
    eASProfile    [1] EASProfile,
    lifetime      [2] INTEGER OPTIONAL
}

EASProfile ::= SEQUENCE
{
    eASID                  [1] EASID,
    eASEndpoint            [2] EASEndpoint,
    aCIDs                  [3] ACIDs OPTIONAL,
    aSPID                  [4] UTF8String OPTIONAL,
    eASType                [5] UTF8String OPTIONAL,
    eASDescription         [6] UTF8String OPTIONAL,
    eASSchedule            [7] Daytime OPTIONAL,
    eASServiceArea         [8] Location OPTIONAL,
    eASServiceKPIs         [9] ServiceKPIs OPTIONAL,
    eASServicePermLevel    [10] UTF8String OPTIONAL,
    eASServiceFeatures     [11] EASServiceFeatures OPTIONAL,
    eASServiceContSupport  [12] ACRScenarios OPTIONAL,
    appLocs                [13] RouteToLocations OPTIONAL,
    eASStatus              [14] EASStatus OPTIONAL
}

EASStatus ::= ENUMERATED
{
    enabled(1),
    disabled(2)
}

EASEndpoint ::= SEQUENCE
{
    fQDN             [1] FQDN OPTIONAL,
    iPv4Addresses    [2] IPv4Addresses OPTIONAL,
    iPv6Addresses    [3] IPv6Addresses OPTIONAL,
    uRI              [4] UTF8String OPTIONAL
}

RouteToLocations ::= SET OF RouteToLocation
EASServiceFeatures ::= SET OF EASServiceFeature
EASServiceFeature ::= UTF8String
ACIDs ::= SET OF ACID
IPv4Addresses ::= SET OF IPv4Address
IPv6Addresses ::= SET OF IPv6Address

SubscriptionType ::= ENUMERATED
{
    subscription(1),
    subscriptionUpdate(2),
    unsubscription(3)
}

EASEventType ::= ENUMERATED
{
    eASAvailabilityChange(1),
    eASDynamicInfoChange(2)
}

EASDynamicInfoFilter ::= SEQUENCE
{
    eASId          [1] EASID,
    eASStatus      [2] BOOLEAN,
    eASAcIDs       [3] BOOLEAN,
    eASDesc        [4] BOOLEAN,
    eASPt          [5] BOOLEAN,
    eASFeature     [6] BOOLEAN,
    eASSchedule    [7] BOOLEAN,
    eASSvcArea     [8] BOOLEAN,
    eASSvcKpi      [9] BOOLEAN,
    eASSvcCont     [10] BOOLEAN
}

EASIDs ::= SET OF EASID

ACREventIDs ::= ENUMERATED
{
    targetInformation(1),
    aCRComplete(2)
}

TargetInfo ::= SEQUENCE
{
    discoveredEAS    [1] DiscoveredEAS,
    targetEESInfo    [2] EDNConfigurationInfo OPTIONAL
}

EDNConfigurationInfo ::= SEQUENCE
{
    eDNConnectionInfo    [1] EDNConnectionInfo,
    eESsInfo             [2] EESsInfo,
    lifetime             [3] INTEGER OPTIONAL
}

EDNConnectionInfo ::= SEQUENCE
{
    dNN            [1] DNN OPTIONAL,
    sNSSAI         [2] SNSSAI OPTIONAL,
    serviceArea    [3] Location OPTIONAL
}

EESsInfo ::= SET OF EESInfo

EESInfo ::= SEQUENCE
{
    eESID          [1] EESID,
    eESEndpoint    [2] EESEndpoint,
    eASIDs         [3] EASIDs OPTIONAL,
    serviceArea    [4] Location OPTIONAL,
    dNAIS          [5] DNAIs OPTIONAL
}

EESID ::= UTF8String

EESEndpoint ::= SEQUENCE
{
    fQDN             [1] FQDN OPTIONAL,
    iPv4Addresses    [2] IPv4Addresses OPTIONAL,
    iPv6Addresses    [3] IPv6Addresses OPTIONAL,
    uRI              [4] UTF8String OPTIONAL
}

-- =================
-- 5GMS AF definitions
-- =================

-- See clause 7.15.2.2 for details of this structure
FiveGMSAFServiceAccessInformation ::= SEQUENCE
{
    gPSI                                [1] GPSI,
    serviceAccessInformationResource    [2] SBIType
}

-- See clause 7.15.2.3 for details of this structure
FiveGMSAFConsumptionReporting ::= SEQUENCE
{
    gPSI                 [1] GPSI,
    consumptionReport    [2] SBIType
}

-- See clause 7.15.2.4 for details of this structure
FiveGMSAFDynamicPolicyInvocation ::= SEQUENCE
{
    gPSI                        [1] GPSI,
    dynamicPolicyResource       [2] SBIType,
    dPIoperationType            [3] DPIOperationType
}

-- See clause 7.15.2.5 for details of this structure
FiveGMSAFMetricsReporting ::= SEQUENCE
{
    gPSI             [1] GPSI,
    metricsReport    [2] XMLType
}

-- See clause 7.15.2.6 for details of this structure
FiveGMSAFNetworkAssistance ::= SEQUENCE
{
    gPSI                                [1] GPSI,
    networkAssistanceSessionResource    [2] SBIType,
    nAOperationType                     [3] NAOperationType
}

-- See clause 7.15.2.7 for details of this structure
FiveGMSAFUnsuccessfulProcedure ::= SEQUENCE
{
    gPSI                              [1] GPSI,
    fiveGMSAFUnsuccessfulOperation    [2] FiveGMSAFUnsuccessfulOperation,
    fiveGMSAFErrorCode                [3] FiveGMSAFErrorCode
}

-- See clause 7.15.2.8 for details of this structure
FiveGMSAFStartOfInterceptionWithAlreadyConfiguredUE ::= SEQUENCE
{
    gPSI                                [1] GPSI,
    serviceAccessInformationResource    [2] SBIType
}

-- ==============
-- 5GMS AF parameters
-- ==============

DPIOperationType ::= ENUMERATED
{
    createDynamicPolicy(1),
    retrieveDynamicPolicy(2),
    updateDynamicPolicy(3),
    patchDynamicPolicy(4),
    destroyDynamicPolicy(5)
}

NAOperationType ::= ENUMERATED
{
    createNetworkAssistanceSession(1),
    retrieveNetworkAssistanceSession(2),
    updateNetworkAssistanceSession(3),
    patchNetworkAssistanceSession(4),
    destroyNetworkAssistanceSession(5),
    requestBitRateRecommendation(6),
    requestDeliveryBoost(7)
}

FiveGMSAFUnsuccessfulOperation::= ENUMERATED
{
    retrieveServiceAccessInformation(1),
    submitConsumptionReport(2),
    submitMetricsReport(3),
    createDynamicPolicy(4),
    retrieveDynamicPolicy(5),
    updateDynamicPolicy(6),
    patchDynamicPolicy(7),
    destroyDynamicPolicy(8),
    createNetworkAssistanceSession(9),
    retrieveNetworkAssistanceSession(10),
    updateNetworkAssistanceSession(11),
    patchNetworkAssistanceSession(12),
    destroyNetworkAssistanceSession(13),
    requestBitRateRecommendation(14),
    requestDeliveryBoost(15)
}

FiveGMSAFErrorCode ::=ENUMERATED
{
    badRequest400(1),
    unauthorized401(2),
    notFound404(3),
    unsupportedMediaType415(4)
}

-- =================
-- NWDAF definitions
-- =================

NWDAFEventsSubscription ::=SEQUENCE
{
    sUPI                                [1] SUPI,
    nWDAFConsumerNFType                 [2] NWDAFConsumerNFType,
    nWDAFEventsSubscriptionOpType       [3] NWDAFEventsSubscriptionOpType,
    nWDAFSubscribedEventList            [4] SEQUENCE SIZE(1..MAX) OF NWDAFEvent,
    nWDAFEventsSubscription             [5] SBIType,
    nWDAFEventsSubscriptionID           [6] UTF8String OPTIONAL,
    nWDAFEventsSubscriptionResponseCode [7] NWDAFEventsSubscriptionResponseCode
}

NWDAFEventsNotification ::=SEQUENCE
{
    sUPI                        [1] SUPI,
    nWDAFNotifiedEventList      [2] SEQUENCE SIZE(1..MAX) OF NWDAFEvent,
    nWDAFEventsNotification     [3] SBIType
}

NWDAFAnalyticsInfoQuery ::=SEQUENCE
{
    sUPI                           [1] SUPI,
    nWDAFEvent                     [2] NWDAFEvent,
    nWDAFEventReportingRequirement [3] SBIType OPTIONAL,
    nWDAFEventFilter               [4] SBIType OPTIONAL,
    nWDAFAnalyticsData             [5] SBIType OPTIONAL,
    nWDAFAnalyticsInfoResponseCode [6] NWDAFAnalyticsInfoResponseCode
}

NWDAFRoamingAnalyticsSubscription ::=SEQUENCE
{
    sUPI                                [1] SUPI,
    pLMNID                              [2] PLMNID,
    nWDAFEventsSubscriptionOpType       [3] NWDAFEventsSubscriptionOpType,
    nWDAFSubscribedEventList            [4] SEQUENCE SIZE(1..MAX) OF NWDAFEvent,
    nWDAFEventsSubscription             [5] SBIType,
    nWDAFEventsSubscriptionID           [6] UTF8String OPTIONAL,
    nWDAFEventsSubscriptionResponseCode [7] NWDAFEventsSubscriptionResponseCode
}

NWDAFRoamingAnalyticsNotification ::=SEQUENCE
{
    sUPI                          [1] SUPI,
    nWDAFNotifiedEventList        [2] SEQUENCE SIZE(1..MAX) OF NWDAFEvent,
    nWDAFEventsNotification       [3] SBIType
}

-- ==============
-- NWDAF parameters
-- ==============

NWDAFEventsSubscriptionOpType ::= ENUMERATED
{
    pOST(1),
    pUT(2),
    dELETE(3)
}

NWDAFEventsSubscriptionResponseCode ::= ENUMERATED
{
    oK200(1),
    created201(2),
    noContent204(3),
    temporaryRedirect307(4),
    permanentRedirect308(5),
    badRequest400(6),
    unauthorized401(7),
    forbidden403(8),
    notFound404(9),
    notAcceptable406(10),
    lengthRequired411(11),
    payloadTooLarge413(12),
    unsupportedMediaType415(13),
    tooManyRequests429(14),
    internalServerError500(15),
    notImplemented501(16),
    badGateway502(17),
    serviceUnavailable503(18)
}

NWDAFAnalyticsInfoResponseCode ::= ENUMERATED
{
    oK200(1),
    noContent204(2),
    badRequest400(3),
    unauthorized401(4),
    forbidden403(5),
    notFound404(6),
    notAcceptable406(7),
    uRITooLong414(8),
    tooManyRequests429(9),
    internalServerError500(10),
    badGateway502(11),
    serviceUnavailable503(12)
}

NWDAFConsumerNFType ::= ENUMERATED
{
    pCF(1),
    nSSF(2),
    aMF(3),
    sMF(4),
    nEF(5),
    aF(6),
    lMF(7),
    oAM(8),
    nWDAF(9),
    dCCF(10),
    cEF(11)
}

NWDAFEvent ::= ENUMERATED
{
    serviceExperience(1),
    uEMobility(2),
    uEComm(3),
    abnormalBehaviour(4),
    dispersion(5),
    relativeProximity(6),
    pDUSessionTraffic(7)
}

-- =====================
-- 5G DDNMF definitions
-- =====================

-- See clause 7.17.2.2 for details of this structure
FiveGDDNMFProSeUNIDirectDiscovery ::= SEQUENCE
{
    sUPI              [1] SUPI,
    gPSI              [2] GPSI OPTIONAL,
    fiveGProSeMessage [3] FiveGProSeMessage
}

-- See clause 7.17.2.3 for details of this structure
FiveGDDNMFProSeNNIDirectDiscovery ::= SEQUENCE
{
    sUPI                                  [1] SUPI OPTIONAL,
    gPSI                                  [2] GPSI OPTIONAL,
    fiveGDDNMFProSeDirectDiscoveryMessage [3] SBIType
}

-- ====================
-- 5G DDNMF parameters
-- ====================

FiveGProSeMessage ::= CHOICE
{
    fiveGProSeDirectDiscoveryMessage        [1] XMLType,
    fiveGProSeUsageInformationReportMessage [2] XMLType
}

-- =========================
-- 5G PIN Server definitions
-- =========================

-- See clause 7.18.2.2 for details of this structure
FiveGPINAPPMessage ::= SEQUENCE
{
    pINEIdentities            [1] PINEIdentities,
    mACAddress                [2] MACAddress OPTIONAL,
    pINID                     [3] PINID OPTIONAL,
    pINServerID               [4] PINServerID,
    pINAPPMessage             [5] XMLType
}

-- See clause 7.18.2.3 for details of this structure
FiveGStartOfInterceptionWithPINClientInPIN ::= CHOICE
{
    pINClientInPINS         [1] PINClientInPINS,
    pINClientsInPIN         [2] PINClientsInPIN
}

PINClientInPINS ::= SEQUENCE
{
    pINEIdentities          [1] PINEIdentities,
    mACAddress              [2] MACAddress OPTIONAL,
    pINServerID             [3] PINServerID,
    pINClientProfile        [4] XMLType,
    pINProfiles             [5] SEQUENCE OF PINProfile
}

PINClientsInPIN ::= SEQUENCE
{
    pINID                   [1] PINID,
    pINServerID             [2] PINServerID,
    pINClientProfiles       [3] SEQUENCE OF PINClientProfile,
    pINProfile              [4] XMLType
}

-- ========================
-- 5G PIN Server parameters
-- ========================

PINEIdentities ::= SEQUENCE (SIZE(1..MAX)) OF PINEIdentity

PINEIdentity ::= CHOICE
{
    pINClientID   [1] PINClientID,
    gPSI          [2] GPSI,
    identityToken [3] IdentityToken
}

PINClientID ::= UTF8String
IdentityToken ::= UTF8String
PINID ::= UTF8String
PINServerID ::= UTF8String
PINClientProfile ::=XMLType
PINProfile ::= XMLType

-- ===================
-- 5G LALS definitions
-- ===================

LALSReport ::= SEQUENCE
{
    sUPI                [1] SUPI OPTIONAL,
    -- deprecatedPEI was deprecated in r16(16) version6(6).
    deprecatedPEI       [2] PEI OPTIONAL,
    gPSI                [3] GPSI OPTIONAL,
    location            [4] Location OPTIONAL,
    iMPU                [5] IMPU OPTIONAL,
    iMSI                [7] IMSI OPTIONAL,
    mSISDN              [8] MSISDN OPTIONAL
}

-- =====================
-- PDHR/PDSR definitions
-- =====================

PDHeaderReport ::= SEQUENCE
{
    pDUSessionID                [1] PDUSessionID,
    sourceIPAddress             [2] IPAddress,
    sourcePort                  [3] PortNumber OPTIONAL,
    destinationIPAddress        [4] IPAddress,
    destinationPort             [5] PortNumber OPTIONAL,
    nextLayerProtocol           [6] NextLayerProtocol,
    iPv6flowLabel               [7] IPv6FlowLabel OPTIONAL,
    direction                   [8] Direction,
    packetSize                  [9] INTEGER
}

PDSummaryReport ::= SEQUENCE
{
    pDUSessionID                [1] PDUSessionID,
    sourceIPAddress             [2] IPAddress,
    sourcePort                  [3] PortNumber OPTIONAL,
    destinationIPAddress        [4] IPAddress,
    destinationPort             [5] PortNumber OPTIONAL,
    nextLayerProtocol           [6] NextLayerProtocol,
    iPv6flowLabel               [7] IPv6FlowLabel OPTIONAL,
    direction                   [8] Direction,
    pDSRSummaryTrigger          [9] PDSRSummaryTrigger,
    firstPacketTimestamp        [10] Timestamp,
    lastPacketTimestamp         [11] Timestamp,
    packetCount                 [12] INTEGER,
    byteCount                   [13] INTEGER,
    useSessionTrigger           [14] BOOLEAN
}

-- ====================
-- PDHR/PDSR parameters
-- ====================

PDSRSummaryTrigger ::= ENUMERATED
{
    timerExpiry(1),
    packetCount(2),
    byteCount(3),
    startOfFlow(4),
    endOfFlow(5)
}

-- ==================================
-- Identifier Association definitions
-- ==================================

AMFIdentifierAssociation ::= SEQUENCE
{
    sUPI                      [1] SUPI,
    sUCI                      [2] SUCI OPTIONAL,
    pEI                       [3] PEI OPTIONAL,
    gPSI                      [4] GPSI OPTIONAL,
    gUTI                      [5] FiveGGUTI,
    location                  [6] Location,
    fiveGSTAIList             [7] TAIList OPTIONAL,
    additionalUserIdentifiers [8] UserIdentifiers OPTIONAL
}

AMFIdentifierDeassociation ::= SEQUENCE
{
    sUPI                       [1] SUPI,
    sUCI                       [2] SUCI OPTIONAL,
    pEI                        [3] PEI OPTIONAL,
    gPSI                       [4] GPSI OPTIONAL,
    gUTI                       [5] FiveGGUTI,
    location                   [6] Location OPTIONAL,
    additionalUserIdentifiers  [7] UserIdentifiers OPTIONAL
}

MMEIdentifierAssociation ::= SEQUENCE
{
    iMSI        [1] IMSI,
    iMEI        [2] IMEI OPTIONAL,
    mSISDN      [3] MSISDN OPTIONAL,
    gUTI        [4] GUTI,
    location    [5] Location,
    tAIList     [6] TAIList OPTIONAL
}

MMEIdentifierDeassociation ::= SEQUENCE
{
    iMSI        [1] IMSI,
    iMEI        [2] IMEI OPTIONAL,
    mSISDN      [3] MSISDN OPTIONAL,
    gUTI        [4] GUTI,
    location    [5] Location OPTIONAL
}

-- =================================
-- Identifier Association parameters
-- =================================

MMEGroupID ::= OCTET STRING (SIZE(2))

MMECode ::= OCTET STRING (SIZE(1))

TMSI ::= OCTET STRING (SIZE(4))

-- ===================
-- EPS MME definitions
-- ===================

EPSRANHandoverCommand ::= SEQUENCE
{
    userIdentifiers          [1] UserIdentifiers,
    mMEUES1APID              [2] MMEUES1APID,
    eNBUES1APID              [3] RANUES1APID,
    handoverType             [4] EPSHandoverType,
    eRABsToBeForwarded       [5] ERABContextList OPTIONAL,
    eRABsToRelease           [6] ERABReleaseList OPTIONAL,
    targetToSourceContainers [7] SEQUENCE SIZE(1..MAX) OF RANTargetToSourceContainer
}

EPSRANHandoverRequest ::= SEQUENCE
{
    userIdentifiers         [1] UserIdentifiers,
    handoverType            [2] EPSHandoverType,
    handoverCause           [3] EPSRANCause,
    sourceToTargetContainer [4] RANSourceToTargetContainer,
    cSGInfo                 [5] EPSCSGInfo OPTIONAL,
    targetToSourceContainer [6] RANTargetToSourceContainer,
    admittedCSGID           [7] CSGID OPTIONAL,
    ePSRANUEContext         [8] EPSRANUEContext
}

MMEAttach ::= SEQUENCE
{
    attachType                     [1] EPSAttachType,
    attachResult                   [2] EPSAttachResult,
    iMSI                           [3] IMSI,
    iMEI                           [4] IMEI OPTIONAL,
    mSISDN                         [5] MSISDN OPTIONAL,
    gUTI                           [6] GUTI OPTIONAL,
    location                       [7] Location OPTIONAL,
    ePSTAIList                     [8] TAIList OPTIONAL,
    sMSServiceStatus               [9] EPSSMSServiceStatus OPTIONAL,
    oldGUTI                        [10] GUTI OPTIONAL,
    eMM5GRegStatus                 [11] EMM5GMMStatus OPTIONAL,
    pagingRestrictionIndicator     [12] PagingRestrictionIndicator OPTIONAL,
    rATType                        [13] RATType OPTIONAL,
    rRCEstablishmentCause          [14] RRCEstablishmentCause OPTIONAL,
    deprecatedS1Information        [15] S1Information OPTIONAL,
    nASTransportInitialInformation [16] EPSNASTransportInitialInformation OPTIONAL,
    equivalentPLMNList             [17] PLMNList OPTIONAL,
    ePSUENetworkCapability         [18] EPSUENetworkCapability OPTIONAL,
    initailRANUEContextSetup       [19] EPSRANUEContext OPTIONAL,
    mUSIMUERequestType             [20] MUSIMUERequestType OPTIONAL,
    ePSNetworkPolicy               [21] EPSNetworkPolicy OPTIONAL
}

MMEDetach ::= SEQUENCE
{
    detachDirection    [1] MMEDirection,
    detachType         [2] EPSDetachType,
    iMSI               [3] IMSI,
    iMEI               [4] IMEI OPTIONAL,
    mSISDN             [5] MSISDN OPTIONAL,
    gUTI               [6] GUTI OPTIONAL,
    cause              [7] EMMCause OPTIONAL,
    location           [8] Location OPTIONAL,
    switchOffIndicator [9] SwitchOffIndicator OPTIONAL
}

MMELocationUpdate ::= SEQUENCE
{
    iMSI             [1] IMSI,
    iMEI             [2] IMEI OPTIONAL,
    mSISDN           [3] MSISDN OPTIONAL,
    gUTI             [4] GUTI OPTIONAL,
    location         [5] Location OPTIONAL,
    oldGUTI          [6] GUTI OPTIONAL,
    sMSServiceStatus [7] EPSSMSServiceStatus OPTIONAL
}

MMERANTraceReport ::= SEQUENCE
{
    userIdentifiers           [1] UserIdentifiers,
    mMEUES1APID               [2] MMEUES1APID,
    eNBUES1APID               [3] RANUES1APID,
    traceRecordType           [4] TraceRecordType,
    traceDirection            [5] TraceDirection,
    traceActivationInfo       [6] TraceActivation OPTIONAL,
    eUTRANCGI                 [7] ECGI,
    globalRANNodeID           [8] GlobalRANNodeID,
    traceCollectionEntityInfo [9] TraceCollectionEntityInfo OPTIONAL,
    mMETraceData              [10] XMLType OPTIONAL,
    location                  [11] Location OPTIONAL
}

MMEStartOfInterceptionWithEPSAttachedUE ::= SEQUENCE
{
    attachType                     [1] EPSAttachType,
    attachResult                   [2] EPSAttachResult,
    iMSI                           [3] IMSI,
    iMEI                           [4] IMEI OPTIONAL,
    mSISDN                         [5] MSISDN OPTIONAL,
    gUTI                           [6] GUTI OPTIONAL,
    location                       [7] Location OPTIONAL,
    ePSTAIList                     [9] TAIList OPTIONAL,
    sMSServiceStatus               [10] EPSSMSServiceStatus OPTIONAL,
    eMM5GRegStatus                 [12] EMM5GMMStatus OPTIONAL,
    pagingRestrictionIndicator     [13] PagingRestrictionIndicator OPTIONAL,
    rATType                        [14] RATType OPTIONAL,
    rRCEstablishmentCause          [15] RRCEstablishmentCause OPTIONAL,
    deprecatedS1Information        [16] S1Information OPTIONAL,
    nASTransportInitialInformation [17] EPSNASTransportInitialInformation OPTIONAL,
    equivalentPLMNList             [18] PLMNList OPTIONAL,
    ePSUENetworkCapability         [19] EPSUENetworkCapability OPTIONAL,
    initailRANUEContextSetup       [20] EPSRANUEContext OPTIONAL,
    mUSIMUERequestType             [21] MUSIMUERequestType OPTIONAL,
    ePSNetworkPolicy               [22] EPSNetworkPolicy OPTIONAL
}

MMEUEServiceAccept ::= SEQUENCE
{
    userIdentifiers          [1] UserIdentifiers,
    serviceType              [2] OCTET STRING (SIZE(1)) OPTIONAL,
    mTMSI                    [3] TMSI OPTIONAL,
    cSFBResponse             [4] OCTET STRING (SIZE (1)) OPTIONAL,
    uEEPSBearerContextStatus [5] OCTET STRING (SIZE(2)) OPTIONAL,
    uERequestType            [6] MUSIMUERequestType OPTIONAL,
    pagingRestriction        [7] PagingRestrictionIndicator OPTIONAL,
    controlPlaneServiceType  [8] OCTET STRING (SIZE(1)) OPTIONAL
}

MMEUnsuccessfulProcedure ::= SEQUENCE
{
    failedProcedureType [1] MMEFailedProcedureType,
    failureCause        [2] MMEFailureCause,
    iMSI                [3] IMSI OPTIONAL,
    iMEI                [4] IMEI OPTIONAL,
    mSISDN              [5] MSISDN OPTIONAL,
    gUTI                [6] GUTI OPTIONAL,
    location            [7] Location OPTIONAL
}

-- See clause 6.3.2.2.8 for details of this structure
MMEPositioningInfoTransfer ::= SEQUENCE
{
    iMSI                [1] IMSI,
    iMEI                [2] IMEI OPTIONAL,
    mSISDN              [3] MSISDN OPTIONAL,
    gUTI                [4] GUTI OPTIONAL,
    lPPaMessage         [5] OCTET STRING OPTIONAL,
    lPPMessage          [6] OCTET STRING OPTIONAL,
    mMELCSCorrelationId [7] OCTET STRING (SIZE(4))
}

-- ==================
-- EPS MME parameters
-- ==================

AerialUESubscriptionIndicator ::= ENUMERATED
{
    authorized(1),
    notAuthorized(2)
}

BBFTunnelInformation ::= SEQUENCE
{
    hENBTransportLayerAddress [1] IPAddr,
    uDPPortNumber             [2] PortNumber OPTIONAL
}

ConnectedENGNB ::= SEQUENCE
{
    eNGNBID         [1] GNbID,
    supportedTAList [2] TACList,
    broadcastPLMN   [3] PLMNList
}

ConnectedENGNBList ::= SEQUENCE SIZE (1..MAX) OF ConnectedENGNB

EMMCause ::= INTEGER (0..255)

ESMCause ::= INTEGER (0..255)

EPSAttachType ::= ENUMERATED
{
    ePSAttach(1),
    combinedEPSIMSIAttach(2),
    ePSRLOSAttach(3),
    ePSEmergencyAttach(4),
    reserved(5)
}

EPSAttachResult ::= ENUMERATED
{
    ePSOnly(1),
    combinedEPSIMSI(2)
}

EPSCSFallbackIndicator ::= ENUMERATED
{
    cSFallbackRequired(1),
    cSFallbackHighPriority(2)
}

EPSCSGInfo ::= SEQUENCE
{
    cSGID               [1] CSGID OPTIONAL,
    cSGMembershipStatus [2] CSGMembershipIndication OPTIONAL
}

EPSDetachType ::= ENUMERATED
{
    ePSDetach(1),
    iMSIDetach(2),
    combinedEPSIMSIDetach(3),
    reAttachRequired(4),
    reAttachNotRequired(5),
    reserved(6)
}

EPSHandoverRestrictionList ::= ExternalASNType

EPSRANCause ::= ExternalASNType

EPSRANUEContext ::= SEQUENCE
{
    mMEUES1APID                                  [1] MMEUES1APID,
    rANUES1APID                                  [2] RANUES1APID,
    eRABSetupRequest                             [3] ERABContextList OPTIONAL,
    handoverRestrictionList                      [4] EPSHandoverRestrictionList OPTIONAL,
    uERadioCapability                            [5] EPSUERadioCapability OPTIONAL,
    rATFrequencySelectionPriority                [6] RATFrequencySelectionPriority OPTIONAL,
    cSFallbackIndicator                          [7] EPSCSFallbackIndicator OPTIONAL,
    proSeAuthorized                              [8] EPSProSeAuthorization OPTIONAL,
    lTEV2XServicesAuthorized                     [9] LTEV2XServiceAuthorization OPTIONAL,
    aerialUESubscription                         [10] AerialUESubscriptionIndicator OPTIONAL,
    subscriptionBasedUEDifferentiationIndication [11] EPSSubscriptionBasedUEDifferentiationIndication OPTIONAL,
    iABAuthorizedIndicator                       [12] IABAuthorizedIndicator OPTIONAL,
    nRV2XServicesAuthorization                   [13] NRV2XServicesAuthorization OPTIONAL
}

EPSNASTransportInitialInformation ::= SEQUENCE
{
    rANUES1APID             [1] RANUES1APID,
    relayNodeIndicator      [2] BOOLEAN OPTIONAL,
    bBFTunnelInformation    [3] BBFTunnelInformation OPTIONAL,
    eDTSession              [4] BOOLEAN OPTIONAL,
    iABNodeIndication       [5] BOOLEAN OPTIONAL,
    lTENTNTAIInformation    [6] LTENTNTAIInformation OPTIONAL
}

EPSNetworkPolicy ::= OCTET STRING (SIZE (1))

EPSProSeAuthorization ::= ExternalASNType

EPSSMSServiceStatus ::= ENUMERATED
{
    sMSServicesNotAvailable(1),
    sMSServicesNotAvailableInThisPLMN(2),
    networkFailure(3),
    congestion(4)
}

EPSSubscriptionBasedUEDifferentiationIndication ::= ExternalASNType

EPSUENetworkCapability ::= OCTET STRING (SIZE(2..13))

EPSUERadioCapability ::= OCTET STRING

ERABQoSParameters ::= SEQUENCE
{
    qCI [1] QCI
}

ERABContext ::= SEQUENCE
{
    eRABID                [1] EPSBearerID,
    eRABQoSParameters     [2] ERABQoSParameters OPTIONAL,
    transportLayerAddress [3] IPAddr OPTIONAL,
    uLGTPTEID             [4] FTEID OPTIONAL,
    dLGTPTEID             [5] FTEID OPTIONAL
}

ERABContextList ::= SEQUENCE SIZE (1..MAX) OF ERABContext

ERABError ::= SEQUENCE
{
    eRABID [1] EPSBearerID,
    cause  [2] EPSRANCause
}

ERABReleaseList ::= SEQUENCE SIZE (1..MAX) OF ERABError

LTENTNTAIInformation ::= SEQUENCE
{
    pLMN            [1] PLMNID,
    tACListInLTENTN [2] TACList,
    uETAC           [3] TAC OPTIONAL
}

MMEDirection ::= ENUMERATED
{
    networkInitiated(1),
    uEInitiated(2)
}

MMEFailedProcedureType ::= ENUMERATED
{
    attachReject(1),
    authenticationReject(2),
    securityModeReject(3),
    serviceReject(4),
    trackingAreaUpdateReject(5),
    activateDedicatedEPSBearerContextReject(6),
    activateDefaultEPSBearerContextReject(7),
    bearerResourceAllocationReject(8),
    bearerResourceModificationReject(9),
    modifyEPSBearerContectReject(10),
    pDNConnectivityReject(11),
    pDNDisconnectReject(12)
}

MMEFailureCause ::= CHOICE
{
    eMMCause [1] EMMCause,
    eSMCause [2] ESMCause
}

MMEServedGUMMEI ::= SEQUENCE
{
    servedPLMNs [1] PLMNSupportList
}

MMEServedGUMMEIList ::= SEQUENCE(SIZE (1..MAX)) OF MMEServedGUMMEI

MMEUES1APID ::= INTEGER (0..4294967295)

RANUES1APID ::= INTEGER (0..16777215)

S1Information ::= SEQUENCE
{
    globalRANNodeID        [1] GlobalRANNodeID,
    rANNodeName            [2] RANNodeName OPTIONAL,
    supportedTAList        [3] SupportedTAList OPTIONAL,
    cSGIDList              [4] CSGIDList OPTIONAL,
    connectedENGNBList     [5] ConnectedENGNBList OPTIONAL,
    mMEServedGUMMEIList    [6] MMEServedGUMMEIList,
    iABSupported           [7] BOOLEAN OPTIONAL
}

-- ===========================
-- LI Notification definitions
-- ===========================

LINotification ::= SEQUENCE
{
    notificationType                    [1] LINotificationType,
    appliedTargetID                     [2] TargetIdentifier OPTIONAL,
    appliedDeliveryInformation          [3] SEQUENCE OF LIAppliedDeliveryInformation OPTIONAL,
    appliedStartTime                    [4] Timestamp OPTIONAL,
    appliedEndTime                      [5] Timestamp OPTIONAL,
    appliedTargetIsLocal                [6] BOOLEAN OPTIONAL,
    appliedTargetIsNonLocal             [7] BOOLEAN OPTIONAL
}

-- ==========================
-- LI Notification parameters
-- ==========================

LINotificationType ::= ENUMERATED
{
    activation(1),
    deactivation(2),
    modification(3)
}

LIAppliedDeliveryInformation ::= SEQUENCE
{
    hI2DeliveryIPAddress                [1] IPAddress OPTIONAL,
    hI2DeliveryPortNumber               [2] PortNumber OPTIONAL,
    hI3DeliveryIPAddress                [3] IPAddress OPTIONAL,
    hI3DeliveryPortNumber               [4] PortNumber OPTIONAL
}

-- ===============
-- MDF definitions
-- ===============

MDFCellSiteReport ::= SEQUENCE OF CellInformation

-- ==============================
-- 5G EPS Interworking Parameters
-- ==============================

EMM5GMMStatus ::= SEQUENCE
{
    eMMRegStatus  [1] EMMRegStatus OPTIONAL,
    fiveGMMStatus [2] FiveGMMStatus OPTIONAL
}


EPS5GGUTI ::= CHOICE
{
    gUTI      [1] GUTI,
    fiveGGUTI [2] FiveGGUTI
}

EMMRegStatus ::= ENUMERATED
{
    uEEMMRegistered(1),
    uENotEMMRegistered(2)
}

FiveGMMStatus ::= ENUMERATED
{
    uE5GMMRegistered(1),
    uENot5GMMRegistered(2)
}

-- ========================================
-- Separated Location Reporting definitions
-- ========================================

SeparatedLocationReporting ::= SEQUENCE
{
    sUPI                        [1] SUPI,
    sUCI                        [2] SUCI OPTIONAL,
    pEI                         [3] PEI OPTIONAL,
    gPSI                        [4] GPSI OPTIONAL,
    gUTI                        [5] FiveGGUTI OPTIONAL,
    location                    [6] Location,
    non3GPPAccessEndpoint       [7] UEEndpointAddress OPTIONAL,
    rATType                     [8] RATType OPTIONAL,
    ePSIdentities               [9] EPSSubscriberIDs OPTIONAL
}

-- =======================
-- HSS definitions
-- =======================

HSSServingSystemMessage ::= SEQUENCE
{
    iMSI                     [1] IMSI,
    oldPLMNID                [2] PLMNID,
    newPLMNID                [3] PLMNID,
    roamingIndicator         [4] RoamingIndicator,
    responseCodes            [5] UTF8String
}

HSSStartOfInterceptionWithRegisteredTarget ::= SEQUENCE
{
    hSSIdentities              [1] HSSIdentities,
    subscriptionDataSets       [2] SubscriptionDataSets,
    pSUserState                [3] SBIType
}

HSSSubscriberRecordChange ::= SEQUENCE
{
    hSSIdentities                    [1] SEQUENCE OF HSSIdentities,
    subscriberRecordChangePayload    [2] SubscriberRecordChangePayload OPTIONAL
}

HSSIdentities ::= SEQUENCE
{
    ePSSubscriberIDs          [1] EPSSubscriberIDs OPTIONAL,
    iMSSubscriberIDs          [2] IMSSubscriberIDs OPTIONAL
}

SubscriptionDataSets ::= CHOICE
{
    iMSSubscriptionData [1] SBIType
}

-- =======================
-- IMS HSS definitions
-- =======================

IMSHSSServingSystemMessage ::= SEQUENCE
{
    iMSI                     [1] IMSI,
    oldPLMNID                [2] PLMNID,
    authorizationRequest     [3] AuthorizationRequest,
    roamingIndicator         [4] RoamingIndicator,
    deregistrationData       [5] SBIType OPTIONAL
}

IMSHSSStartOfInterceptionWithRegisteredTarget ::= SEQUENCE
{
    hSSIdentities          [1] SEQUENCE OF HSSIdentities,
    iMSProfileData         [2] SBIType OPTIONAL,
    iMSRegistrationStatus  [3] IMSRegistrationStatus
}

IMSHSSSubscriberRecordChange ::= SEQUENCE
{
    hSSIdentities            [1] SEQUENCE OF HSSIdentities,
    iMSProfileData           [2] SBIType OPTIONAL,
    mSISDNs                  [3] SEQUENCE (SIZE(1..MAX)) OF MSISDN OPTIONAL,
    iMEI                     [4] IMEI OPTIONAL,
    previousIMEI             [5] IMEI OPTIONAL
}

IMSRegistrationStatus ::= ENUMERATED
{
    initialRegistration(1),
    reregistration(2),
    timeoutDeregistration(3),
    userDeregistration(4),
    administrativeDeregistration(5),
    authenticationFailure(6),
    authenticationTimeout(7),
    unregisteredUser(8)
}

AuthorizationRequest ::= SEQUENCE
{
    authorizationType            [1] AuthorizationType,
    iMPI                         [2] IMPI,
    visitedNetworkIdentifier     [3] UTF8String
}

AuthorizationType ::= ENUMERATED
{
    registration(1),
    deregistration(2)
}

SubscriberRecordChangePayload ::= CHOICE
{
    iMEIUpdateInfo          [1] IMEIUpdateInfo,
    iMEIUpdateResponse      [2] IMEIUpdateResponse,
    roamingStatusUpdateInfo [3] RoamingStatusUpdateInfo
}

IMEIUpdateInfo ::= SEQUENCE
{
    iMSI       [1] IMSI OPTIONAL,
    iMEI       [2] IMEI OPTIONAL,
    iMEISV     [3] IMEISV OPTIONAL
}

IMEIUpdateResponse ::= SEQUENCE
{
    previousIMEI    [1] IMEI OPTIONAL,
    previousIMEISV  [2] IMEISV OPTIONAL
}

RoamingStatusUpdateInfo ::= SEQUENCE
{
    iMSI           [1] IMSI OPTIONAL,
    pLMNID         [2] PLMNID OPTIONAL
}

-- =========================
-- Charging Data Definitions
-- =========================

ChargingDataEvent ::= SEQUENCE
{
    location                [1] Location OPTIONAL,
    chargingDataInformation [2] ChargingDataInformation
}

-- ========================
-- Charging Data Parameters
-- ========================

ChargingDataInformation ::= CHOICE
{
    nchfChargingDataRequest    [1] NchfChargingDataRequest,
    rfChargingDataRequest      [2] RfChargingDataRequest,
    translatedChargingDataInfo [3] TranslatedChargingDataInfo
}

NchfChargingDataRequest ::= SEQUENCE
{
    sBIchargingData   [1] SBIChargingData,
    nchfChargingEvent [2] NchfChargingEvent OPTIONAL,
    roamerInOut       [3] RoamerInOut
}

SBIChargingData ::= CHOICE
{
    fullSBIChargingData    [1] EncapsulatedSBIChargingData
}

EncapsulatedSBIChargingData ::= CHOICE
{
    encapsulatedSBIConvergedChargingData [1] SBIType,
    encapsulatedSBIOfflineChargingData   [2] SBIType
}

NchfChargingEvent ::= ENUMERATED
{
    pDUSessionChargingInformation(1),
    sMSChargingInformation(2),
    nEFChargingInformation(3),
    registrationChargingInformation(4),
    n2ConnectionChargingInformation(5),
    locationReportingChargingInformation(6),
    nSPAChargingInformation(7),
    nSMChargingInformation(8),
    mMTelChargingInformation(9),
    iMSChargingInformation(10),
    edgeInfrastructureUsageChargingInformation(11),
    eASDeploymentChargingInformation(12),
    directEdgeEnablingServiceChargingInformation(13),
    exposedEdgeEnablingServiceChargingInformation(14),
    proSeChargingInformation(15),
    mMSChargingInformation(16),
    mBSSessionChargingInformation(17),
    tSNChargingInformation(18),
    nSACFChargingInformation(19),
    nSSAAChargingInformation(20),
    rangingSLChargingInformation(21)
}

RoamerInOut ::= ENUMERATED
{
    in-bound(1),
    out-bound(2)
}

RfChargingDataRequest ::= SEQUENCE
{
    rfChargingData  [1] DiameterChargingData,
    rfChargingEvent [2] RfChargingEvent OPTIONAL
}

DiameterChargingData ::= CHOICE
{
    fullDiameterChargingData    [1] EncapsulatedRfChargingData
}

EncapsulatedRfChargingData ::= OCTET STRING

RfChargingEvent ::= ENUMERATED
{
    aoC-Information(1),
    pS-Information(2),
    iMS-Information(3),
    mMS-Information(4),
    lCS-Information(5),
    poC-Information(6),
    mBMS-Inform(7),
    sMS-Information(8),
    vCS-Information(9),
    mMTel-Information(10),
    proSe-Information(11),
    service-Generic-Information(12),
    iM-Information(13),
    dCD-Information(14),
    m2M-Information(15),
    cPDT-Information(16)
}

TranslatedChargingDataInfo ::= SEQUENCE

{
    translatedChargingData  [1] TranslatedChargingData
}

TranslatedChargingData ::= SEQUENCE
{
    releaseID           [1] INTEGER (0..7),
    versonID            [2] INTEGER (0..31),
    specificationNumber [3] INTEGER (0..31),
    releaseIDExtension  [4] INTEGER (0..255) OPTIONAL,
    recordData          [5] ExternalChargingASN
}

ExternalChargingASN ::= ExternalASNType

-- =================
-- Common Parameters
-- =================

AccessType ::= ENUMERATED
{
    threeGPPAccess(1),
    nonThreeGPPAccess(2),
    threeGPPandNonThreeGPPAccess(3)
}

AllowedNSSAI ::= SEQUENCE OF NSSAI

AllowedTACs ::= SEQUENCE (SIZE(1..MAX)) OF TAC

AreaOfInterest ::= SEQUENCE
{
    areaOfInterestTAIList     [1] AreaOfInterestTAIList OPTIONAL,
    areaOfInterestCellList    [2] AreaOfInterestCellList OPTIONAL,
    areaOfInterestRANNodeList [3] AreaOfInterestRANNodeList OPTIONAL
}

AreaOfInterestCellList ::= SEQUENCE (SIZE(1..MAX)) OF NCGI

AreaOfInterestItem ::= SEQUENCE
{
    areaOfInterest  [1] AreaOfInterest
}

AreaOfInterestRANNodeList ::= SEQUENCE (SIZE(1..MAX)) OF GlobalRANNodeID

AreaOfInterestTAIList ::= SEQUENCE (SIZE(1..MAX)) OF TAI

BroadcastPLMNItem ::= SEQUENCE
{
    pLMNIdentity          [1] PLMNID,
    tAISliceSupportList   [2] TAISliceSupportList,
    nPNSupport            [3] NID
}

CellCAGList ::= SEQUENCE (SIZE(1..MAX)) OF CAGID

CauseMisc ::= ENUMERATED
{
    controlProcessingOverload(1),
    notEnoughUserPlaneProcessingResources(2),
    hardwareFailure(3),
    oMIntervention(4),
    unknownPLMNOrSNPN(5),
    unspecified(6)
}

CauseNas ::= ENUMERATED
{
    normalRelease(1),
    authenticationFailure(2),
    deregister(3),
    unspecified(4)
}

CauseProtocol ::= ENUMERATED
{
    transferSyntaxError(1),
    abstractSyntaxError-reject(2),
    abstractSyntaxErrorIgnoreAndNotify(3),
    messageNotCompatibleWithReceiverState(4),
    semanticError(5),
    abstractSyntaxErrorFalselyConstructedMessage(6),
    unspecified(7)
}

CauseRadioNetwork ::= ENUMERATED
{
    unspecified(1),
    txnrelocoverallExpiry(2),
    successfulHandover(3),
    releaseDueToNGRANGeneratedReason(4),
    releaseDueTo5gcGeneratedReason(5),
    handoverCancelled(6),
    partialHandover(7),
    hoFailureInTarget5GCNGRANNodeOrTargetSystem(8),
    hoTargetNotAllowed(9),
    tNGRelocOverallExpiry(10),
    tNGRelocPrepExpiry(11),
    cellNotAvailable(12),
    unknownTargetID(13),
    noRadioResourcesAvailableInTargetCell(14),
    unknownLocalUENGAPID(15),
    inconsistentRemoteUENGAPID(16),
    handoverDesirableForRadioReason(17),
    timeCriticalHandover(18),
    resourceOptimisationHandover(19),
    reduceLoadInServingCell(20),
    userInactivity(21),
    radioConnectionWithUELost(22),
    radioResourcesNotAvailable(23),
    invalidQoSCombination(24),
    failureInRadioInterfaceProcedure(25),
    interactionWithOtherProcedure(26),
    unknownPDUSessionID(27),
    multiplePDUSessionIDInstances(29),
    multipleQoSFlowIDInstances(30),
    encryptionAndOrIntegrityProtectionAlgorithmsNotSupported(31),
    nGIntraSystemHandoverTriggered(32),
    nGInterSystemHandoverTriggered(33),
    xNHandoverTriggered(34),
    notSupported5QIValue(35),
    uEContextTransfer(36),
    iMSVoiceeEPSFallbackOrRATFallbackTriggered(37),
    uPIntegrityProtectioNotPossible(38),
    uPConfidentialityProtectionNotPossible(39),
    sliceNotSupported(40),
    uEInRRCInactiveStateNotReachable(41),
    redirection(42),
    resourcesNotAvailableForTheSlice(43),
    uEMaxIntegrityProtectedDataRateReason(44),
    releaseDueToCNDetectedMobility(45),
    n26InterfaceNotAvailable(46),
    releaseDueToPreemption(47),
    multipleLocationReportingReferenceIDInstances(48),
    rSNNotAvailableForTheUP(49),
    nPMAccessDenied(50),
    cAGOnlyAccessDenied(51),
    insufficientUECapabilities(52)
}

CauseTransport ::= ENUMERATED
{
    transportResourceUnavailable(1),
    unspecified(2)
}

Direction ::= ENUMERATED
{
    fromTarget(1),
    toTarget(2)
}

DNN ::= UTF8String

E164Number ::= NumericString (SIZE(1..15))

EmailAddress ::= UTF8String

EPSHandoverType ::= ExternalASNType

EquivalentPLMNs ::= SEQUENCE (SIZE(1..MAX)) OF PLMNID

EUI64 ::= OCTET STRING (SIZE(8))

FiveGGUTI ::= SEQUENCE
{
    mCC         [1] MCC,
    mNC         [2] MNC,
    aMFRegionID [3] AMFRegionID,
    aMFSetID    [4] AMFSetID,
    aMFPointer  [5] AMFPointer,
    fiveGTMSI   [6] FiveGTMSI
}

FiveGMMCause ::= INTEGER (0..255)

FiveGSSubscriberID ::= CHOICE
{
    sUPI [1] SUPI,
    sUCI [2] SUCI,
    pEI  [3] PEI,
    gPSI [4] GPSI
}

FiveGSSubscriberIDs ::= SEQUENCE
{
    fiveGSSubscriberID [1] SEQUENCE SIZE(1..MAX) OF FiveGSSubscriberID
}

FiveGSMRequestType ::= ENUMERATED
{
    initialRequest(1),
    existingPDUSession(2),
    initialEmergencyRequest(3),
    existingEmergencyPDUSession(4),
    modificationRequest(5),
    reserved(6),
    mAPDURequest(7)
}

FiveGSMCause ::= INTEGER (0..255)

FiveGTMSI ::= INTEGER (0..4294967295)

FiveGSRVCCInfo ::= SEQUENCE
{
    uE5GSRVCCCapability   [1] BOOLEAN,
    sessionTransferNumber [2] UTF8String OPTIONAL,
    correlationMSISDN     [3] MSISDN OPTIONAL
}

FiveGSUserStateInfo ::= SEQUENCE
{
    fiveGSUserState [1] FiveGSUserState,
    accessType      [2] AccessType
}

FiveGSUserState ::= ENUMERATED
{
    deregistered(1),
    registeredNotReachableForPaging(2),
    registeredReachableForPaging(3),
    connectedNotReachableForPaging(4),
    connectedReachableForPaging(5),
    notProvidedFromAMF(6)
}

ForbiddenAreaInformation ::= SEQUENCE
{
    pLMNIdentity  [1] PLMNID,
    forbiddenTACs [2] ForbiddenTACs
}

ForbiddenTACs ::= SEQUENCE (SIZE(1..MAX)) OF TAC

FTEID ::= SEQUENCE
{
    tEID        [1] INTEGER (0.. 4294967295),
    iPv4Address [2] IPv4Address OPTIONAL,
    iPv6Address [3] IPv6Address OPTIONAL
}

FTEIDList ::= SEQUENCE OF FTEID

GPSI ::= CHOICE
{
    mSISDN      [1] MSISDN,
    nAI         [2] NAI
}

GUAMI ::= SEQUENCE
{
    aMFID       [1] AMFID,
    pLMNID      [2] PLMNID
}

GUMMEI ::= SEQUENCE
{
    mMEID       [1] MMEID,
    mCC         [2] MCC,
    mNC         [3] MNC
}

GUTI ::= SEQUENCE
{
    mCC          [1] MCC,
    mNC          [2] MNC,
    mMEGroupID   [3] MMEGroupID,
    mMECode      [4] MMECode,
    mTMSI        [5] TMSI
}

HandoverCause ::= CHOICE
{
    radioNetwork    [1] CauseRadioNetwork,
    transport       [2] CauseTransport,
    nas             [3] CauseNas,
    protocol        [4] CauseProtocol,
    misc            [5] CauseMisc
}

HandoverType ::= ENUMERATED
{
    intra5GS(1),
    fiveGStoEPS(2),
    ePSto5GS(3),
    fiveGStoUTRA(4)
}

HomeNetworkIdentifier ::= UTF8String

HomeNetworkPublicKeyID ::= OCTET STRING

HSMFURI ::= UTF8String

IMEI ::= NumericString (SIZE(14))

IMEISV ::= NumericString (SIZE(16))

IMPI ::= NAI

IMPU ::= CHOICE
{
    sIPURI [1] SIPURI,
    tELURI [2] TELURI
}

IMSI ::= NumericString (SIZE(6..15))

IMSIUnauthenticatedIndication ::= BOOLEAN

IMSSubscriberIDs ::= CHOICE
{
    iMPI        [1] IMPI,
    iMPU        [2] IMPU
}

Initiator ::= ENUMERATED
{
    uE(1),
    network(2),
    unknown(3)
}

IPAddress ::= CHOICE
{
    iPv4Address [1] IPv4Address,
    iPv6Address [2] IPv6Address
}

IPv4Address ::= OCTET STRING (SIZE(4))

IPv6Address ::= OCTET STRING (SIZE(16))

IPv6FlowLabel ::= INTEGER(0..1048575)

LocationAreaOfInterestList  ::= SEQUENCE (SIZE(1..MAX)) OF AreaOfInterestItem

LocationEventType ::= ENUMERATED
{
    direct(1),
    changeOfServeCell(2),
    uEPrescenceInAreaOfInterest(3),
    stopChangeOfServeCell(4),
    stopUEPresenceInAreaOfInterest(5),
    cancelLocationReportingForTheUE(6)
}

LocationReportArea ::= ENUMERATED
{
    cell(1)
}

LocationReportingRequestType ::= SEQUENCE
{
    eventType           [1] LocationEventType,
    reportArea          [2] LocationReportArea,
    areaOfInterestList  [3] LocationAreaOfInterestList
}

MACAddress ::= OCTET STRING (SIZE(6))

MACRestrictionIndicator ::= ENUMERATED
{
    noResrictions(1),
    mACAddressNotUseableAsEquipmentIdentifier(2),
    unknown(3)
}

MCC ::= NumericString (SIZE(3))

MNC ::= NumericString (SIZE(2..3))

MMEID ::= SEQUENCE
{
    mMEGI       [1] MMEGI,
    mMEC        [2] MMEC
}

MMEC ::= NumericString

MMEGI ::= NumericString

MobilityRestrictionList ::= SEQUENCE
{
    servingPLMN               [1] PLMNID,
    equivalentPLMNs           [2] EquivalentPLMNs OPTIONAL,
    rATRestrictions           [3] RATRestrictions OPTIONAL,
    forbiddenAreaInformation  [4] ForbiddenAreaInformation OPTIONAL,
    serviceAreaInformation    [5] ServiceAreaInformation OPTIONAL
}

MSISDN ::= NumericString (SIZE(1..15))

NAI ::= UTF8String

NextLayerProtocol ::= INTEGER(0..255)

NonLocalID ::= ENUMERATED
{
    local(1),
    nonLocal(2)
}

NonIMEISVPEI ::= CHOICE
{
    mACAddress [1] MACAddress,
    eUI64      [2] EUI64
}

NPNAccessInformation ::= CHOICE
{
    pNINPNAccessInformation [1] CellCAGList
}

NSSAI ::= SEQUENCE OF SNSSAI

PagingRestrictionIndicator ::= OCTET STRING (SIZE(1..33))

PeriodicCommunicationIndicator ::= ENUMERATED
{
    periodic(1),
    nonPeriodic(2)
}

PLMNID ::= SEQUENCE
{
    mCC [1] MCC,
    mNC [2] MNC
}

PLMNList ::= SEQUENCE (SIZE(1..MAX)) OF PLMNID

PDNConnectionType ::= ENUMERATED
{
    iPv4(1),
    iPv6(2),
    iPv4v6(3),
    nonIP(4),
    ethernet(5)
}

PDUSessionID ::= INTEGER (0..255)

PDUSessionResourceInformation ::= SEQUENCE
{
    pDUSessionID              [1] PDUSessionID
}

PDUSessionType ::= ENUMERATED
{
    iPv4(1),
    iPv6(2),
    iPv4v6(3),
    unstructured(4),
    ethernet(5)
}

PEI ::= CHOICE
{
    iMEI        [1] IMEI,
    iMEISV      [2] IMEISV,
    mACAddress  [3] MACAddress,
    eUI64       [4] EUI64
}

PortNumber ::= INTEGER (0..65535)

PrimaryAuthenticationType ::= ENUMERATED
{
    eAPAKAPrime(1),
    fiveGAKA(2),
    eAPTLS(3),
    none(4),
    ePSAKA(5),
    eAPAKA(6),
    iMSAKA(7),
    gBAAKA(8),
    uMTSAKA(9)
}

ProtectionSchemeID ::= INTEGER (0..15)

RANNodeName ::= CHOICE
{
    rANNodeNameVisible  [1] OCTET STRING,
    rANNodeNameUTF8     [2] UTF8String
}

RANUENGAPID ::= INTEGER (0..4294967295)

-- See clause 9.3.1.20 of TS 38.413 [23] for details
RANSourceToTargetContainer ::= OCTET STRING

-- See clause 9.3.1.21 of TS 38.413 [23] for details
RANTargetToSourceContainer ::= OCTET STRING

RATInformation ::= ENUMERATED
{
    unlicensed(1),
    nBIoT(2),
    nRLEO(3),
    nRMEO(4),
    nRGEO(5),
    nROTHERSAT(6)
}

RATRestrictions ::= SEQUENCE (SIZE(1..MAX)) OF RATRestrictionItem

RATRestrictionInformation ::= BIT STRING (SIZE(8, ...))

RATRestrictionItem ::= SEQUENCE
{
    pLMNIdentity               [1] PLMNID,
    rATRestrictionInformation  [2] RATRestrictionInformation
}

RATType ::= ENUMERATED
{
    nR(1),
    eUTRA(2),
    wLAN(3),
    virtual(4),
    nBIOT(5),
    wireline(6),
    wirelineCable(7),
    wirelineBBF(8),
    lTEM(9),
    nRU(10),
    eUTRAU(11),
    trustedN3GA(12),
    trustedWLAN(13),
    uTRA(14),
    gERA(15),
    nRLEO(16),
    nRMEO(17),
    nRGEO(18),
    nROTHERSAT(19),
    nRREDCAP(20),
    wBEUTRANLEO(21),
    wBEUTRANMEO(22),
    wBEUTRANGEO(23),
    wBEUTRANOTHERSAT(24),
    nBIOTLEO(25),
    nBIOTMEO(26),
    nBIOTGEO(27),
    nBIOTOTHERSAT(28),
    lTEMLEO(29),
    lTEMMEO(30),
    lTEMGEO(31),
    lTEMOTHERSAT(32),
    nREREDCAP(33)
}

RejectedNSSAI ::= SEQUENCE OF RejectedSNSSAI

RejectedSNSSAI ::= SEQUENCE
{
    causeValue  [1] RejectedSliceCauseValue,
    sNSSAI      [2] SNSSAI
}

RejectedSliceCauseValue ::= INTEGER (0..255)

ReRegRequiredIndicator ::= ENUMERATED
{
    reRegistrationRequired(1),
    reRegistrationNotRequired(2)
}

RoutingIndicator ::= INTEGER (0..9999)

SchemeOutput ::= OCTET STRING

ServiceAreaInformation ::= SEQUENCE (SIZE(1..MAX)) OF ServiceAreaInfo

ServiceAreaInfo ::= SEQUENCE
{
    pLMNIdentity    [1] PLMNID,
    allowedTACs     [2] AllowedTACs OPTIONAL,
    notAllowedTACs  [3] ForbiddenTACs OPTIONAL
}

SIPURI ::= UTF8String

Slice ::= SEQUENCE
{
    allowedNSSAI        [1] NSSAI OPTIONAL,
    configuredNSSAI     [2] NSSAI OPTIONAL,
    rejectedNSSAI       [3] RejectedNSSAI OPTIONAL
}

SMPDUDNRequest ::= OCTET STRING

-- TS 24.501 [13], clause 9.11.3.6.1
SMSOverNASIndicator ::= ENUMERATED
{
    sMSOverNASNotAllowed(1),
    sMSOverNASAllowed(2)
}

SNSSAI ::= SEQUENCE
{
    sliceServiceType               [1] INTEGER (0..255),
    sliceDifferentiator            [2] OCTET STRING (SIZE(3)) OPTIONAL,
    mappedHPLMNSliceServiceType    [3] INTEGER (0..255) OPTIONAL,
    mappedHPLMNSliceDifferentiator [4] OCTET STRING (SIZE(3)) OPTIONAL
}

SubscriberIdentifier ::= CHOICE
{
    sUCI   [1] SUCI,
    sUPI   [2] SUPI
}

SUCI ::= SEQUENCE
{
    mCC                         [1] MCC,
    mNC                         [2] MNC,
    routingIndicator            [3] RoutingIndicator,
    protectionSchemeID          [4] ProtectionSchemeID,
    homeNetworkPublicKeyID      [5] HomeNetworkPublicKeyID,
    schemeOutput                [6] SchemeOutput,
    -- routingIndicatorLength shall be included if different from the number
    -- of meaningful digits given in routingIndicator.
    routingIndicatorLength      [7] INTEGER (1..4) OPTIONAL,
    sUPIType                    [8] SUPIType OPTIONAL,
    homeNetworkIdentifier       [9] HomeNetworkIdentifier OPTIONAL
}

SUPI ::= CHOICE
{
    iMSI        [1] IMSI,
    nAI         [2] NAI
}

SUPIUnauthenticatedIndication ::= BOOLEAN

SUPIType ::= INTEGER (0..7)

SupportedTAList ::= SEQUENCE (SIZE(1..MAX)) OF TAItem

SwitchOffIndicator ::= ENUMERATED
{
    normalDetach(1),
    switchOff(2)
}

TAItem ::= SEQUENCE
{
    tAC                  [1] TAC,
    broadcastPLMNList    [2] SEQUENCE (SIZE(1..MAX)) OF BroadcastPLMNItem,
    rATinformation       [3] RATInformation OPTIONAL
}

TAISliceSupportList ::= SEQUENCE (SIZE(1..MAX)) OF SNSSAI

TargetIdentifier ::= CHOICE
{
    sUPI                   [1] SUPI,
    iMSI                   [2] IMSI,
    pEI                    [3] PEI,
    iMEI                   [4] IMEI,
    gPSI                   [5] GPSI,
    mSISDN                 [6] MSISDN,
    nAI                    [7] NAI,
    iPv4Address            [8] IPv4Address,
    iPv6Address            [9] IPv6Address,
    ethernetAddress        [10] MACAddress,
    iMPU                   [11] IMPU,
    iMPI                   [12] IMPI,
    e164Number             [13] E164Number,
    emailAddress           [14] EmailAddress,
    mCPTTID                [15] UTF8String,
    instanceIdentifierURN  [16] UTF8String,
    pTCChatGroupID         [17] PTCChatGroupID
}

TargetIdentifierProvenance ::= ENUMERATED
{
    lEAProvided(1),
    observed(2),
    matchedOn(3),
    other(4)
}

TELURI ::= UTF8String

Timestamp ::= GeneralizedTime

UEContextInfo ::= SEQUENCE
{
    supportVoPS         [1] BOOLEAN OPTIONAL,
    supportVoPSNon3GPP  [2] BOOLEAN OPTIONAL,
    lastActiveTime      [3] Timestamp OPTIONAL,
    accessType          [4] AccessType OPTIONAL,
    rATType             [5] RATType OPTIONAL
}

UEEndpointAddress ::= CHOICE
{
    iPv4Address         [1] IPv4Address,
    iPv6Address         [2] IPv6Address,
    ethernetAddress     [3] MACAddress
}

UserIdentifiers ::= SEQUENCE
{
    fiveGSSubscriberIDs [1] FiveGSSubscriberIDs OPTIONAL,
    ePSSubscriberIDs    [2] EPSSubscriberIDs OPTIONAL
}

UUID ::= OCTET STRING (SIZE (16))

-- ===================
-- Location parameters
-- ===================

Location ::= SEQUENCE
{
    locationInfo                [1] LocationInfo OPTIONAL,
    positioningInfo             [2] PositioningInfo OPTIONAL,
    locationPresenceReport      [3] LocationPresenceReport OPTIONAL,
    fourGPositioningInfo        [4] FourGPositioningInfo OPTIONAL,
    fourGLocationInfo           [5] FourGLocationInfo OPTIONAL,
    iMSLocation                 [6] IMSLocation OPTIONAL,
    coarseLocation              [7] CoarseLocation OPTIONAL
}

CellSiteInformation ::= SEQUENCE
{
    geographicalCoordinates     [1] GeographicalCoordinates,
    azimuth                     [2] INTEGER (0..359) OPTIONAL,
    operatorSpecificInformation [3] UTF8String OPTIONAL
}

-- TS 29.518 [22], clause 6.4.6.2.6
LocationInfo ::= SEQUENCE
{
    userLocation                [1] UserLocation OPTIONAL,
    currentLoc                  [2] BOOLEAN OPTIONAL,
    geoInfo                     [3] GeographicArea OPTIONAL,
    rATType                     [4] RATType OPTIONAL,
    timeZone                    [5] TimeZone OPTIONAL,
    additionalCellIDs           [6] SEQUENCE OF CellInformation OPTIONAL
}

-- TS 29.571 [17], clause 5.4.4.7
UserLocation ::= SEQUENCE
{
    eUTRALocation               [1] EUTRALocation OPTIONAL,
    nRLocation                  [2] NRLocation OPTIONAL,
    n3GALocation                [3] N3GALocation OPTIONAL,
    uTRALocation                [4] UTRALocation OPTIONAL,
    gERALocation                [5] GERALocation OPTIONAL
}

-- TS 29.571 [17], clause 5.4.4.8
EUTRALocation ::= SEQUENCE
{
    tAI                         [1] TAI,
    eCGI                        [2] ECGI,
    ageOfLocationInfo           [3] AgeOfLocation OPTIONAL,
    uELocationTimestamp         [4] Timestamp OPTIONAL,
    geographicalInformation     [5] UTF8String OPTIONAL,
    geodeticInformation         [6] UTF8String OPTIONAL,
    globalNGENbID               [7] GlobalRANNodeID OPTIONAL,
    cellSiteInformation         [8] CellSiteInformation OPTIONAL,
    globalENbID                 [9] GlobalRANNodeID OPTIONAL,
    ignoreTAI                   [10] BOOLEAN OPTIONAL,
    ignoreECGI                  [11] BOOLEAN OPTIONAL,
    cellRadioRelatedInformation [12] SEQUENCE OF CellRadioRelatedInformation OPTIONAL
}

-- TS 29.571 [17], clause 5.4.4.9
NRLocation ::= SEQUENCE
{
    tAI                         [1] TAI,
    nCGI                        [2] NCGI,
    ageOfLocationInfo           [3] AgeOfLocation OPTIONAL,
    uELocationTimestamp         [4] Timestamp OPTIONAL,
    geographicalInformation     [5] UTF8String OPTIONAL,
    geodeticInformation         [6] UTF8String OPTIONAL,
    globalGNbID                 [7] GlobalRANNodeID OPTIONAL,
    cellSiteInformation         [8] CellSiteInformation OPTIONAL,
    ignoreNCGI                  [9] BOOLEAN OPTIONAL,
    nRNTNTAIInfo                [10] NRNTNTAIInfo OPTIONAL,
    iABMTUserLocation           [11] IABMTUserLocation OPTIONAL,
    cellRadioRelatedInformation [12] SEQUENCE OF CellRadioRelatedInformation OPTIONAL
}

-- TS 29.571 [17], clause 5.4.4.10
N3GALocation ::= SEQUENCE
{
    tAI                         [1] TAI OPTIONAL,
    n3IWFID                     [2] N3IWFIDNGAP OPTIONAL,
    uEIPAddr                    [3] IPAddr OPTIONAL,
    portNumber                  [4] INTEGER OPTIONAL,
    tNAPID                      [5] TNAPID OPTIONAL,
    tWAPID                      [6] TWAPID OPTIONAL,
    hFCNodeID                   [7] HFCNodeID OPTIONAL,
    gLI                         [8] GLI OPTIONAL,
    w5GBANLineType              [9] W5GBANLineType OPTIONAL,
    gCI                         [10] GCI OPTIONAL,
    ageOfLocationInfo           [11] AgeOfLocation OPTIONAL,
    uELocationTimestamp         [12] Timestamp OPTIONAL,
    protocol                    [13] TransportProtocol OPTIONAL
}

-- TS 29.571 [17], clause 5.4.4.52
UTRALocation ::= SEQUENCE
{
    cGI                         [1] CGI OPTIONAL,
    sAI                         [2] SAI OPTIONAL,
    lAI                         [3] LAI OPTIONAL,
    rAI                         [4] RAI OPTIONAL,
    ageOfLocationInfo           [5] INTEGER OPTIONAL,
    uELocationTimestamp         [6] Timestamp OPTIONAL,
    geographicalInformation     [7] UTF8String OPTIONAL,
    geodeticInformation         [8] UTF8String OPTIONAL,
    cellSiteInformation         [9] CellSiteInformation OPTIONAL
}

-- TS 29.571 [17], clause 5.4.4.53
GERALocation ::= SEQUENCE
{
    locationNumber              [1] E164Number OPTIONAL,
    cGI                         [2] CGI OPTIONAL,
    rAI                         [3] RAI OPTIONAL,
    sAI                         [4] SAI OPTIONAL,
    lAI                         [5] LAI OPTIONAL,
    vLRNumber                   [6] UTF8String OPTIONAL,
    mSCNumber                   [7] UTF8String OPTIONAL,
    ageOfLocationInfo           [8] INTEGER OPTIONAL,
    uELocationTimestamp         [9] Timestamp OPTIONAL,
    geographicalInformation     [10] UTF8String OPTIONAL,
    geodeticInformation         [11] UTF8String OPTIONAL,
    cellSiteInformation         [12] CellSiteInformation OPTIONAL
}

IMSLocation ::= SEQUENCE
{
    pANIHeaderInfo        [1] SEQUENCE OF PANIHeaderInfo OPTIONAL,
    geolocationHeaderInfo [2] SEQUENCE OF SIPGeolocationHeaderInfo OPTIONAL,
    cNIHeaderInfo         [3] SEQUENCE OF SIPCNIHeaderInfo OPTIONAL
}

-- TS 38.413 [23], clause 9.3.2.4
IPAddr ::= SEQUENCE
{
    iPv4Addr                    [1] IPv4Address OPTIONAL,
    iPv6Addr                    [2] IPv6Address OPTIONAL
}

-- TS 29.571 [17], clause 5.4.4.28
GlobalRANNodeID ::= SEQUENCE
{
    pLMNID                      [1] PLMNID,
    aNNodeID                    [2] ANNodeID,
    nID                         [3] NID OPTIONAL
}

ANNodeID ::= CHOICE
{
    n3IWFID [1] N3IWFIDSBI,
    gNbID   [2] GNbID,
    nGENbID [3] NGENbID,
    eNbID   [4] ENbID,
    wAGFID  [5] WAGFID,
    tNGFID  [6] TNGFID
}

-- TS 38.413 [23], clause 9.3.1.6
GNbID ::= BIT STRING(SIZE(22..32))

-- TS 29.571 [17], clause 5.4.4.4
TAI ::= SEQUENCE
{
    pLMNID                      [1] PLMNID,
    tAC                         [2] TAC,
    nID                         [3] NID OPTIONAL
}

CGI ::= SEQUENCE
{
    lAI    [1] LAI,
    cellID [2] CellID
}

LAI ::= SEQUENCE
{
    pLMNID [1] PLMNID,
    lAC    [2] LAC
}

LAC ::= OCTET STRING (SIZE(2))

CellID ::= OCTET STRING (SIZE(2))

SAI ::= SEQUENCE
{
    pLMNID [1] PLMNID,
    lAC    [2] LAC,
    sAC    [3] SAC
}

SAC ::= OCTET STRING (SIZE(2))

RAI ::= SEQUENCE
{
    pLMNID [1] PLMNID,
    lAC    [2] LAC,
    rAC    [3] RAC
}

RAC ::= OCTET STRING (SIZE(2))

-- TS 29.571 [17], clause 5.4.4.5
ECGI ::= SEQUENCE
{
    pLMNID                      [1] PLMNID,
    eUTRACellID                 [2] EUTRACellID,
    nID                         [3] NID OPTIONAL
}

TACList ::= SEQUENCE OF TAC

TAIList ::= SEQUENCE OF TAI

-- TS 29.571 [17], clause 5.4.4.6
NCGI ::= SEQUENCE
{
    pLMNID                      [1] PLMNID,
    nRCellID                    [2] NRCellID,
    nID                         [3] NID OPTIONAL
}

RANCGI ::= CHOICE
{
    eCGI                        [1] ECGI,
    nCGI                        [2] NCGI,
    cGI                         [3] CGI
}

CellInformation ::= SEQUENCE
{
    rANCGI                      [1] RANCGI,
    cellSiteinformation         [2] CellSiteInformation OPTIONAL,
    timeOfLocation              [3] Timestamp OPTIONAL,
    cellRadioRelatedInformation [4] CellRadioRelatedInformation OPTIONAL,
    band                        [5] RFBand OPTIONAL
}

CellRadioRelatedInformation ::= CHOICE
{
    nGInformation [1] NGInformation,
    f1Information [2] F1Information,
    s1Information [3] S1Information
}

RFBand ::= UTF8String

-- TS 38.413 [23], clause 9.3.1.57
N3IWFIDNGAP ::= BIT STRING (SIZE(16))

-- TS 29.571 [17], clause 5.4.4.28
N3IWFIDSBI ::= UTF8String

-- TS 29.571 [17], clause 5.4.4.28 and table 5.4.2-1
TNGFID ::= UTF8String

-- TS 29.571 [17], clause 5.4.4.28 and table 5.4.2-1
WAGFID ::= UTF8String

-- TS 29.571 [17], clause 5.4.4.62
TNAPID ::= SEQUENCE
{
    sSID         [1] SSID OPTIONAL,
    bSSID        [2] BSSID OPTIONAL,
    civicAddress [3] CivicAddressBytes OPTIONAL
}

-- TS 29.571 [17], clause 5.4.4.64
TWAPID ::= SEQUENCE
{
    sSID         [1] SSID OPTIONAL,
    bSSID        [2] BSSID OPTIONAL,
    civicAddress [3] CivicAddressBytes OPTIONAL
}

-- TS 29.571 [17], clause 5.4.4.62 and clause 5.4.4.64
SSID ::= UTF8String

-- TS 29.571 [17], clause 5.4.4.62 and clause 5.4.4.64
BSSID ::= UTF8String

-- TS 29.571 [17], clause 5.4.4.36 and table 5.4.2-1
HFCNodeID ::= UTF8String

-- TS 29.571 [17], clause 5.4.4.10 and table 5.4.2-1
-- Contains the original binary data i.e. value of the YAML field after base64 encoding is removed
GLI ::= OCTET STRING (SIZE(0..150))

-- TS 29.571 [17], clause 5.4.4.10 and table 5.4.2-1
GCI ::= UTF8String

-- TS 29.571 [17], clause 5.4.4.10 and table 5.4.3.38
TransportProtocol ::= ENUMERATED
{
    uDP(1),
    tCP(2)
}

-- TS 29.571 [17], clause 5.4.4.10 and clause 5.4.3.33
W5GBANLineType ::= ENUMERATED
{
    dSL(1),
    pON(2)
}

-- TS 29.571 [17], table 5.4.2-1
TAC ::= OCTET STRING (SIZE(2..3))

-- TS 38.413 [23], clause 9.3.1.9
EUTRACellID ::= BIT STRING (SIZE(28))

-- TS 38.413 [23], clause 9.3.1.7
NRCellID ::= BIT STRING (SIZE(36))

-- TS 38.413 [23], clause 9.3.1.8
NGENbID ::= CHOICE
{
    macroNGENbID                [1] BIT STRING (SIZE(20)),
    shortMacroNGENbID           [2] BIT STRING (SIZE(18)),
    longMacroNGENbID            [3] BIT STRING (SIZE(21))
}
-- TS 23.003 [19], clause 12.7.1 encoded as per TS 29.571 [17], clause 5.4.2
NID ::= UTF8String (SIZE(11))

-- TS 36.413 [38], clause 9.2.1.37
ENbID ::= CHOICE
{
    macroENbID                  [1] BIT STRING (SIZE(20)),
    homeENbID                   [2] BIT STRING (SIZE(28)),
    shortMacroENbID             [3] BIT STRING (SIZE(18)),
    longMacroENbID              [4] BIT STRING (SIZE(21))
}


-- TS 29.518 [22], clause 6.4.6.2.3
PositioningInfo ::= SEQUENCE
{
    positionInfo                [1] LocationData OPTIONAL,
    rawMLPResponse              [2] RawMLPResponse OPTIONAL
}

RawMLPResponse ::= CHOICE
{
    -- The following parameter contains a copy of unparsed XML code of the
    -- MLP response message, i.e. the entire XML document containing
    -- a <slia> (described in OMA-TS-MLP-V3_5-20181211-C [20], clause 5.2.3.2.2) or
    -- a <slirep> (described in OMA-TS-MLP-V3_5-20181211-C [20], clause 5.2.3.2.3) MLP message.
    mLPPositionData             [1] UTF8String,
    -- OMA MLP result id, defined in OMA-TS-MLP-V3_5-20181211-C [20], Clause 5.4
    mLPErrorCode                [2] INTEGER (1..699)
}

-- TS 29.572 [24], clause 6.1.6.2.3
LocationData ::= SEQUENCE
{
    locationEstimate            [1] GeographicArea,
    accuracyFulfilmentIndicator [2] AccuracyFulfilmentIndicator OPTIONAL,
    ageOfLocationEstimate       [3] AgeOfLocation OPTIONAL,
    velocityEstimate            [4] VelocityEstimate OPTIONAL,
    civicAddress                [5] CivicAddress OPTIONAL,
    positioningDataList         [6] SET OF PositioningMethodAndUsage OPTIONAL,
    gNSSPositioningDataList     [7] SET OF GNSSPositioningMethodAndUsage OPTIONAL,
    eCGI                        [8] ECGI OPTIONAL,
    nCGI                        [9] NCGI OPTIONAL,
    altitude                    [10] Altitude OPTIONAL,
    barometricPressure          [11] BarometricPressure OPTIONAL
}

-- TS 29.172 [53], clause 7.4.29
GERANPositioningInfo ::= SEQUENCE
{
    gERANPositioningData      [1] GERANPositioningData OPTIONAL,
    gERANGANSSPositioningData [2] GERANGANSSPositioningData OPTIONAL
}

-- TS 29.172 [53], clause 7.4.30
GERANPositioningData ::= OCTET STRING

-- TS 29.172 [53], clause 7.4.31
GERANGANSSPositioningData ::= OCTET STRING

-- TS 29.172 [53], clause 7.4.32
UTRANPositioningInfo ::= SEQUENCE
{
    uTRANPositioningData           [1] UTRANPositioningData OPTIONAL,
    uTRANGANSSPositioningData      [2] UTRANGANSSPositioningData OPTIONAL,
    uTRANAdditionalPositioningData [3] UTRANAdditionalPositioningData
}

-- TS 29.172 [53], clause 7.4.33
UTRANPositioningData ::= OCTET STRING

-- TS 29.172 [53], clause 7.4.34
UTRANGANSSPositioningData ::= OCTET STRING

-- TS 29.172 [53], clause 7.4.63
UTRANAdditionalPositioningData ::= OCTET STRING

-- TS 29.172 [53], table 6.2.2-2
FourGPositioningInfo ::= SEQUENCE
{
    locationData              [1] LocationData,
    cGI                       [2] CGI OPTIONAL,
    sAI                       [3] SAI OPTIONAL,
    eSMLCCellInfo             [4] ESMLCCellInfo OPTIONAL,
    gERANPositioningInfo      [5] GERANPositioningInfo OPTIONAL,
    uTRANPositioningInfo      [6] UTRANPositioningInfo OPTIONAL,
    rawMLPResponse            [7] RawMLPResponse OPTIONAL
}

FourGLocationInfo ::= CHOICE
{
    ePSLocationInformation     [1] EPSLocationInformation,
    ePSUserLocationInformation [2] EPSUserLocationInformation
}

-- TS 29.272 [106], clause 7.3.111
EPSLocationInformation ::= SEQUENCE
{
    mMELocationInformation  [1] MMELocationInformation OPTIONAL,
    sGSNLocationInformation [2] SGSNLocationInformation OPTIONAL
}

-- TS 29.274 [87], clause 8.21
EPSUserLocationInformation ::= OCTET STRING

-- TS 29.272 [106], clause 7.3.115
MMELocationInformation ::= SEQUENCE
{
    eCGI                     [1] ECGI OPTIONAL,
    tAI                      [2] TAI OPTIONAL,
    geographicalInformation  [3] GeographicalInformationOctet OPTIONAL,
    geodeticInformation      [4] GeodeticInformationOctet OPTIONAL,
    currentLocationRetrieved [5] BOOLEAN OPTIONAL,
    ageOfLocationInformation [6] INTEGER OPTIONAL,
    userCSGInformation       [7] UserCSGInformation OPTIONAL,
    eNbID                    [8] ENbID OPTIONAL,
    additionalCellIDs        [9] SEQUENCE OF CellInformation OPTIONAL
}

-- TS 32.299 [111], clause 7.3.240A
UserCSGInformation ::= SEQUENCE
{
    cSGID                   [1] CSGID,
    cSGAccessMode           [2] CSGAccessMode,
    cSGMembershipIndication [3] CSGMembershipIndication
}

-- TS 29.272 [106], clause 7.3.79
CSGID ::= INTEGER

CSGIDList ::= SEQUENCE SIZE(1..MAX) OF CSGID

-- TS 32.299 [111], clause 7.2.46A
CSGAccessMode ::= ENUMERATED
{
    closedMode(1),
    hybridMode(2)
}

-- TS 32.299 [111], clause 7.2.46B
CSGMembershipIndication ::= ENUMERATED
{
    notCSGMember(1),
    cSGMember(2)
}

-- TS 29.272 [106], clause 7.3.116
SGSNLocationInformation ::= SEQUENCE
{
    cGI                      [1] CGI OPTIONAL,
    lAI                      [2] LAI OPTIONAL,
    sAI                      [3] SAI OPTIONAL,
    rAI                      [4] RAI OPTIONAL,
    geographicalInformation  [5] GeographicalInformationOctet OPTIONAL,
    geodeticInformation      [6] GeodeticInformationOctet OPTIONAL,
    currentLocationRetrieved [7] BOOLEAN OPTIONAL,
    ageOfLocationInformation [8] INTEGER OPTIONAL,
    userCSGInformation       [9] UserCSGInformation OPTIONAL
}

-- TS 29.172 [53], clause 7.4.57
ESMLCCellInfo ::= SEQUENCE
{
    eCGI          [1] ECGI,
    cellPortionID [2] CellPortionID
}

-- TS 29.171 [54], clause 7.4.31
CellPortionID ::= INTEGER (0..4095)

-- TS 29.518 [22], clause 6.2.6.2.5
LocationPresenceReport ::= SEQUENCE
{
    type                        [1] AMFEventType,
    timestamp                   [2] Timestamp,
    areaList                    [3] SET OF AMFEventArea OPTIONAL,
    timeZone                    [4] TimeZone OPTIONAL,
    accessTypes                 [5] SET OF AccessType OPTIONAL,
    rMInfoList                  [6] SET OF RMInfo OPTIONAL,
    cMInfoList                  [7] SET OF CMInfo OPTIONAL,
    reachability                [8] UEReachability OPTIONAL,
    location                    [9] UserLocation OPTIONAL,
    additionalCellIDs           [10] SEQUENCE OF CellInformation OPTIONAL
}

-- TS 29.518 [22], clause 6.2.6.3.3
AMFEventType ::= ENUMERATED
{
    locationReport(1),
    presenceInAOIReport(2)
}

-- TS 29.518 [22], clause 6.2.6.2.16
AMFEventArea ::= SEQUENCE
{
    presenceInfo                [1] PresenceInfo OPTIONAL,
    lADNInfo                    [2] LADNInfo OPTIONAL
}

-- TS 29.571 [17], clause 5.4.4.27
PresenceInfo ::= SEQUENCE
{
    presenceState               [1] PresenceState OPTIONAL,
    trackingAreaList            [2] SET OF TAI OPTIONAL,
    eCGIList                    [3] SET OF ECGI OPTIONAL,
    nCGIList                    [4] SET OF NCGI OPTIONAL,
    globalRANNodeIDList         [5] SET OF GlobalRANNodeID OPTIONAL,
    globalENbIDList             [6] SET OF GlobalRANNodeID OPTIONAL
}

-- TS 29.518 [22], clause 6.2.6.2.17
LADNInfo ::= SEQUENCE
{
    lADN                        [1] UTF8String,
    presence                    [2] PresenceState OPTIONAL
}

-- TS 29.571 [17], clause 5.4.3.20
PresenceState ::= ENUMERATED
{
    inArea(1),
    outOfArea(2),
    unknown(3),
    inactive(4)
}

-- TS 29.518 [22], clause 6.2.6.2.8
RMInfo ::= SEQUENCE
{
    rMState                     [1] RMState,
    accessType                  [2] AccessType
}

-- TS 29.518 [22], clause 6.2.6.2.9
CMInfo ::= SEQUENCE
{
    cMState                     [1] CMState,
    accessType                  [2] AccessType
}

-- TS 29.518 [22], clause 6.2.6.3.7
UEReachability ::= ENUMERATED
{
    unreachable(1),
    reachable(2),
    regulatoryOnly(3)
}

-- TS 29.518 [22], clause 6.2.6.3.9
RMState ::= ENUMERATED
{
    registered(1),
    deregistered(2)
}

-- TS 29.518 [22], clause 6.2.6.3.10
CMState ::= ENUMERATED
{
    idle(1),
    connected(2)
}

-- TS 29.572 [24], clause 6.1.6.2.5
GeographicArea ::= CHOICE
{
    point                       [1] Point,
    pointUncertaintyCircle      [2] PointUncertaintyCircle,
    pointUncertaintyEllipse     [3] PointUncertaintyEllipse,
    polygon                     [4] Polygon,
    pointAltitude               [5] PointAltitude,
    pointAltitudeUncertainty    [6] PointAltitudeUncertainty,
    ellipsoidArc                [7] EllipsoidArc
}

-- TS 29.002 [47], clause 17.7.1, type GeographicalInformation
GeographicalInformationOctet ::= OCTET STRING (SIZE (8))

-- TS 29.002 [47], clause 17.7.1, type GeodeticInformation
GeodeticInformationOctet ::= OCTET STRING (SIZE (10))

-- TS 29.572 [24], clause 6.1.6.3.12
AccuracyFulfilmentIndicator ::= ENUMERATED
{
    requestedAccuracyFulfilled(1),
    requestedAccuracyNotFulfilled(2)
}

-- TS 29.572 [24], clause 6.1.6.2.17
VelocityEstimate ::= CHOICE
{
    horVelocity                         [1] HorizontalVelocity,
    horWithVertVelocity                 [2] HorizontalWithVerticalVelocity,
    horVelocityWithUncertainty          [3] HorizontalVelocityWithUncertainty,
    horWithVertVelocityAndUncertainty   [4] HorizontalWithVerticalVelocityAndUncertainty
}

-- TS 29.572 [24], clause 6.1.6.2.14
CivicAddress ::= SEQUENCE
{
    country                             [1] UTF8String,
    a1                                  [2] UTF8String OPTIONAL,
    a2                                  [3] UTF8String OPTIONAL,
    a3                                  [4] UTF8String OPTIONAL,
    a4                                  [5] UTF8String OPTIONAL,
    a5                                  [6] UTF8String OPTIONAL,
    a6                                  [7] UTF8String OPTIONAL,
    prd                                 [8] UTF8String OPTIONAL,
    pod                                 [9] UTF8String OPTIONAL,
    sts                                 [10] UTF8String OPTIONAL,
    hno                                 [11] UTF8String OPTIONAL,
    hns                                 [12] UTF8String OPTIONAL,
    lmk                                 [13] UTF8String OPTIONAL,
    loc                                 [14] UTF8String OPTIONAL,
    nam                                 [15] UTF8String OPTIONAL,
    pc                                  [16] UTF8String OPTIONAL,
    bld                                 [17] UTF8String OPTIONAL,
    unit                                [18] UTF8String OPTIONAL,
    flr                                 [19] UTF8String OPTIONAL,
    room                                [20] UTF8String OPTIONAL,
    plc                                 [21] UTF8String OPTIONAL,
    pcn                                 [22] UTF8String OPTIONAL,
    pobox                               [23] UTF8String OPTIONAL,
    addcode                             [24] UTF8String OPTIONAL,
    seat                                [25] UTF8String OPTIONAL,
    rd                                  [26] UTF8String OPTIONAL,
    rdsec                               [27] UTF8String OPTIONAL,
    rdbr                                [28] UTF8String OPTIONAL,
    rdsubbr                             [29] UTF8String OPTIONAL,
    prm                                 [30] UTF8String OPTIONAL,
    pom                                 [31] UTF8String OPTIONAL
}

-- TS 29.571 [17], clauses 5.4.4.62 and 5.4.4.64
-- Contains the original binary data i.e. value of the YAML field after base64 encoding is removed
CivicAddressBytes ::= OCTET STRING

-- TS 29.572 [24], clause 6.1.6.2.15
PositioningMethodAndUsage ::= SEQUENCE
{
    method                              [1] PositioningMethod,
    mode                                [2] PositioningMode,
    usage                               [3] Usage,
    methodCode                          [4] MethodCode OPTIONAL
}

-- TS 29.572 [24], clause 6.1.6.2.16
GNSSPositioningMethodAndUsage ::= SEQUENCE
{
    mode                                [1] PositioningMode,
    gNSS                                [2] GNSSID,
    usage                               [3] Usage
}

-- TS 29.572 [24], clause 6.1.6.2.6
Point ::= SEQUENCE
{
    geographicalCoordinates             [1] GeographicalCoordinates
}

-- TS 29.572 [24], clause 6.1.6.2.7
PointUncertaintyCircle ::= SEQUENCE
{
    geographicalCoordinates             [1] GeographicalCoordinates,
    -- deprecatedUncertainty was deprecated in r18(18) version3(3)
    -- and shall be set to 0. The uncertaintySBI parameter shall be used instead.
    deprecatedUncertainty               [2] Uncertainty,
    uncertaintySBI                      [3] UncertaintySBI OPTIONAL
}

-- TS 29.572 [24], clause 6.1.6.2.8
PointUncertaintyEllipse ::= SEQUENCE
{
    geographicalCoordinates             [1] GeographicalCoordinates,
    uncertainty                         [2] UncertaintyEllipse,
    confidence                          [3] Confidence
}

-- TS 29.572 [24], clause 6.1.6.2.9
Polygon ::= SEQUENCE
{
    pointList                           [1] SET SIZE (3..15) OF GeographicalCoordinates
}

-- TS 29.572 [24], clause 6.1.6.2.10
PointAltitude ::= SEQUENCE
{
    point                               [1] GeographicalCoordinates,
    altitude                            [2] Altitude
}

-- TS 29.572 [24], clause 6.1.6.2.11
PointAltitudeUncertainty ::= SEQUENCE
{
    point                               [1] GeographicalCoordinates,
    altitude                            [2] Altitude,
    uncertaintyEllipse                  [3] UncertaintyEllipse,
    -- deprecatedUncertaintyAltitude was deprecated in r18(18) version3(3)
    -- and shall be set to 0. The uncertaintyAltitudeSBI parameter shall be used instead.
    deprecatedUncertaintyAltitude       [4] Uncertainty,
    confidence                          [5] Confidence,
    uncertaintyAltitudeSBI              [6] UncertaintySBI OPTIONAL
}

-- TS 29.572 [24], clause 6.1.6.2.12
EllipsoidArc ::= SEQUENCE
{
    point                               [1] GeographicalCoordinates,
    innerRadius                         [2] InnerRadius,
    -- deprecatedUncertaintyRadius was deprecated in r18(18) version3(3)
    -- and shall be set to 0. The uncertaintyRadiusSBI parameter shall be used instead.
    deprecatedUncertaintyRadius         [3] Uncertainty,
    offsetAngle                         [4] Angle,
    includedAngle                       [5] Angle,
    confidence                          [6] Confidence,
    uncertaintyRadiusSBI                [7] UncertaintySBI OPTIONAL
}

-- TS 29.572 [24], clause 6.1.6.2.4
GeographicalCoordinates ::= SEQUENCE
{
    latitude                            [1] UTF8String,
    longitude                           [2] UTF8String,
    mapDatumInformation                 [3] OGCURN OPTIONAL
}

-- TS 29.572 [24], clause 6.1.6.2.22
UncertaintyEllipse ::= SEQUENCE
{
    -- deprecatedSemiMajor was deprecated in r18(18) version3(3)
    -- and shall be set to 0. The semiMajorSBI parameter shall be used instead.
    deprecatedSemiMajor                 [1] Uncertainty,
    -- deprecatedSemiMinor was deprecated in r18(18) version3(3)
    -- and shall be set to 0. The semiMinorSBI parameter shall be used instead.
    deprecatedSemiMinor                 [2] Uncertainty,
    orientationMajor                    [3] Orientation,
    semiMajorSBI                        [4] UncertaintySBI OPTIONAL,
    semiMinorSBI                        [5] UncertaintySBI OPTIONAL
}

-- TS 29.572 [24], clause 6.1.6.2.18
HorizontalVelocity ::= SEQUENCE
{
    hSpeed                              [1] HorizontalSpeed,
    bearing                             [2] Angle
}

-- TS 29.572 [24], clause 6.1.6.2.19
HorizontalWithVerticalVelocity ::= SEQUENCE
{
    hSpeed                              [1] HorizontalSpeed,
    bearing                             [2] Angle,
    vSpeed                              [3] VerticalSpeed,
    vDirection                          [4] VerticalDirection
}

-- TS 29.572 [24], clause 6.1.6.2.20
HorizontalVelocityWithUncertainty ::= SEQUENCE
{
    hSpeed                              [1] HorizontalSpeed,
    bearing                             [2] Angle,
    uncertainty                         [3] SpeedUncertainty
}

-- TS 29.572 [24], clause 6.1.6.2.21
HorizontalWithVerticalVelocityAndUncertainty ::= SEQUENCE
{
    hSpeed                              [1] HorizontalSpeed,
    bearing                             [2] Angle,
    vSpeed                              [3] VerticalSpeed,
    vDirection                          [4] VerticalDirection,
    hUncertainty                        [5] SpeedUncertainty,
    vUncertainty                        [6] SpeedUncertainty
}

-- The following types are described in TS 29.572 [24], table 6.1.6.3.2-1

Altitude ::= UTF8String
Angle ::= INTEGER (0..360)
UncertaintySBI ::= UTF8String
Orientation ::= INTEGER (0..180)
Confidence ::= INTEGER (0..100)
InnerRadius ::= INTEGER (0..327675)
AgeOfLocation ::= INTEGER (0..32767)
HorizontalSpeed ::= UTF8String
VerticalSpeed ::= UTF8String
SpeedUncertainty ::= UTF8String
BarometricPressure ::= INTEGER (30000..115000)
Uncertainty ::= INTEGER (0..127)

-- TS 29.572 [24], clause 6.1.6.3.13
VerticalDirection ::= ENUMERATED
{
    upward(1),
    downward(2)
}

-- TS 29.572 [24], clause 6.1.6.3.6
PositioningMethod ::= ENUMERATED
{
    cellID(1),
    eCID(2),
    oTDOA(3),
    barometricPressure(4),
    wLAN(5),
    bluetooth(6),
    mBS(7),
    motionSensor(8),
    dLTDOA(9),
    dLAOD(10),
    multiRTT(11),
    nRECID(12),
    uLTDOA(13),
    uLAOA(14),
    networkSpecific(15)
}

-- TS 29.572 [24], clause 6.1.6.3.7
PositioningMode ::= ENUMERATED
{
    uEBased(1),
    uEAssisted(2),
    conventional(3)
}

-- TS 29.572 [24], clause 6.1.6.3.8
GNSSID ::= ENUMERATED
{
    gPS(1),
    galileo(2),
    sBAS(3),
    modernizedGPS(4),
    qZSS(5),
    gLONASS(6),
    bDS(7),
    nAVIC(8)
}

-- TS 29.572 [24], clause 6.1.6.3.9
Usage ::= ENUMERATED
{
    unsuccess(1),
    successResultsNotUsed(2),
    successResultsUsedToVerifyLocation(3),
    successResultsUsedToGenerateLocation(4),
    successMethodNotDetermined(5)
}

-- TS 29.571 [17], table 5.2.2-1
TimeZone ::= UTF8String

-- Open Geospatial Consortium URN [35]
OGCURN ::= UTF8String

-- TS 29.572 [24], clause 6.1.6.2.15
MethodCode ::= INTEGER (16..31)

PANIHeaderInfo ::= SEQUENCE
{
    accessNetworkInformation [1] SIPAccessNetworkInformation,
    accessInfo               [2] SEQUENCE OF SIPAccessInfo OPTIONAL,
    pANILocation             [3] SEQUENCE OF SIPLocationInfo OPTIONAL
}

SIPGeolocationHeaderInfo ::= SEQUENCE
{
    locationValue [1] UTF8String,
    cidInfo       [2] UTF8String OPTIONAL
}

SIPAccessInfo ::= UTF8String

SIPCellularAccessInfo ::= SEQUENCE
{
    accessInfo  [1] SIPAccessInfo,
    cellInfoAge [2] SIPCNICellInfoAge
}

SIPCNICellInfoAge ::= INTEGER(0..999999999)

SIPLocationInfo ::= SEQUENCE
{
    locationInfo    [1] LocationInfo OPTIONAL,
    cellInformation [2] CellInformation OPTIONAL
}

SIPAccessNetworkInformation ::= SEQUENCE
{
    accessNetworkInfo [1] UTF8String,
    servingPLMN       [2] PLMNID OPTIONAL
}

SIPCNIHeaderInfo ::= SEQUENCE
{
    cellularNetworkInformation [1] SIPCellularNetworkInformation,
    cellularAccessInfo         [2] SEQUENCE OF SIPCellularAccessInfo OPTIONAL,
    cNILocation                [3] SEQUENCE OF SIPLocationInfo OPTIONAL
}

SIPCellularNetworkInformation ::= SEQUENCE
{
    cellularNetworkInfo  [1] UTF8String,
    servingPLMN          [2] PLMNID OPTIONAL
}

-- TS 29.571 [17], clause 5.4.4.9 and TS 38.413 [23] clause 9.3.3.53
NRNTNTAIInfo ::= SEQUENCE
{
    servingPLMN                   [1] PLMNID,
    tACListNRNTN                  [2] SEQUENCE (SIZE(1..MAX)) OF TAC,
    uELocationDerivedNTNTAC       [3] TAC OPTIONAL
}

-- TS 38.413 [23], clause 9.3.1.260
IABMTUserLocation ::= SEQUENCE
{
    nRCGI             [1] NCGI,
    tAI               [2] TAI OPTIONAL
}

CoarseLocation ::= CHOICE
{
    tS36413CoarseUELocation [1] TS36413CoarseUELocation
}

-- TS 36.413 [38], clause 9.2.1.167
TS36413CoarseUELocation ::= OCTET STRING

-- ==================================================
-- Structures to allow reuse of encapsulated payloads
-- ==================================================

RCSPayload ::= CHOICE
{
    fullPayload     [1] EncapsulatedRCSPayload,
    modifiedPayload [2] ModifiedRCSPayload
}

EncapsulatedRCSPayload ::= CHOICE
{
    mIME [1] MIMEEntity,
    mSRP [2] MSRPMessage,
    sIP  [3] SIPMessage
}

ModifiedRCSPayload ::= SEQUENCE
{
    modifiedRCSPayload [1] EncapsulatedRCSPayload,
    modifications      [2] PayloadModifications
}

PayloadModifications ::= SEQUENCE
{
    modificationList [1] SEQUENCE OF PayloadModification
}

PayloadModification ::= CHOICE
{
    predefinedModification [1] PredefinedPayloadModification,
    describedModification  [2] PayloadModificationDescription
}

PredefinedPayloadModification ::= ENUMERATED
{
    pANILocationRemoval(1),
    cNILocationRemoval(2),
    sIPGeolocationInfoRemoval(3),
    presenceInformationLocationRemoval(4),
    tS33128SMSTPDURedaction(5),
    tS33128TruncatedSMSTPDU(6),
    iMSTextContentRemoval(7),
    iMSSubjectContentRemoval(8),
    rCSPresenceLocationRemoval(9),
    rCSCPIMLocationRemoval(10),
    rCSTextContentRemoval(11),
    rCSSubjectContentRemoval(12),
    rCSGeolocationPUSHContentRemoval(13),
    rCSFileURLContentRemoval(14),
    threeGPP2SMSUserDataRedaction(15)
}

PayloadModificationDescription ::= SEQUENCE
{
    modificationLocation [1] ModificationLocation,
    modificationType     [2] ModificationType
}

ModificationLocation ::= CHOICE
{
    jSONPointer        [1] UTF8String,
    xPath              [2] UTF8String,
    sIPHeader          [3] UTF8String,
    sIPBody            [4] NULL,
    mIMEHeader         [5] UTF8String,
    mIMEBody           [6] MIMEBody,
    uTF8Location       [7] IndexRange,
    octetLocation      [8] IndexRange,
    aBNFRule           [9] ABNFRuleLocation
}

ABNFRuleLocation ::= UTF8String

ModificationType ::= CHOICE
{
    removed                  [1] PayloadInformationRemoved,
    replacedWithCharacters   [2] PayloadInformationReplacedWithCharacters,
    replacedWithOctets       [3] OCTET STRING,
    replacedWithBits         [4] BIT STRING
}

PayloadInformationRemoved ::= CHOICE
{
    charactersRemoved [1] INTEGER,
    octetsRemoved     [2] INTEGER,
    bitsRemoved       [3] INTEGER
}

PayloadInformationReplacedWithCharacters ::= SEQUENCE
{
    characters [1] UTF8String
}

IndexRange ::= SEQUENCE
{
    start [1] INTEGER,
    end   [2] INTEGER
}

-- ===============================================
-- Externally Defined Structures - MSRP Parameters
-- ===============================================

EncapsulatedMSRP ::= UTF8String

MSRPMessage ::= SEQUENCE
{
    encapsulatedMSRP [1] EncapsulatedMSRP
}

-- ==================================================
-- Externally Defined Structures - SBIType Parameters
-- ==================================================

-- Details for the encoding and use of this parameter may be found in the clause
-- that defines the xIRI that carries it. This parameter provides a generic
-- mechanism to convey service based interface structures defined in Stage 3 working groups.

SBIType ::= SEQUENCE
{
    sBIReference         [1] SBIReference,
    sBIValue             [2] SBIValue
}

SBIReference ::= UTF8String

SBIValue ::= UTF8String

-- ==================================================
-- Externally Defined Structures - XMLType Parameters
-- ==================================================

XMLType ::= SEQUENCE
{
    xMLNamespace [1] XMLNamespace,
    xMLValue     [2] XMLValue
}

XMLNamespace ::= UTF8String

XMLValue ::= UTF8String

-- ======================================================
-- Externally Defined Structures - MIME Entity Parameters
-- ======================================================

EncapsulatedMIMEEntity ::= UTF8String

MIMEContentType ::= UTF8String

MIMEEntity ::= SEQUENCE
{
    contentType            [1] MIMEContentType,
    encapsulatedMIMEEntity [2] EncapsulatedMIMEEntity
}

MIMEPartIdentifier ::= CHOICE
{
    index     [1] INTEGER
}

MIMEBody ::= CHOICE
{
    fullBody [1] NULL,
    bodyPart [2] MIMEPartIdentifier
}

-- =======================================================
-- Externally Defined Structures - External ASN Parameters
-- =======================================================
ExternalASNType ::= SEQUENCE
{
    moduleIdentifier [1] OBJECT IDENTIFIER,
    aSNReference     [2] ExternalASNReference OPTIONAL,
    encodedASNValue  [3] ExternalASNValue
}

ExternalASNReference ::= UTF8String

ExternalASNValue ::= CHOICE
{
    bER          [1] OCTET STRING,
    alignedPER   [2] OCTET STRING
}

END

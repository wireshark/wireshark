-- Extracted from RFC 4985 Appendix A.1.  1988 ASN.1 Module
--
   PKIXServiceNameSAN88 {iso(1) identified-organization(3) dod(6)
         internet(1) security(5) mechanisms(5) pkix(7) id-mod(0)
         id-mod-dns-srv-name-88(39) }

   DEFINITIONS EXPLICIT TAGS ::=

      BEGIN

      -- EXPORTS ALL --

      IMPORTS

   -- UTF8String, / move hyphens before slash if UTF8String does not
   -- resolve with your compiler

        id-pkix
              FROM PKIX1Explicit88 { iso(1) identified-organization(3)
              dod(6) internet(1) security(5) mechanisms(5) pkix(7)
              id-mod(0) id-pkix1-explicit(18) } ;
              -- from RFC3280 [N2]
     -- Service Name Object Identifier and Syntax
     -- id-pkix OBJECT IDENTIFIER ::= {1 3 6 1 5 5 7}

     id-on   OBJECT IDENTIFIER ::= { id-pkix 8 }

     id-on-dnsSRV OBJECT IDENTIFIER ::= { id-on 7 }

     SRVName ::= IA5String    (SIZE (1..MAX))

   END

-- Extracted from RFC 4985 Appendix A.2.  1993 ASN.1 Module
--
   PKIXServiceNameSAN93 {iso(1) identified-organization(3) dod(6)
       internet(1) security(5) mechanisms(5) pkix(7) id-mod(0)
       id-mod-dns-srv-name-93(40) }

   DEFINITIONS EXPLICIT TAGS ::=

   BEGIN

   -- EXPORTS ALL --

   IMPORTS

      id-pkix
            FROM PKIX1Explicit88 { iso(1) identified-organization(3)
            dod(6) internet(1) security(5) mechanisms(5) pkix(7)
            id-mod(0) id-pkix1-explicit(18) } ;
             -- from RFC 3280 [N2]


   -- In the GeneralName definition using the 1993 ASN.1 syntax
   -- includes:

   OTHER-NAME ::= TYPE-IDENTIFIER


   -- Service Name Object Identifier

--   id-on   OBJECT IDENTIFIER ::= { id-pkix 8 }

--   id-on-dnsSRV OBJECT IDENTIFIER ::= { id-on 7 }
   -- Service Name

   srvName OTHER-NAME ::= { SRVName IDENTIFIED BY { id-on-dnsSRV }}

--   SRVName ::= IA5String (SIZE (1..MAX))

   END

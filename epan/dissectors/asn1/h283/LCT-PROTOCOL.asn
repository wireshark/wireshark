-- http://www.itu.int/ITU-T/asn1/database/itu-t/h/h283/1999/LCT-PROTOCOL.asn

-- Module LCT-PROTOCOL (H.283:05/1999)
LCT-PROTOCOL {itu-t recommendation h 283 version(0) 1} DEFINITIONS AUTOMATIC
TAGS ::=
BEGIN

H221NonStandard ::= SEQUENCE {
  t35CountryCode    INTEGER(0..255), -- country, as per Recommendation T.35
  t35Extension      INTEGER(0..255), -- assigned nationally
  manufacturerCode  INTEGER(0..65535)
} -- assigned nationally

NonStandardIdentifier ::= CHOICE {
  object           OBJECT IDENTIFIER,
  h221NonStandard  H221NonStandard,
  ...
}

NonStandardParameter ::= SEQUENCE {
  nonStandardIdentifier  NonStandardIdentifier,
  data                   OCTET STRING
}

LCTPDU ::= SEQUENCE {
  srcAddr                MTAddress,
  dstAddr                MTAddress,
  timestamp              INTEGER(0..4294967295), -- milliseconds
  seqNumber              INTEGER(0..65535),
  pduType                CHOICE {ack      NULL,
                                 rdcData  RDCData},
  nonStandardParameters  SEQUENCE OF NonStandardParameter OPTIONAL,
  ...
}

MTAddress ::= SEQUENCE {
  mAddress  INTEGER(0..65535),
  tAddress  INTEGER(0..65535)
}

RDCData ::= SEQUENCE {
  reliable  BOOLEAN,
  dataType  CHOICE {lctMessage  LCTMessage,
                    rdcPDU      OCTET STRING}, -- Common RDC PDU
  ...
}

LCTMessage ::= CHOICE {
  lctRequest          LCTRequest,
  lctResponse         LCTResponse,
  lctIndication       LCTIndication,
  nonStandardMessage  NonStandardMessage,
  ...
}

LCTRequest ::= CHOICE {announceReq    NULL,
                       deviceListReq  NULL,
                       ...
}

LCTResponse ::= CHOICE {
  announceResp    NULL,
  deviceListResp  OCTET STRING, -- Common RDC 
  ...
}

LCTIndication ::= CHOICE {deviceChange  NULL,
                          ...
}

NonStandardMessage ::= SEQUENCE {
  nonStandardParameters  SEQUENCE OF NonStandardParameter OPTIONAL,
  ...
}

END

-- Generated by Asnp, the ASN.1 pretty-printer of France Telecom R&D

-- Copyright 2005 - 2009 Anders Broman
MAP-Protocol{ 0 identified-organization (4) etsi (0) mobileDomain (0) gsm-Network (1) modules (3) map-Protocol (4) version5 (5) }

DEFINITIONS ::=

BEGIN
-- Import from GSM MAP for convenience
IMPORTS
	IMSI
FROM MAP-CommonDataTypes {
   itu-t identified-organization (4) etsi (0) mobileDomain (0)
   gsm-Network (1) modules (3) map-CommonDataTypes (18) version12 (12)}
;
-- 6.4.2.1
-- http://www.3gpp2.org/Public_html/specs/X.S0004-550-E_v2.0_070723.pdf
AuthenticationDirective ::= [PRIVATE 18] SET {
	electronicSerialNumber					[9] IMPLICIT ElectronicSerialNumber,
	--M 6.5.2.63
--	mobileIdentificationNumber				[8] IMPLICIT MobileIdentificationNumber,
	--M 6.5.2.81
	msid									MSID OPTIONAL,
	--
	authenticationAlgorithmVersion			[77] IMPLICIT AuthenticationAlgorithmVersion OPTIONAL,
	-- O 6.5.2.7 a
	authenticationResponseReauthentication	[182] IMPLICIT AuthenticationResponseReauthentication OPTIONAL,
	-- O 6.5.2.mT j
	authenticationResponseUniqueChallenge	[37] IMPLICIT AuthenticationResponseUniqueChallenge OPTIONAL,
	--	O 6.5.2.12 b
	callHistoryCount						[38] IMPLICIT CallHistoryCount OPTIONAL,
	--	O 6.5.2.18
	cdmaPrivateLongCodeMask					[67] IMPLICIT CDMAPrivateLongCodeMask OPTIONAL,
	-- O 6.5.2.36 m
	carrierDigits							[86] IMPLICIT CarrierDigits OPTIONAL,
	-- O 6.5.2.28 j
	caveKey									[316] IMPLICIT CaveKey OPTIONAL,
	-- CaveKey O 2.38 p X.S0004-550-E_v1.0_040406.pdf
	denyAccess								[50] IMPLICIT DenyAccess OPTIONAL,
	--	O 6.5.2.54 d
	destinationDigits						[87] IMPLICIT	DestinationDigits OPTIONAL,
	-- O 6.5.2.56
	locationAreaID							[33] IMPLICIT LocationAreaID OPTIONAL,
	--	O 6.5.2.77 e
	randomVariableReauthentication			[191] IMPLICIT RandomVariableReauthentication OPTIONAL,
	-- O 6.5.2.uT j
	meid									[390] IMPLICIT MEID OPTIONAL,
	-- O
	mobileStationMIN						[184] IMPLICIT MobileStationMIN OPTIONAL,
	-- O 6.5.2.oC j
	mscid									[21] IMPLICIT MSCID OPTIONAL,
	-- O 6.5.2.82 n
	randomVariableSSD						[42] IMPLICIT RandomVariableSSD OPTIONAL,
	--	O 6.5.2.103 f
	randomVariableUniqueChallenge			[43] IMPLICIT RandomVariableUniqueChallenge OPTIONAL,
	--	O 6.5.2.104 b
	routingDigits							[150] IMPLICIT RoutingDigits OPTIONAL,
	-- O 6.5.2.114
	senderIdentificationNumber				[103] IMPLICIT SenderIdentificationNumber OPTIONAL,
	--	O 6.5.2.116 g
	-- ServiceIndicator O 2.221 k
	sharedSecretData						[46] IMPLICIT SharedSecretData OPTIONAL,
	--	O 6.5.2.119 c
	signalingMessageEncryptionKey			[45] IMPLICIT SignalingMessageEncryptionKey OPTIONAL,
	-- O 6.5.2.120 m
	ssdnotShared							[52] IMPLICIT SSDNotShared OPTIONAL,
	--	O 6.5.2.141 h
	updateCount								[51] IMPLICIT UpdateCount OPTIONAL
	--	O 6.5.2.163 i
	-- VoicePrivacyMask O 2.297 m
}
-- AuthenticationDirective RETURN RESULT Parameters
AuthenticationDirectiveRes ::= [PRIVATE 18] SET {
	callHistoryCount						[38] IMPLICIT CallHistoryCount OPTIONAL
	--	 O 6.5.2.18 a
}
-- 6.4.2.2
AuthenticationDirectiveForward ::= [PRIVATE 18] SET {
-- AuthenticationDirectiveForward INVOKE Parameters
	interMSCCircuitID						[6] IMPLICIT	InterMSCCircuitID,
	--	M 6.5.2.72
	mobileIdentificationNumber				[8] IMPLICIT MobileIdentificationNumber,
	--M 6.5.2.81
	authenticationResponseUniqueChallenge	[37] IMPLICIT AuthenticationResponseUniqueChallenge OPTIONAL,
	--	O 6.5.2.12 b
	randomVariableUniqueChallenge			[43] IMPLICIT RandomVariableUniqueChallenge OPTIONAL,
	--	O 6.5.2.104 b
	updateCount								[51] IMPLICIT UpdateCount OPTIONAL,
	-- O 6.5.2.163 b
	...
}

-- AuthenticationDirectiveForward RETURN RESULT Parameters

AuthenticationDirectiveForwardRes ::= [PRIVATE 18] SET {
	countUpdateReport						[138] IMPLICIT CountUpdateReport OPTIONAL,
	-- O 6.5.2.52 a
	uniqueChallengeReport					[124] IMPLICIT UniqueChallengeReport OPTIONAL,
	--	O 6.5.2.162
	...
}
-- http://www.3gpp2.org/Public_html/specs/X.S0004-540-E_v2.0_070723.pdf
-- 6.4.2.3 AuthenticationFailureReport
AuthenticationFailureReport ::= [PRIVATE 18] SET {
	electronicSerialNumber					[9] IMPLICIT ElectronicSerialNumber,
	--M 6.5.2.63
	msid									MSID OPTIONAL,
	reportType								[44] IMPLICIT ReportType,
	-- 	M 6.5.2.112
	systemAccessType						[34] IMPLICIT SystemAccessType,
	--	M 6.5.2.145
	systemCapabilities						[49] IMPLICIT SystemCapabilities,
	--	(Serving) M 6.5.2.146
	callHistoryCount						[38] IMPLICIT CallHistoryCount OPTIONAL,
	--	O 6.5.2.18 a
	callHistoryCountExpected				[79] IMPLICIT CallHistoryCountExpected OPTIONAL,
	--	 O 6.5.2.19 a
	mscid									[21] IMPLICIT MSCID OPTIONAL,
	--	(Serving MSC) O 6.5.2.82 b
	reportType2								[44] IMPLICIT ReportType OPTIONAL,
	-- 	M 6.5.2.112 c optional?
	senderIdentificationNumber				[103] IMPLICIT SenderIdentificationNumber OPTIONAL,
	--	O 6.5.2.116 d
	terminalType							[47] IMPLICIT TerminalType OPTIONAL,
	-- O 6.5.2.154
	meid									[390] IMPLICIT MEID OPTIONAL
	-- O
}

-- AuthenticationFailureReport RETURN RESULT Parameters
AuthenticationFailureReportRes ::= [PRIVATE 18] SET {
	authenticationAlgorithmVersion			[77] IMPLICIT AuthenticationAlgorithmVersion OPTIONAL,
	-- O 6.5.2.7 a
	authenticationResponseUniqueChallenge	[37] IMPLICIT AuthenticationResponseUniqueChallenge OPTIONAL,
	--O 6.5.2.12 b
	callHistoryCount						[38] IMPLICIT CallHistoryCount OPTIONAL,
	--O 6.5.2.18 c
	carrierDigits							[86] IMPLICIT CarrierDigits OPTIONAL,
	-- O 6.5.2.28 i
	denyAccess								[50] IMPLICIT DenyAccess OPTIONAL,
	-- O 6.5.2.54 d
	destinationDigits						[87] IMPLICIT	DestinationDigits OPTIONAL,
	-- O 6.5.2.56 i
	randomVariableSSD						[42] IMPLICIT RandomVariableSSD OPTIONAL,
	-- O 6.5.2.103 e
	randomVariableUniqueChallenge			[43] IMPLICIT RandomVariableUniqueChallenge OPTIONAL,
	-- O 6.5.2.104 b
	sharedSecretData						[46] IMPLICIT SharedSecretData OPTIONAL,
	-- O 6.5.2.119 c
	routingDigits							[150] IMPLICIT RoutingDigits OPTIONAL,
	-- O 6.5.2.114
	ssdnotShared							[52] IMPLICIT SSDNotShared OPTIONAL,
	-- O 6.5.2.141 f
	terminalType							[47] IMPLICIT TerminalType OPTIONAL,
	-- O 6.5.2.154 g
	updateCount								[51] IMPLICIT UpdateCount OPTIONAL
	-- O 6.5.2.163 h
}

-- 6.4.2.4 AuthenticationRequest

AuthenticationRequest ::= [PRIVATE 18] SET {
	electronicSerialNumber					[9] IMPLICIT ElectronicSerialNumber,
	-- M 6.5.2.63
--	mobileIdentificationNumber				[8] IMPLICIT MobileIdentificationNumber,
	-- M 6.5.2.81
	msid									MSID OPTIONAL,
	--M 6.5.2.bu
	mscid									[21] IMPLICIT MSCID,
	-- (Serving MSC) M 6.5.2.82
	systemAccessType						[34] IMPLICIT SystemAccessType,
	-- M 6.5.2.145
	systemCapabilities						[49] IMPLICIT SystemCapabilities,
	-- (Serving) M 6.5.2.146
	authenticationData						[161] IMPLICIT AuthenticationData OPTIONAL,
	-- O 6.5.2.9 a
	authenticationResponse					[35] IMPLICIT AuthenticationResponse,
	-- O 6.5.2.10 b
	callHistoryCount						[38] IMPLICIT CallHistoryCount OPTIONAL,
	-- O 6.5.2.18 b
	cdmaNetworkIdentification				[232] IMPLICIT CDMANetworkIdentification OPTIONAL,
	-- (Serving MSC) O 6.5.2.bk
	confidentialityModes					[39] IMPLICIT ConfidentialityModes OPTIONAL,
	-- (Actual) O 6.5.2.50 c
	controlChannelMode                      [199] IMPLICIT ControlChannelMode OPTIONAL,
	-- O 6.5.2.ac
	digits		 							[4] IMPLICIT Digits OPTIONAL,
	-- (Dialed) O 6.5.2.58 d
	pc-ssn									[32] IMPLICIT PC-SSN OPTIONAL,
	-- (Serving MSC or VLR or HLR) O 6.5.2.93 e
	randomVariable							[40] IMPLICIT RandomVariable OPTIONAL,
	-- O 6.5.2.101 b
	serviceRedirectionCause					[237] IMPLICIT ServiceRedirectionCause OPTIONAL,
	-- O 6.5.2.bp
	senderIdentificationNumber				[103] IMPLICIT SenderIdentificationNumber OPTIONAL,
	-- O 6.5.2.116 f
	suspiciousAccess						[285] IMPLICIT SuspiciousAccess OPTIONAL,
	-- O 6.5.2.do h
	terminalType							[47] IMPLICIT TerminalType OPTIONAL,
	-- O 6.5.2.154 g
	transactionCapability					[123] IMPLICIT TransactionCapability OPTIONAL,
	-- O 6.5.2.160
	meid									[390] IMPLICIT MEID OPTIONAL
	-- O
	}


-- AuthenticationRequest RETURN RESULT Parameters
AuthenticationRequestRes ::= [PRIVATE 18] SET {
	analogRedirectRecord					[225] IMPLICIT AnalogRedirectRecord OPTIONAL,
	-- O 6.5.2.bd j
	authenticationAlgorithmVersion			[77] IMPLICIT AuthenticationAlgorithmVersion OPTIONAL,
	-- O 6.5.2.7 a
	authenticationResponseUniqueChallenge	[37] IMPLICIT AuthenticationResponseUniqueChallenge OPTIONAL,
	-- O 6.5.2.12 b
	callHistoryCount						[38] IMPLICIT CallHistoryCount OPTIONAL,
	-- O 6.5.2.18 c
	carrierDigits							[86] IMPLICIT CarrierDigits OPTIONAL,
	-- O 6.5.2.28 i
	cdmaPrivateLongCodeMask					[67] IMPLICIT CDMAPrivateLongCodeMask OPTIONAL,
	--O 6.5.2.36 d
	cdmaRedirectRecord						[229] IMPLICIT CDMARedirectRecord OPTIONAL,
	-- O 6.5.2.bh k
	dataKey									[215] IMPLICIT DataKey OPTIONAL,
	-- O 6.5.2.at j
	denyAccess								[50] IMPLICIT DenyAccess OPTIONAL,
	-- O 6.5.2.54 e
	mobileIdentificationNumber				[8] IMPLICIT MobileIdentificationNumber OPTIONAL,
	-- O 6.5.2.81 l
	roamingIndication						[239] IMPLICIT RoamingIndication OPTIONAL,
	-- O 6.5.2.br m
	serviceRedirectionInfo					[238] IMPLICIT ServiceRedirectionInfo OPTIONAL,
	-- O 6.5.2.bq j, k
	destinationDigits						[87] IMPLICIT	DestinationDigits OPTIONAL,
	-- O 6.5.2.56 i
	randomVariableSSD						[42] IMPLICIT RandomVariableSSD OPTIONAL,
	-- O 6.5.2.103 f
	randomVariableUniqueChallenge			[43] IMPLICIT RandomVariableUniqueChallenge OPTIONAL,
	-- O 6.5.2.104 b
	routingDigits							[150] IMPLICIT RoutingDigits OPTIONAL,
	-- O 6.5.2.114
	sharedSecretData						[46] IMPLICIT SharedSecretData OPTIONAL,
	-- O 6.5.2.119 c
	signalingMessageEncryptionKey			[45] IMPLICIT SignalingMessageEncryptionKey OPTIONAL,
	-- O 6.5.2.120 g
	ssdnotShared							[52] IMPLICIT SSDNotShared OPTIONAL,
	-- O 6.5.2.141 h
	updateCount								[51] IMPLICIT UpdateCount OPTIONAL,
	-- O 6.5.2.163 i
	voicePrivacyMask						[48] IMPLICIT VoicePrivacyMask OPTIONAL,
	-- O 6.5.2.166 d
	...
}

-- 6.4.2.5 AuthenticationStatusReport

AuthenticationStatusReport ::= [PRIVATE 18] SET {
	electronicSerialNumber					[9] IMPLICIT ElectronicSerialNumber,
	-- M 6.5.2.63
--	mobileIdentificationNumber				[8] IMPLICIT MobileIdentificationNumber,
	-- M 6.5.2.81
	msid									MSID OPTIONAL,
	--
	systemCapabilities						[49] IMPLICIT SystemCapabilities,
	-- (Serving) M 6.5.2.146
	countUpdateReport						[138] IMPLICIT CountUpdateReport OPTIONAL,
	-- O 6.5.2.52 a
	meid									[390] IMPLICIT MEID OPTIONAL,
	--
	mscid									[21] IMPLICIT MSCID OPTIONAL,
	-- (Serving) O 6.5.2.82 e
	reauthenticationReport					[192] IMPLICIT ReauthenticationReport OPTIONAL,
	-- O 6.5.2.vT e
	senderIdentificationNumber				[103] IMPLICIT SenderIdentificationNumber OPTIONAL,
	-- O 6.5.2.116 b
	serviceIndicator						[193] IMPLICIT ServiceIndicator OPTIONAL,
	-- O 6.5.2.wB e
	signalingMessageEncryptionReport		[194] IMPLICIT SignalingMessageEncryptionReport OPTIONAL,
	-- O 6.5.2.xB h
	ssdUpdateReport							[156] IMPLICIT SSDUpdateReport OPTIONAL,
	-- O 6.5.2.142 c
	uniqueChallengeReport					[124] IMPLICIT UniqueChallengeReport OPTIONAL,
	-- O 6.5.2.162 d
	voicePrivacyReport						[196] IMPLICIT VoicePrivacyReport OPTIONAL
	-- O 6.5.2.zB g
}
-- AuthenticationStatusReport RETURN RESULT Parameters
AuthenticationStatusReportRes ::= [PRIVATE 18] SET {
	authenticationAlgorithmVersion			[77] IMPLICIT AuthenticationAlgorithmVersion OPTIONAL,
	-- O 6.5.2.7 a
	authenticationResponseUniqueChallenge	[37] IMPLICIT AuthenticationResponseUniqueChallenge OPTIONAL,
	-- O 6.5.2.12 b
	callHistoryCount						[38] IMPLICIT CallHistoryCount OPTIONAL,
	-- O 6.5.2.18 c
	carrierDigits							[86] IMPLICIT CarrierDigits OPTIONAL,
	-- O 6.5.2.28 i
	denyAccess								[50] IMPLICIT DenyAccess OPTIONAL,
	-- O 6.5.2.54 d
	destinationDigits						[87] IMPLICIT	DestinationDigits OPTIONAL,
	-- O 6.5.2.56 i
	randomVariableSSD						[42] IMPLICIT RandomVariableSSD OPTIONAL,
	-- O 6.5.2.103 e
	randomVariableUniqueChallenge			[43] IMPLICIT RandomVariableUniqueChallenge OPTIONAL,
	-- O 6.5.2.104 b
	routingDigits							[150] IMPLICIT RoutingDigits OPTIONAL,
	-- O 6.5.2.114
	sharedSecretData						[46] IMPLICIT SharedSecretData OPTIONAL,
	-- O 6.5.2.119 c
	ssdnotShared							[52] IMPLICIT SSDNotShared OPTIONAL,
	-- O 6.5.2.141 f
	updateCount								[51] IMPLICIT UpdateCount OPTIONAL,
	-- O 6.5.2.163 g
	...
}
-- 6.4.2.6 BaseStationChallenge
BaseStationChallenge ::= [PRIVATE 18] SET {
	electronicSerialNumber					[9] IMPLICIT ElectronicSerialNumber,
	-- M 6.5.2.63
--	mobileIdentificationNumber				[8] IMPLICIT MobileIdentificationNumber,
	-- M 6.5.2.81
	msid									MSID OPTIONAL,
	--
	randomVariableBaseStation				[41] IMPLICIT RandomVariableBaseStation,
	-- M 6.5.2.102
	senderIdentificationNumber				[103] IMPLICIT SenderIdentificationNumber OPTIONAL,
	-- O 6.5.2.116 a
	serviceIndicator						[193] IMPLICIT ServiceIndicator OPTIONAL,
	-- O 6.5.2.wB b
	meid									[390] IMPLICIT MEID OPTIONAL
	-- O
	}
-- BaseStationChallenge RETURN RESULT Parameters
BaseStationChallengeRes ::= [PRIVATE 18] SET {
	authenticationResponseBaseStation	[36] IMPLICIT AuthenticationResponseBaseStation,
	-- M 6.5.2.11
	...
	}
-- 6.4.2.7 Blocking

Blocking ::= [PRIVATE 18] SET {
	interMSCCircuitID						[6] IMPLICIT	InterMSCCircuitID,
	-- M 6.5.2.72
	...
	}
-- Blocking RETURN RESULT Parameters
-- zero octets

-- 6.4.2.8 BulkDeregistration
BulkDeregistration ::= [PRIVATE 18] SET {
	senderIdentificationNumber				[103] IMPLICIT SenderIdentificationNumber OPTIONAL,
	-- M 6.5.2.116
	...
	}
-- BulkDeregistration RETURN RESULT Parameters
-- zero octets

-- 6.4.2.9 CountRequest
CountRequest ::= [PRIVATE 18] SET {
	electronicSerialNumber					[9] IMPLICIT ElectronicSerialNumber,
	-- M 6.5.2.63
	mobileIdentificationNumber				[8] IMPLICIT MobileIdentificationNumber,
	-- M 6.5.2.81
	senderIdentificationNumber				[103] IMPLICIT SenderIdentificationNumber OPTIONAL,
	-- O 6.5.2.116 a
	meid									[390] IMPLICIT MEID OPTIONAL,
	-- O
	...
	}

--CountRequest RETURN RESULT Parameters
CountRequestRes ::= [PRIVATE 18] SET {
	callHistoryCount						[38] IMPLICIT CallHistoryCount OPTIONAL,
	-- O 6.5.2.18 a
	...
	}
-- 6.4.2.10 FacilitiesDirective
FacilitiesDirective ::= [PRIVATE 18] SET {
	billingID								[1] IMPLICIT BillingID,
	-- M 6.5.2.16
	channelData								[5] IMPLICIT ChannelData,
	-- (Serving) M 6.5.2.47 a
	electronicSerialNumber					[9] IMPLICIT ElectronicSerialNumber,
	-- M 6.5.2.63
	interMSCCircuitID						[6] IMPLICIT	InterMSCCircuitID,
	-- M 6.5.2.72
	interSwitchCount						[7] IMPLICIT InterSwitchCount,
	-- M 6.5.2.73
	mobileIdentificationNumber				[8] IMPLICIT MobileIdentificationNumber,
	-- M 6.5.2.81
	servingCellID							[2] IMPLICIT ServingCellID,
	-- M 6.5.2.117
	stationClassMark						[18] IMPLICIT StationClassMark,
	-- M 6.5.2.143
	targetCellID							[3] IMPLICIT TargetCellID,
	-- M 6.5.2.148
	confidentialityModes					[39] IMPLICIT ConfidentialityModes OPTIONAL,
	-- (Desired) O 6.5.2.50 b
	handoffReason							[30] IMPLICIT HandoffReason OPTIONAL,
	-- O 6.5.2.70 c
	handoffState							[164] IMPLICIT HandoffState OPTIONAL,
	-- O 6.5.2.71 d
	signalingMessageEncryptionKey			[45] IMPLICIT SignalingMessageEncryptionKey OPTIONAL,
	--  O 6.5.2.120 e
	tdmaBurstIndicator						[31] IMPLICIT TDMABurstIndicator OPTIONAL,
	-- (Serving) O 6.5.2.151 f
	tdmaCallMode							[29] IMPLICIT TDMACallMode OPTIONAL,
	--  O 6.5.2.152 g
	tdmaChannelData							[28] IMPLICIT TDMAChannelData OPTIONAL,
	-- (Serving) O 6.5.2.153 f
	voicePrivacyMask						[48] IMPLICIT VoicePrivacyMask OPTIONAL,
	-- O 6.5.2.166 h
	...
	}

-- FacilitiesDirective RETURN RESULT Parameters
FacilitiesDirectiveRes ::= [PRIVATE 18] SET {
	channelData								[5] IMPLICIT ChannelData,
	-- (Target) M 6.5.2.47 a
	confidentialityModes					[39] IMPLICIT ConfidentialityModes OPTIONAL,
	-- (Actual) O 6.5.2.50 b
	tdmaBurstIndicator						[31] IMPLICIT TDMABurstIndicator OPTIONAL,
	-- (Target) O 6.5.2.151 c
	tdmaChannelData							[28] IMPLICIT TDMAChannelData OPTIONAL
	-- (Target) O 6.5.2.153 d	...
	}

-- 6.4.2.11 FacilitiesDirective2
-- N.S0007-0 v 1.0
FacilitiesDirective2 ::= [PRIVATE 18] SET {
	billingID								[1] IMPLICIT BillingID,
	-- M 6.5.2.16
	electronicSerialNumber					[9] IMPLICIT ElectronicSerialNumber,
	-- M 6.5.2.63
	interMSCCircuitID						[6] IMPLICIT InterMSCCircuitID,
	-- M 6.5.2.72
	interSwitchCount						[7] IMPLICIT InterSwitchCount,
	-- M 6.5.2.73
	mobileIdentificationNumber				[8] IMPLICIT MobileIdentificationNumber,
	-- M 6.5.2.81
	servingCellID							[2] IMPLICIT ServingCellID,
	-- M 6.5.2.117
	baseStationManufacturerCode				[197] IMPLICIT BaseStationManufacturerCode OPTIONAL,
	-- O 6 .5.2.aa a a
	alertCode								[75] IMPLICIT AlertCode OPTIONAL,
	-- O 6.5.2.3 s
	cdma2000HandoffInvokeIOSData			[356] IMPLICIT CDMA2000HandoffInvokeIOSData OPTIONAL,
	--O 6.5.2.gm xx
	cdmaBandClassList						[172] IMPLICIT CDMABandClassList OPTIONAL,
	-- O 6.5.2.c r
	cdmaCallMode							[62] IMPLICIT CDMACallMode OPTIONAL,
	-- O 6.5.2.29 c, d, e
	cdmaChannelData							[63] IMPLICIT CDMAChannelData OPTIONAL,
	-- (Serving) O 6.5.2.30 c
	cdmaConnectionReferenceList				[212] IMPLICIT CDMAConnectionReferenceList OPTIONAL,
	-- O 6.5.2.aq c, t, aa
	cdmaMobileProtocolRevision				[66] IMPLICIT CDMAMobileProtocolRevision OPTIONAL,
	-- O 6.5.2.34 c
	cdmaMSMeasuredChannelIdentity			[351] IMPLICIT CDMAMSMeasuredChannelIdentity OPTIONAL,
	-- O 6.5.2.gh nn
	cdmaPrivateLongCodeMask					[67] IMPLICIT CDMAPrivateLongCodeMask OPTIONAL,
	-- O 6.5.2.36 f
	cdmaServiceConfigurationRecord			[174] IMPLICIT CDMAServiceConfigurationRecord OPTIONAL,
	-- O 6.5.2.e c, s
	cdmaServiceOptionList					[176] IMPLICIT CDMAServiceOptionList OPTIONAL,
	-- O 6.5.2.g
	cdmaServingOneWayDelay					[60] IMPLICIT CDMAServingOneWayDelay OPTIONAL,
	-- O 6.5.2.38 a, c
	cdmaStationClassMark					[59] IMPLICIT CDMAStationClassMark OPTIONAL,
	-- O 6.5.2.41 c
	cdmaStationClassMark2					[177] IMPLICIT CDMAStationClassMark2 OPTIONAL,
	-- O 6.5.2.h TSB76 c, mm
	cdmaTargetMAHOList						[136] IMPLICIT CDMATargetMAHOList OPTIONAL,
	-- O 6.5.2.43 g
	cdmaTargetMeasurementList				[134] IMPLICIT CDMATargetMeasurementList OPTIONAL,
	-- O 6.5.2.45 h
	channelData								[5] IMPLICIT ChannelData OPTIONAL,
	-- (Serving) O 6.5.2.47 i
	confidentialityModes					[39] IMPLICIT ConfidentialityModes OPTIONAL,
	-- (Desired) O 6.5.2.50 b
	dataKey									[215] IMPLICIT DataKey OPTIONAL,
	-- O 6.5.2.at aa
	dataPrivacyParameters					[216] IMPLICIT DataPrivacyParameters OPTIONAL,
	-- O 6.5.2.au x
	handoffReason							[30] IMPLICIT HandoffReason OPTIONAL,
	-- O 6.5.2.70 c
	handoffState							[164] IMPLICIT HandoffState OPTIONAL,
	-- O 6.5.2.71 d
	ilspInformation							[217] IMPLICIT ISLPInformation OPTIONAL,
	--(Desired) O 6.5.2.av u
	msLocation								[70] IMPLICIT MSLocation OPTIONAL,
	-- O 6.5.2.84 c
	nampsCallMode							[165] IMPLICIT NAMPSCallMode OPTIONAL,
	-- O 6.5.2.85 e, m
	nampsChannelData						[74] IMPLICIT NAMPSChannelData OPTIONAL,
	-- (Serving) O 6.5.2.86 n
	randomVariable							[40] IMPLICIT RandomVariable OPTIONAL,
	-- O 6.5.2.101 aa
	nonPublicData							[200] IMPLICIT NonPublicData OPTIONAL,
	-- O 6.5.2.ad t
	pdsnAddress								[349]	IMPLICIT PDSNAddress OPTIONAL,
	--O 6.5.2.gf gg
	pdsnProtocolType						[350] IMPLICIT PDSNProtocolType OPTIONAL,
	-- O 6.5.2.gg hh
	qosPriority								[348] IMPLICIT QoSPriority OPTIONAL,
	-- O 6.5.2.ge ff
	signalingMessageEncryptionKey			[45] IMPLICIT SignalingMessageEncryptionKey OPTIONAL,
	-- O 6.5.2.120 j
	stationClassMark						[18] IMPLICIT StationClassMark,
	-- M 6.5.2.143
	systemOperatorCode						[206] IMPLICIT SystemOperatorCode OPTIONAL,
	-- O 6 .5.2.a j b b
	targetCellID							[3] IMPLICIT TargetCellID OPTIONAL,
	-- O 6.5.2.148 b
	tdmaBandwidth							[220] IMPLICIT TDMABandwidth OPTIONAL,
	-- (Desired) O 6.5.2.ay z
	tdmaBurstIndicator						[31] IMPLICIT TDMABurstIndicator OPTIONAL,
	-- (Serving) O 6.5.2.151 o
	tdmaCallMode							[29] IMPLICIT TDMACallMode OPTIONAL,
	-- O 6.5.2.152 e, p
	tdmaChannelData							[28] IMPLICIT TDMAChannelData OPTIONAL,
	-- (Serving) O 6.5.2.153 o
	tdmaServiceCode							[178] IMPLICIT TDMAServiceCode OPTIONAL,
	-- O 6 .5.2.i x
	tdmaTerminalCapability					[179] TDMATerminalCapability OPTIONAL,
	-- y O 6 .5.2.j x
	tdmaVoiceCoder							[180] IMPLICIT TDMAVoiceCoder OPTIONAL,
	-- O 6.5.2.k u
	terminalType							[47] IMPLICIT TerminalType OPTIONAL,
	-- O 6 .5.2.154
	userZoneData							[209] IMPLICIT UserZoneData OPTIONAL,
	-- O 6.5.2.am (IS-730) v
	voicePrivacyMask						[48] IMPLICIT VoicePrivacyMask OPTIONAL,
	-- O 6.5.2.166 q
	meid									[390] IMPLICIT MEID OPTIONAL
	-- O
}

-- FacilitiesDirective2 RETURN RESULT Parameters
FacilitiesDirective2Res ::= [PRIVATE 18] SET {
	bsmcstatus								[198] IMPLICIT BSMCStatus OPTIONAL,
	--
	cdma2000HandoffResponseIOSData			[357] IMPLICIT CDMA2000HandoffResponseIOSData OPTIONAL,
	-- O 6.5.2.gn yy
	-- O 6 .5.2.a b f
	cdmaChannelData							[63] IMPLICIT CDMAChannelData OPTIONAL,
	-- (Target) O 6.5.2.30 a
	cdmaCodeChannelList						[132] IMPLICIT CDMACodeChannelList OPTIONAL,
	-- O 6.5.2.33 a
	cdmaConnectionReferenceList				[212] IMPLICIT CDMAConnectionReferenceList OPTIONAL,
	-- O 6.5.2.aq a, i,
	cdmaSearchParameters					[230] IMPLICIT CDMASearchParameters OPTIONAL,
	--O 6.5.2.bi a, k
	cdmaSearchWindow						[69] IMPLICIT CDMASearchWindow OPTIONAL,
	-- O 6.5.2.37 a
	cdmaServiceConfigurationRecord			[174] IMPLICIT CDMAServiceConfigurationRecord OPTIONAL,
	-- O 6.5.2.e a, h
	channelData								[5] IMPLICIT ChannelData OPTIONAL,
	-- (Target) O 6.5.2.47 b
	confidentialityModes					[39] IMPLICIT ConfidentialityModes OPTIONAL,
	-- (Actual) O 6.5.2.50 c
	ilspInformation							[217] IMPLICIT ISLPInformation OPTIONAL,
	-- (Actual) O 6.5.2.av j
	nampsChannelData						[74] IMPLICIT NAMPSChannelData OPTIONAL,
	-- (Target) O 6.5.2.86 d
	sOCStatus								[205] IMPLICIT SOCStatus OPTIONAL,
	-- O 6 .5.2.a i f
	targetCellID							[3] IMPLICIT TargetCellID OPTIONAL,
	-- O 6.5.2.148 e
	tdmaBurstIndicator						[31] IMPLICIT TDMABurstIndicator OPTIONAL,
	-- (Target) O 6.5.2.151 f
	tdmaChannelData							[28] IMPLICIT TDMAChannelData OPTIONAL,
	-- (Target) O 6.5.2.153 g
	tdmaVoiceCoder							[180] IMPLICIT TDMAVoiceCoder OPTIONAL
	-- (Target ) O 6 .5.2.k h
}

-- 6.4.2.12 FacilitiesRelease
FacilitiesRelease ::= [PRIVATE 18] SET {
	interMSCCircuitID						[6] IMPLICIT	InterMSCCircuitID,
	-- M 6.5.2.72
	releaseReason							[10] IMPLICIT ReleaseReason,
	-- M 6.5.2.111
	billingID								[1] IMPLICIT BillingID OPTIONAL,
	-- O 6.5.2.16 a
	mobileIdentificationNumber				[8] IMPLICIT MobileIdentificationNumber OPTIONAL
	-- O 6.5.2.81
	}

-- FacilitiesRelease RETURN RESULT Parameters
FacilitiesReleaseRes ::= [PRIVATE 18] SET {
	billingID								[1] IMPLICIT BillingID OPTIONAL
	-- O 6.5.2.16
	}

-- Updated with N.S0004, N.S0012-0 v 1.0 N.S0023-0 v 1.0
-- http://www.3gpp2.org/Public_html/specs/X.S0004-540-E_v2.0_070723.pdf
-- 6.4.2.13 FeatureRequest
FeatureRequest ::= [PRIVATE 18] SET {
	digits		 							[4] IMPLICIT Digits,
	-- (Dialed) M 6.5.2.58
	electronicSerialNumber					[9] IMPLICIT ElectronicSerialNumber,
	-- M 6.5.2.63
	msid									MSID OPTIONAL,
	--
	billingID								[1] IMPLICIT BillingID OPTIONAL,
	-- O 6.5.2.16
	acgencountered							[340] IMPLICIT ACGEncountered OPTIONAL,
	-- O 6.5.2.fv
	callingPartyName						[243] IMPLICIT CallingPartyName OPTIONAL,
	-- O 6.5.2.bw c
	callingPartyNumberDigits1				[80] IMPLICIT CallingPartyNumberDigits1 OPTIONAL,
	-- O 6.5.2.21 c
	callingPartyNumberDigits2				[81] IMPLICIT CallingPartyNumberDigits2 OPTIONAL,
	-- O 6.5.2.22 c
	callingPartySubaddress					[84] IMPLICIT CallingPartySubaddress OPTIONAL,
	-- O 6.5.2.25 c
	conferenceCallingIndicator				[137] IMPLICIT ConferenceCallingIndicator OPTIONAL,
	-- O 6.5.2.49
	mobileDirectoryNumber					[93] IMPLICIT MobileDirectoryNumber OPTIONAL,
	-- O 6.5.2.80 d
	mobileIdentificationNumber				[8] IMPLICIT MobileIdentificationNumber OPTIONAL,
	-- O 6.5.2.81
	mscid									[21] IMPLICIT MSCID OPTIONAL,
	-- (Serving) O 6.5.2.82 e
	mSCIdentificationNumber					[94] IMPLICIT MSCIdentificationNumber OPTIONAL,
	-- O 6.5.2.83
	oneTimeFeatureIndicator					[97] IMPLICIT OneTimeFeatureIndicator OPTIONAL,
	-- O 6.5.2.88 f
	pc-ssn									[32] IMPLICIT PC-SSN OPTIONAL,
	-- O 6.5.2.93
	senderIdentificationNumber				[103] IMPLICIT SenderIdentificationNumber OPTIONAL,
	-- O 6.5.2.116
	systemMyTypeCode						[22] IMPLICIT SystemMyTypeCode OPTIONAL,
	-- (Originating MSC)
	transactionCapability					[123] IMPLICIT TransactionCapability OPTIONAL,
	-- 6.5.2.160
	meid									[390] IMPLICIT MEID OPTIONAL
	-- O
	}
-- FeatureRequest RETURN RESULT Parameters
FeatureRequestRes ::= [PRIVATE 18] SET {
	featureResult							[18] IMPLICIT FeatureResult,
	-- M 6.5.2.67
	accessDeniedReason						[20] IMPLICIT AccessDeniedReason OPTIONAL,
	-- O 6.5.2.1 a
	actionCode								[128] IMPLICIT ActionCode OPTIONAL,
	-- O 6.5.2.2 b
	announcementList						[130] IMPLICIT AnnouncementList OPTIONAL,
	-- O 6.5.2.6 c
	callingPartyNumberString1				[82] IMPLICIT CallingPartyNumberString1 OPTIONAL,
	-- O 6.5.2.23 d
	callingPartyNumberString2				[83] IMPLICIT CallingPartyNumberString2 OPTIONAL,
	-- O 6.5.2.24 d
	callingPartySubaddress					[84] IMPLICIT CallingPartySubaddress OPTIONAL,
	-- O 6.5.2.25 d
	carrierDigits							[86] IMPLICIT CarrierDigits OPTIONAL,
	-- O 6.5.2.28 d
	conferenceCallingIndicator				[137] IMPLICIT ConferenceCallingIndicator OPTIONAL,
	-- O 6.5.2.49 e
	digits		 							[4] IMPLICIT Digits OPTIONAL,
	-- (Dialed) O 6.5.2.58 f
	digits-Destination						[4] IMPLICIT Digits OPTIONAL,
	-- (Destination) O 6.5.2.58 l
	displayText								[244] IMPLICIT DisplayText OPTIONAL,
	-- O 6.5.2.bx l, m
	displayText2							[299] IMPLICIT DisplayText2 OPTIONAL,
	-- O 6.5.2.ec l, m
	dmh-AccountCodeDigits					[140] IMPLICIT DMH-AccountCodeDigits OPTIONAL,
	-- O 6.5.2.59 g
	dmh-AlternateBillingDigits				[141] IMPLICIT DMH-AlternateBillingDigits OPTIONAL,
	-- O 6.5.2.60 g
	dmh-BillingDigits						[142] IMPLICIT DMH-BillingDigits OPTIONAL,
	-- O 6.5.2.61 g
	dmh-RedirectionIndicator				[88] IMPLICIT DMH-RedirectionIndicator OPTIONAL,
	-- O 6.5.2.62 d
	groupInformation						[163] IMPLICIT GroupInformation OPTIONAL,
	-- O 6.5.2.69 h
	mobileDirectoryNumber					[93] IMPLICIT MobileDirectoryNumber OPTIONAL,
	-- O 6.5.2.80 g
	noAnswerTime							[96] IMPLICIT NoAnswerTime OPTIONAL,
	-- O 6.5.2.87 d
	oneTimeFeatureIndicator					[97] IMPLICIT OneTimeFeatureIndicator OPTIONAL,
	-- O 6.5.2.88 i
	pACAIndicator							[146] IMPLICIT PACAIndicator OPTIONAL,
	-- O 6.5.2.91 j
	pilotNumber								[168] IMPLICIT PilotNumber OPTIONAL,
	-- O 6.5.2.95 h
	preferredLanguageIndicator				[147] IMPLICIT PreferredLanguageIndicator OPTIONAL,
	-- O 6.5.2.96 n, o
	redirectingNumberDigits					[100] IMPLICIT RedirectingNumberDigits OPTIONAL,
	-- O 6.5.2.107 d
	redirectingNumberString					[101] IMPLICIT RedirectingNumberString OPTIONAL,
	-- O 6.5.2.108 d
	redirectingSubaddress					[102] IMPLICIT RedirectingSubaddress OPTIONAL,
	-- O 6.5.2.109 d
	resumePIC								[266] IMPLICIT ResumePIC OPTIONAL,
	-- O 6.5.2.cu m
	routingDigits							[150] IMPLICIT RoutingDigits OPTIONAL,
	-- O 6.5.2.114 d
	terminationList							[120] IMPLICIT TerminationList OPTIONAL,
	-- O 6.5.2.156 k
	terminationTriggers						[122] IMPLICIT TerminationTriggers OPTIONAL,
	-- O 6.5.2.159 d
	triggerAddressList						[276] IMPLICIT TriggerAddressList OPTIONAL
	-- O 6.5.2.de n
	}

-- 6.4.2.14 FlashRequest
FlashRequest ::= [PRIVATE 18] SET {
	digits		 							[4] IMPLICIT Digits,
	-- (Dialed) M 6.5.2.58 a
	interMSCCircuitID						[6] IMPLICIT InterMSCCircuitID,
	-- M 6.5.2.72
	mobileIdentificationNumber				[8] IMPLICIT MobileIdentificationNumber,
	-- M 6.5.2.81
	confidentialityModes					[39] IMPLICIT ConfidentialityModes OPTIONAL,
	-- (Actual) O 6.5.2.50 b
	electronicSerialNumber					[9] IMPLICIT ElectronicSerialNumber OPTIONAL,
	-- O 6.5.2.63
	emergencyServicesRoutingDigits			[239] IMPLICIT EmergencyServicesRoutingDigits OPTIONAL
	-- O 6.5.bs
	}
-- FlashRequest RETURN RESULT Parameters
-- zero octets


-- 6.4.2.15 HandoffBack
HandoffBack ::= [PRIVATE 18] SET {
	channelData								[5] IMPLICIT ChannelData,
	-- (Serving) M 6.5.2.47 a
	interMSCCircuitID						[6] IMPLICIT InterMSCCircuitID,
	-- M 6.5.2.72
	mobileIdentificationNumber				[8] IMPLICIT MobileIdentificationNumber,
	-- M 6.5.2.81
	servingCellID							[2] IMPLICIT ServingCellID,
	-- M 6.5.2.117
	targetCellID							[3] IMPLICIT TargetCellID,
	-- M 6.5.2.148
	billingID								[1] IMPLICIT BillingID OPTIONAL,
	-- O 6.5.2.16 b
	confidentialityModes					[39] IMPLICIT ConfidentialityModes OPTIONAL,
	-- (Desired) O 6.5.2.50 c	
	handoffReason							[30] IMPLICIT HandoffReason OPTIONAL,
	-- O 6.5.2.70 d
	handoffState							[164] IMPLICIT HandoffState OPTIONAL,
	-- O 6.5.2.71 e
	signalingMessageEncryptionKey			[45] IMPLICIT SignalingMessageEncryptionKey OPTIONAL,
	-- O 6.5.2.120 c, f
	tdmaBurstIndicator						[31] IMPLICIT TDMABurstIndicator OPTIONAL,
	-- (Serving) O 6.5.2.151 g
	tdmaCallMode							[29] IMPLICIT TDMACallMode OPTIONAL,
	-- O 6.5.2.152 h
	tdmaChannelData							[28] IMPLICIT TDMAChannelData OPTIONAL,
	-- (Serving) O 6.5.2.153 g
	voicePrivacyMask						[48] IMPLICIT VoicePrivacyMask OPTIONAL,
	-- O 6.5.2.166 i
	...
	}

-- HandoffBack RETURN RESULT Parameters

HandoffBackRes ::= [PRIVATE 18] SET {
	channelData								[5] IMPLICIT ChannelData,
	-- (Target) M 6.5.2.47 a
	confidentialityModes					[39] IMPLICIT ConfidentialityModes OPTIONAL,
	-- (Actual) O 6.5.2.50 b
	tdmaBurstIndicator						[31] IMPLICIT TDMABurstIndicator OPTIONAL,
	-- (Target) O 6.5.2.151 c
	tdmaChannelData							[28] IMPLICIT TDMAChannelData OPTIONAL,
	-- (Target) O 6.5.2.153 d
	...
	}
--6.4.2.16 HandoffBack2
HandoffBack2 ::= [PRIVATE 18] SET {
	billingID								[1] IMPLICIT BillingID,
	-- M 6.5.2.16
	interMSCCircuitID						[6] IMPLICIT InterMSCCircuitID,
	-- M 6.5.2.72
	mobileIdentificationNumber				[8] IMPLICIT MobileIdentificationNumber,
	-- M 6.5.2.81
	servingCellID							[2] IMPLICIT ServingCellID OPTIONAL,
	-- M 6.5.2.117 a
	baseStationManufacturerCode				[197] IMPLICIT BaseStationManufacturerCode OPTIONAL,
	-- O 6 .5.2.a a u
	cdma2000HandoffInvokeIOSData			[356] IMPLICIT CDMA2000HandoffInvokeIOSData OPTIONAL,
	-- O 6.5.2.gm xx
	cdmaBandClassList						[172] IMPLICIT CDMABandClassList OPTIONAL,
	-- O 6.5.2.c r
	cdmaCallMode							[62] IMPLICIT CDMACallMode OPTIONAL,
	-- O 6.5.2.29 c, d, e
	cdmaChannelData							[63] IMPLICIT CDMAChannelData OPTIONAL,
	-- (Serving) O 6.5.2.30 c
	cdmaConnectionReferenceList				[212] IMPLICIT CDMAConnectionReferenceList OPTIONAL,
	-- O 6.5.2.aq IS-737 c, t, aa
	cdmaMSMeasuredChannelIdentity			[351] IMPLICIT CDMAMSMeasuredChannelIdentity OPTIONAL,
	-- O 6.5.2.gh oo
	cdmaMobileProtocolRevision				[66] IMPLICIT CDMAMobileProtocolRevision OPTIONAL,
	-- O 6.5.2.34 c
	cdmaServiceConfigurationRecord			[174] IMPLICIT CDMAServiceConfigurationRecord OPTIONAL,
	-- O 6.5.2.e c, s, mm
	cdmaServiceOptionList					[176] IMPLICIT CDMAServiceOptionList OPTIONAL,
	-- O 6.5.2.g TSB76 c, x
	cdmaPrivateLongCodeMask					[67] IMPLICIT CDMAPrivateLongCodeMask OPTIONAL,
	-- O 6.5.2.36 f
	cdmaServingOneWayDelay					[60] IMPLICIT CDMAServingOneWayDelay OPTIONAL,
	-- O 6.5.2.38 a, c
	cdmaStationClassMark					[59] IMPLICIT CDMAStationClassMark OPTIONAL,
	-- O 6.5.2.41 c
	cdmaStationClassMark2					[177] IMPLICIT CDMAStationClassMark2 OPTIONAL,
	-- O 6.5.2.h TSB76 c, nn
	cdmaTargetMAHOList						[136] IMPLICIT CDMATargetMAHOList OPTIONAL,
	-- O 6.5.2.43 g
	cdmaTargetMeasurementList				[134] IMPLICIT CDMATargetMeasurementList OPTIONAL,
	-- O 6.5.2.45 h
	channelData								[5] IMPLICIT ChannelData OPTIONAL,
	-- (Serving) O 6.5.2.47 i
	confidentialityModes					[39] IMPLICIT ConfidentialityModes OPTIONAL,
	-- (Desired) O 6.5.2.50 j
	dataKey									[215] IMPLICIT DataKey OPTIONAL,
	-- O 6.5.2.at aa
	dataPrivacyParameters					[216] IMPLICIT DataPrivacyParameters OPTIONAL,
	-- O 6.5.2.au w
	handoffReason							[30] IMPLICIT HandoffReason OPTIONAL,
	-- O 6.5.2.70 k
	handoffState							[164] IMPLICIT HandoffState OPTIONAL,
	-- O 6.5.2.71 l
	interSwitchCount						[7] IMPLICIT InterSwitchCount OPTIONAL,
	-- O 6.5.2.73 k
	ilspInformation							[217] IMPLICIT ISLPInformation OPTIONAL,
	-- O 6.5.2.av y
	msLocation								[70] IMPLICIT MSLocation OPTIONAL,
	-- O 6.5.2.84 c
	nampsCallMode							[165] IMPLICIT NAMPSCallMode OPTIONAL,
	-- O 6.5.2.85 e, m
	nampsChannelData						[74] IMPLICIT NAMPSChannelData OPTIONAL,
	-- (Serving) O 6.5.2.86 n
	pdsnAddress								[349] IMPLICIT PDSNAddress OPTIONAL,
	-- O 6.5.2.gf hh
	pdsnProtocolType						[350] IMPLICIT PDSNProtocolType OPTIONAL,
	-- O 6.5.2.gg ii
	qosPriority								[348] IMPLICIT QoSPriority OPTIONAL,
	-- O 6.5.2.ge jj
	randomVariable							[40] IMPLICIT RandomVariable OPTIONAL,
	-- O 6.5.2.101
	signalingMessageEncryptionKey			[45] IMPLICIT SignalingMessageEncryptionKey OPTIONAL,
	-- O 6.5.2.120 j
	stationClassMark						[18] IMPLICIT StationClassMark OPTIONAL,
	-- O 6 .5.2.14 3 i , n, o
	systemOperatorCode						[206] IMPLICIT SystemOperatorCode OPTIONAL,
	-- O 6 .5.2.a j v
	targetCellID							[3] IMPLICIT TargetCellID OPTIONAL,
	-- O 6.5.2.148
	tdmaBandwidth							[220] IMPLICIT TDMABandwidth OPTIONAL,
	-- (Desired) O 6.5.2.ay
	tdmaBurstIndicator						[31] IMPLICIT TDMABurstIndicator OPTIONAL,
	-- (Serving) O 6.5.2.151 o
	tdmaCallMode							[29] IMPLICIT TDMACallMode OPTIONAL,
	-- O 6.5.2.152 e, p
	tdmaChannelData							[28] IMPLICIT TDMAChannelData OPTIONAL,
	-- (Serving) O 6.5.2.153 o
	tdmaServiceCode							[178] IMPLICIT TDMAServiceCode OPTIONAL,
	-- O 6 .5.2.i x
	tdmaTerminalCapability					[179] TDMATerminalCapability OPTIONAL,
	-- y O 6 .5.2.j x
	tdmaVoiceCoder							[180] IMPLICIT TDMAVoiceCoder OPTIONAL,
	-- O 6.5.2.k u
	terminalType							[47] IMPLICIT TerminalType OPTIONAL,
	-- O 6 .5.2.154
	voicePrivacyMask						[48] IMPLICIT VoicePrivacyMask OPTIONAL,
	-- O 6.5.2.166 q
	...
	}

-- HandoffBack2 RETURN RESULT Parameters
HandoffBack2Res ::= [PRIVATE 18] SET {
	bsmcstatus								[198] IMPLICIT BSMCStatus OPTIONAL,
	-- O 6 .5.2.a b f
	cdma2000HandoffResponseIOSData			[357] IMPLICIT CDMA2000HandoffResponseIOSData OPTIONAL,
	-- O 6.5.2.gn yy
	cdmaChannelData							[63] IMPLICIT CDMAChannelData OPTIONAL,
	-- (Target) O 6.5.2.30 a
	cdmaCodeChannelList						[132] IMPLICIT CDMACodeChannelList OPTIONAL,
	-- O 6.5.2.33 a
	cdmaSearchParameters					[230] IMPLICIT CDMASearchParameters OPTIONAL,
	-- O 6.5.2.bi a, k
	cdmaConnectionReferenceList				[212] IMPLICIT CDMAConnectionReferenceList OPTIONAL,
	-- O 6.5.2.aq a, i, l, zz
	cdmaSearchWindow						[69] IMPLICIT CDMASearchWindow OPTIONAL,
	-- O 6.5.2.37 a
	cdmaServiceConfigurationRecord			[174] IMPLICIT CDMAServiceConfigurationRecord OPTIONAL,
	-- O 6.5.2.e a, h, t
	channelData								[5] IMPLICIT ChannelData OPTIONAL,
	-- (Target) O 6.5.2.47 b
	confidentialityModes					[39] IMPLICIT ConfidentialityModes OPTIONAL,
	-- (Actual) O 6.5.2.50 c
	nampsChannelData						[74] IMPLICIT NAMPSChannelData OPTIONAL,
	-- (Target) O 6.5.2.86 d
	sOCStatus								[205] IMPLICIT SOCStatus OPTIONAL,
	-- O 6 .5.2.a i f
	targetCellID							[3] IMPLICIT TargetCellID OPTIONAL,
	-- O 6.5.2.148 e
	tdmaBurstIndicator						[31] IMPLICIT TDMABurstIndicator OPTIONAL,
	-- (Target) O 6.5.2.151 f
	tdmaChannelData							[28] IMPLICIT TDMAChannelData OPTIONAL,
	-- (Target) O 6.5.2.153 g
	tdmaVoiceCoder							[180] IMPLICIT TDMAVoiceCoder OPTIONAL
	-- (Target ) O 6 .5.2.k h
	}

-- 6.4.2.17 HandoffMeasurementRequest

HandoffMeasurementRequest ::= [PRIVATE 18] SET {
	channelData								[5] IMPLICIT ChannelData,
	-- (Serving) M 6.5.2.47 a
	servingCellID							[2] IMPLICIT ServingCellID,
	-- M 6.5.2.117
	stationClassMark						[18] IMPLICIT StationClassMark,
	-- M 6.5.2.143
	targetCellIDList						[207] IMPLICIT TargetCellIDList OPTIONAL,
	-- O 6 .5.2.ak i
	tdmaCallMode							[29] IMPLICIT TDMACallMode OPTIONAL,
	-- O 6.5.2.152 b
	tdmaChannelData							[28] IMPLICIT TDMAChannelData OPTIONAL,
	-- (Serving) O 6.5.2.153 c
	tdmaTerminalCapability					[179] IMPLICIT TDMATerminalCapability OPTIONAL
	-- O 6 .5.2.j h
	}

--HandoffMeasurementRequest RETURN RESULT Parameters
HandoffMeasurementRequestRes ::= [PRIVATE 18] SET {
	signalQuality							[11] IMPLICIT SignalQuality,
	-- M 6.5.2.121 a
	targetCellID							[3] IMPLICIT TargetCellID,
	-- M 6.5.2.148 a
	...
	}

-- 6.4.2.18 HandoffMeasurementRequest2
HandoffMeasurementRequest2 ::= [PRIVATE 18] SET {
	servingCellID							[2] IMPLICIT ServingCellID,
	-- M 6.5.2.117
	cdmaCallMode							[62] IMPLICIT CDMACallMode OPTIONAL,
	-- O 6.5.2.29 a, b
	cdmaChannelData							[63] IMPLICIT CDMAChannelData OPTIONAL,
	-- (Serving) O 6.5.2.30 b
	cdmaServiceConfigurationRecord			[174] IMPLICIT CDMAServiceConfigurationRecord OPTIONAL,
	-- O 6.5.2.e
	cdmaServingOneWayDelay					[60] IMPLICIT CDMAServingOneWayDelay OPTIONAL,
	-- O 6.5.2.38 b
	cdmaStationClassMark					[59] IMPLICIT CDMAStationClassMark OPTIONAL,
	-- O 6.5.2.41 b
	cdmaStationClassMark2					[177] IMPLICIT CDMAStationClassMark2 OPTIONAL,
	-- O 6.5.2.h i
	channelData								[5] IMPLICIT ChannelData OPTIONAL,
	-- (Serving) O 6.5.2.47 c
	msLocation								[70] IMPLICIT MSLocation OPTIONAL,
	-- O 6.5.2.84 b
	nampsCallMode							[165] IMPLICIT NAMPSCallMode OPTIONAL,
	-- O 6.5.2.85 d
	nampsChannelData						[74] IMPLICIT NAMPSChannelData OPTIONAL,
	-- (Serving) O 6.5.2.86 e
	stationClassMark						[18] IMPLICIT StationClassMark OPTIONAL,
	-- O 6.5.2.143 c, f
	targetCellIDList						[207] IMPLICIT TargetCellIDList OPTIONAL,
	-- O 6.5.2.ak
	tdmaBandwidth							[220] IMPLICIT TDMABandwidth OPTIONAL,
	-- (Desired) O 6.5.2.ay
	tdmaCallMode							[29] IMPLICIT TDMACallMode OPTIONAL,
	-- O 6.5.2.152 g
	tdmaChannelData							[28] IMPLICIT TDMAChannelData OPTIONAL,
	-- (Serving) O 6.5.2.153 f
	tdmaServiceCode							[178] IMPLICIT TDMAServiceCode OPTIONAL,
	-- O 6.5.2.i
	tdmaTerminalCapability					[179] IMPLICIT TDMATerminalCapability OPTIONAL
	-- O 6.5.2.j
	}

-- HandoffMeasurementRequest2 RETURN RESULT Parameters
HandoffMeasurementRequest2Res ::= [PRIVATE 18] SET {
	cdmaTargetMeasurementList				[134] IMPLICIT CDMATargetMeasurementList OPTIONAL,
	-- O 6.5.2.45 a
	targetMeasurementList					[157] IMPLICIT TargetMeasurementList OPTIONAL
	-- O 6.5.2.150 b	...
	}

-- 6.4.2.19 HandoffToThird
HandoffToThird ::= [PRIVATE 18] SET {
	billingID								[1] IMPLICIT BillingID,
	-- M 6.5.2.16 N.S0006
	electronicSerialNumber					[9] IMPLICIT ElectronicSerialNumber,
	-- M 6.5.2.63
	interMSCCircuitID						[6] IMPLICIT InterMSCCircuitID,
	-- M 6.5.2.72
	interSwitchCount						[7] IMPLICIT InterSwitchCount,
	-- (Serving) M 6.5.2.73
	mobileIdentificationNumber				[8] IMPLICIT MobileIdentificationNumber,
	-- M 6.5.2.81
	mscid									[21] IMPLICIT MSCID,
	-- (Target) M 6.5.2.82
	servingCellID							[2] IMPLICIT ServingCellID,
	-- M 6.5.2.117
	baseStationManufacturerCode				[197] IMPLICIT BaseStationManufacturerCode OPTIONAL,
	-- O 6 .5.2.aa u
	stationClassMark						[18] IMPLICIT StationClassMark,
	-- M 6.5.2.143
	targetCellID							[3] IMPLICIT TargetCellID,
	-- M 6.5.2.148
	cdmaBandClassList						[172] IMPLICIT CDMABandClassList OPTIONAL,
	-- O 6.5.2.c q
	cdmaCallMode							[62] IMPLICIT CDMACallMode OPTIONAL,
	-- O 6.5.2.29 c, d, e
	cdmaChannelData							[63] IMPLICIT CDMAChannelData OPTIONAL,
	-- (Serving) O 6.5.2.30 c
	cdmaMobileProtocolRevision				[66] IMPLICIT CDMAMobileProtocolRevision OPTIONAL,
	-- O 6.5.2.34 c, r
	cdmaPrivateLongCodeMask					[67] IMPLICIT CDMAPrivateLongCodeMask OPTIONAL,
	-- O 6.5.2.36 f
	cdmaServiceConfigurationRecord			[174] IMPLICIT CDMAServiceConfigurationRecord OPTIONAL,
	-- O 6.5.2.e c, s
	cdmaServiceOptionList					[176] IMPLICIT CDMAServiceOptionList OPTIONAL,
	-- O 6.5.2.g c, t
	cdmaServingOneWayDelay					[60] IMPLICIT CDMAServingOneWayDelay OPTIONAL,
	-- O 6.5.2.38 a, c
	cdmaStationClassMark					[59] IMPLICIT CDMAStationClassMark OPTIONAL,
	-- O 6.5.2.41 c, r, u
	cdmaStationClassMark2					[177] IMPLICIT CDMAStationClassMark2 OPTIONAL,
	-- O 6.5.2.h r
	cdmaTargetMAHOList						[136] IMPLICIT CDMATargetMAHOList OPTIONAL,
	-- O 6.5.2.43 g
	cdmaTargetMeasurementList				[134] IMPLICIT CDMATargetMeasurementList OPTIONAL,
	-- O 6.5.2.45 h
	channelData								[5] IMPLICIT ChannelData OPTIONAL,
	-- (Serving) O 6.5.2.47 b
	confidentialityModes					[39] IMPLICIT ConfidentialityModes OPTIONAL,
	-- (Desired) O 6.5.2.50 c
	handoffReason							[30] IMPLICIT HandoffReason OPTIONAL,
	-- O 6.5.2.70 d
	handoffState							[164] IMPLICIT HandoffState OPTIONAL,
	-- O 6 .5.2.71 t
	msLocation								[70] IMPLICIT MSLocation OPTIONAL,
	-- O 6.5.2.84 c
	nampsCallMode							[165] IMPLICIT NAMPSCallMode OPTIONAL,
	-- O 6.5.2.85 e, l
	nampsChannelData						[74] IMPLICIT NAMPSChannelData OPTIONAL,
	-- (Serving) O 6.5.2.86 m
	signalingMessageEncryptionKey			[45] IMPLICIT SignalingMessageEncryptionKey OPTIONAL,
	-- O 6.5.2.120 c
	tdmaBurstIndicator						[31] IMPLICIT TDMABurstIndicator OPTIONAL,
	-- (Serving) O 6.5.2.151 e
	tdmaCallMode							[29] IMPLICIT TDMACallMode OPTIONAL,
	-- O 6.5.2.152 f
	tdmaChannelData							[28] IMPLICIT TDMAChannelData OPTIONAL,
	-- (Serving) O 6.5.2.153 e
	tdmaServiceCode							[178] IMPLICIT TDMAServiceCode OPTIONAL,
	-- O 6 .5.2.i x
	tdmaTerminalCapability					[179] IMPLICIT TDMATerminalCapability OPTIONAL,
	-- y O 6 .5.2.j x
	tdmaVoiceCoder							[180] IMPLICIT TDMAVoiceCoder OPTIONAL,
	-- O 6.5.2.k u
	terminalType							[47] IMPLICIT TerminalType OPTIONAL,
	-- O 6 .5.2.154
	voicePrivacyMask						[48] IMPLICIT VoicePrivacyMask OPTIONAL
	-- O 6.5.2.166 g
		}

-- HandoffToThird RETURN RESULT Parameters
HandoffToThirdRes ::= [PRIVATE 18] SET {
	cdmaChannelData							[63] IMPLICIT CDMAChannelData OPTIONAL,
	-- (Target) O 6.5.2.30 a
	cdmaCodeChannelList						[132] IMPLICIT CDMACodeChannelList OPTIONAL,
	-- O 6.5.2.33 a
	cdmaSearchWindow						[69] IMPLICIT CDMASearchWindow OPTIONAL,
	-- O 6.5.2.37 a
	cdmaServiceConfigurationRecord			[174] IMPLICIT CDMAServiceConfigurationRecord OPTIONAL,
	--
	channelData								[5] IMPLICIT ChannelData OPTIONAL,
	-- (Target) O 6.5.2.47 a
	confidentialityModes					[39] IMPLICIT ConfidentialityModes OPTIONAL,
	-- (Actual) O 6.5.2.50 b
	nampsChannelData						[74] IMPLICIT NAMPSChannelData OPTIONAL,
	-- (Target) O 6.5.2.86 d
	targetCellID							[3] IMPLICIT TargetCellID,
	-- O 6.5.2.148 e
	tdmaBurstIndicator						[31] IMPLICIT TDMABurstIndicator OPTIONAL,
	-- (Target) O 6.5.2.151 c
	tdmaChannelData							[28] IMPLICIT TDMAChannelData OPTIONAL,
	-- (Target) O 6.5.2.153 d
	tdmaVoiceCoder							[180] IMPLICIT TDMAVoiceCoder OPTIONAL
	-- (Target) O 6.5.2.k j
	}

-- 6.4.2.20 HandoffToThird2
HandoffToThird2 ::= [PRIVATE 18] SET {
	bsmcstatus								[198] IMPLICIT BSMCStatus OPTIONAL,
	-- O 6 .5.2.a b f
	billingID								[1] IMPLICIT BillingID,
	-- M 6.5.2.16
	electronicSerialNumber					[9] IMPLICIT ElectronicSerialNumber,
	-- M 6.5.2.63
	interMSCCircuitID						[6] IMPLICIT InterMSCCircuitID,
	-- M 6.5.2.72
	interSwitchCount						[7] IMPLICIT InterSwitchCount,
	-- (Serving) M 6.5.2.73
	mobileIdentificationNumber				[8] IMPLICIT MobileIdentificationNumber,
	-- M 6.5.2.81
	mscid									[21] IMPLICIT MSCID,
	-- (Target) M 6.5.2.82
	servingCellID							[2] IMPLICIT ServingCellID,
	-- M 6.5.2.117 a
	targetCellID							[3] IMPLICIT TargetCellID,
	-- O 6.5.2.148 b
	cdma2000HandoffInvokeIOSData			[356] IMPLICIT CDMA2000HandoffInvokeIOSData OPTIONAL,
	-- O 6.5.2.gm xx
	cdmaCallMode							[62] IMPLICIT CDMACallMode OPTIONAL,
	-- O 6.5.2.29 c, d, e
	cdmaChannelData							[63] IMPLICIT CDMAChannelData OPTIONAL,
	-- (Serving) O 6.5.2.30 c
	cdmaConnectionReferenceList				[212] IMPLICIT CDMAConnectionReferenceList OPTIONAL,
	-- O 6.5.2.aq IS-737 c, s, z
	cdmaMSMeasuredChannelIdentity			[351] IMPLICIT CDMAMSMeasuredChannelIdentity OPTIONAL,
	-- O 6.5.2.gh oo
	cdmaMobileProtocolRevision				[66] IMPLICIT CDMAMobileProtocolRevision OPTIONAL,
	-- O 6.5.2.34 c
	cdmaPrivateLongCodeMask					[67] IMPLICIT CDMAPrivateLongCodeMask OPTIONAL,
	-- O 6.5.2.36 f
	cdmaServiceConfigurationRecord			[174] IMPLICIT CDMAServiceConfigurationRecord OPTIONAL,
	-- O 6.5.2.e c, r, mm
	cdmaServiceOptionList					[176] IMPLICIT CDMAServiceOptionList OPTIONAL,
	-- O 6.5.2.g c, x
	cdmaServingOneWayDelay					[60] IMPLICIT CDMAServingOneWayDelay OPTIONAL,
	-- O 6.5.2.38 a, c
	cdmaStationClassMark					[59] IMPLICIT CDMAStationClassMark OPTIONAL,
	-- O 6.5.2.41 c
	cdmaStationClassMark2					[177] IMPLICIT CDMAStationClassMark2 OPTIONAL,
	-- O 6.5.2.h TSB76 c, nn
	cdmaTargetMAHOList						[136] IMPLICIT CDMATargetMAHOList OPTIONAL,
	-- O 6.5.2.43 g
	cdmaTargetMeasurementList				[134] IMPLICIT CDMATargetMeasurementList OPTIONAL,
	-- O 6.5.2.45 h
	channelData								[5] IMPLICIT ChannelData OPTIONAL,
	-- (Serving) O 6.5.2.47 i
	confidentialityModes					[39] IMPLICIT ConfidentialityModes OPTIONAL,
	-- (Desired) O 6.5.2.50 j
	dataKey									[215] IMPLICIT DataKey OPTIONAL,
	-- O 6.5.2.at IS-737 ab z
	dataPrivacyParameters					[216] IMPLICIT DataPrivacyParameters OPTIONAL,
	-- O 6.5.2.au IS-737 v
	handoffReason							[30] IMPLICIT HandoffReason OPTIONAL,
	-- O 6.5.2.70 k
	ilspInformation							[217] IMPLICIT ISLPInformation OPTIONAL,
	-- O 6.5.2.av w
	msLocation								[70] IMPLICIT MSLocation OPTIONAL,
	-- O 6.5.2.84 c
	nampsCallMode							[165] IMPLICIT NAMPSCallMode OPTIONAL,
	-- O 6.5.2.85 e, l
	nampsChannelData						[74] IMPLICIT NAMPSChannelData OPTIONAL,
	-- (Serving) O 6.5.2.86 m
	pdsnAddress								[349] IMPLICIT PDSNAddress OPTIONAL,
	-- O 6.5.2.gf hh
	pdsnProtocolType						[350] IMPLICIT PDSNProtocolType OPTIONAL,
	-- O 6.5.2,gg ii
	qosPriority								[348] IMPLICIT QoSPriority OPTIONAL,
	-- O 6.5.2.ge jj
	randomVariable							[40] IMPLICIT RandomVariable OPTIONAL,
	-- O 6.5.2.101 z
	sOCStatus								[205] IMPLICIT SOCStatus OPTIONAL,
	-- O 6 .5.2.a i f
	signalingMessageEncryptionKey			[45] IMPLICIT SignalingMessageEncryptionKey OPTIONAL,
	-- O 6.5.2.120 j
	stationClassMark						[18] IMPLICIT StationClassMark OPTIONAL,
	-- O 6.5.2.143 i, m, n
	tdmaBandwidth							[220] IMPLICIT TDMABandwidth OPTIONAL,
	--(Desired) O 6.5.2.ay y
	tdmaBurstIndicator						[31] IMPLICIT TDMABurstIndicator OPTIONAL,
	-- (Serving) O 6.5.2.151 n
	tdmaCallMode							[29] IMPLICIT TDMACallMode OPTIONAL,
	-- O 6.5.2.152 n, o
	tdmaChannelData							[28] IMPLICIT TDMAChannelData OPTIONAL,
	-- (Serving) O 6.5.2.153 n
	tdmaServiceCode							[178] IMPLICIT TDMAServiceCode OPTIONAL,
	-- O 6.5.2.i u
	tdmaTerminalCapability					[179] TDMATerminalCapability OPTIONAL,
	-- O 6.5.2.j
	tdmaVoiceCoder							[180] IMPLICIT TDMAVoiceCoder OPTIONAL,
	-- O 6.5.2.k
	userZoneData							[209] IMPLICIT UserZoneData OPTIONAL,
	-- O 6.5.2.am (IS-730)
	voicePrivacyMask						[48] IMPLICIT VoicePrivacyMask OPTIONAL,
	-- O 6.5.2.166 p	
	meid									[390] IMPLICIT MEID OPTIONAL
	-- O
	}

-- HandoffToThird2 RETURN RESULT Parameters
HandoffToThird2Res ::= [PRIVATE 18] SET {
	cdma2000HandoffResponseIOSData			[357] IMPLICIT CDMA2000HandoffResponseIOSData OPTIONAL,
	-- O 6.5.2.gn yy
	cdmaChannelData							[63] IMPLICIT CDMAChannelData OPTIONAL,
	-- (Target) O 6.5.2.30 a
	cdmaCodeChannelList						[132] IMPLICIT CDMACodeChannelList OPTIONAL,
	-- O 6.5.2.33 a
	cdmaConnectionReferenceList				[212] IMPLICIT CDMAConnectionReferenceList OPTIONAL,
	-- O 6.5.2.aq IS-737 a, i, k, zz
	cdmaSearchParameters					[230] IMPLICIT CDMASearchParameters OPTIONAL,
	-- O 6.5.2.bi a, k
	cdmaSearchWindow						[69] IMPLICIT CDMASearchWindow OPTIONAL,
	-- O 6.5.2.37 a
	cdmaServiceConfigurationRecord			[174] IMPLICIT CDMAServiceConfigurationRecord OPTIONAL,
	-- O 6.5.2.e a, h, t
	channelData								[5] IMPLICIT ChannelData OPTIONAL,
	-- (Target) O 6.5.2.47 b
	confidentialityModes					[39] IMPLICIT ConfidentialityModes OPTIONAL,
	-- (Actual) O 6.5.2.50 c
	nampsChannelData						[74] IMPLICIT NAMPSChannelData OPTIONAL,
	-- (Target) O 6.5.2.86 d
	targetCellID							[3] IMPLICIT TargetCellID,
	-- O 6.5.2.148 e
	tdmaBurstIndicator						[31] IMPLICIT TDMABurstIndicator OPTIONAL,
	-- (Target) O 6.5.2.151 f
	tdmaChannelData							[28] IMPLICIT TDMAChannelData OPTIONAL,
	-- (Target) O 6.5.2.153 g
	tdmaVoiceCoder							[180] IMPLICIT TDMAVoiceCoder OPTIONAL
	-- (Target) O 6.5.2.k j
	}

-- 6.4.2.21 InformationDirective Updated with N.S0012-0 v 1.0
-- http://www.3gpp2.org/Public_html/specs/X.S0004-540-E_v2.0_070723.pdf
InformationDirective ::= [PRIVATE 18] SET {
	electronicSerialNumber					[9] IMPLICIT ElectronicSerialNumber,
	-- M 6.5.2.63
	msid									MSID OPTIONAL,
	-- M 2.153 e
	alertCode								[75] IMPLICIT AlertCode OPTIONAL,
	-- O 6.5.2.3 a
	announcementList						[130] IMPLICIT AnnouncementList OPTIONAL,
	-- O 6.5.2.6 b
	callingPartyNumberString1				[82] IMPLICIT CallingPartyNumberString1 OPTIONAL,
	-- O 6.5.2.23 c
	callingPartyNumberString2				[83] IMPLICIT CallingPartyNumberString2 OPTIONAL,
	-- O 6.5.2.24 c
	callingPartySubaddress					[84] IMPLICIT CallingPartySubaddress OPTIONAL,
	-- O 6.5.2.25 c
	displayText								[244] IMPLICIT DisplayText OPTIONAL,
	-- O 6.5.2.bx d, e, p
	displayText2							[299] IMPLICIT DisplayText2 OPTIONAL,
	-- 6.5.2.ec
	redirectingNumberString					[101] IMPLICIT RedirectingNumberString OPTIONAL,
	-- O 6.5.2.108 c
	redirectingSubaddress					[102] IMPLICIT RedirectingSubaddress OPTIONAL,
	-- O 6.5.2.109 c
	senderIdentificationNumber				[103] IMPLICIT SenderIdentificationNumber OPTIONAL
	-- O 6.5.2.116 d
	}

-- InformationDirective RETURN RESULT Parameters

InformationDirectiveRes ::= [PRIVATE 18] SET {
	alertResult								[129] IMPLICIT AlertResult OPTIONAL
	-- O 6.5.2.4 a
	}

-- 6.4.2.22 InformationForward
InformationForward ::= [PRIVATE 18] SET {
	interMSCCircuitID						[6] IMPLICIT	InterMSCCircuitID,
	-- M 6.5.2.72
	mobileIdentificationNumber				[8] IMPLICIT MobileIdentificationNumber,
	-- M 6.5.2.81
	alertCode								[75] IMPLICIT AlertCode OPTIONAL,
	-- O 6.5.2.3 a
	announcementList						[130] IMPLICIT AnnouncementList OPTIONAL,
	-- O 6.5.2.6 a
	callingPartyNumberString1				[82] IMPLICIT CallingPartyNumberString1 OPTIONAL,
	-- O 6.5.2.23 b
	callingPartyNumberString2				[83] IMPLICIT CallingPartyNumberString2 OPTIONAL,
	-- O 6.5.2.24 b
	callingPartySubaddress					[84] IMPLICIT CallingPartySubaddress OPTIONAL,
	-- O 6.5.2.25 b
	displayText								[244] IMPLICIT DisplayText OPTIONAL,
	-- O 6.5.2.bx d, e, p
	displayText2							[299] IMPLICIT DisplayText2 OPTIONAL,
	-- 6.5.2.ec
	electronicSerialNumber					[9] IMPLICIT ElectronicSerialNumber OPTIONAL,
	-- O 6.5.2.63 a
	messageWaitingNotificationCount			[92] IMPLICIT MessageWaitingNotificationCount OPTIONAL,
	-- O 6.5.2.78 a
	messageWaitingNotificationType			[145] IMPLICIT MessageWaitingNotificationType OPTIONAL,
	-- O 6.5.2.79 a
	redirectingNumberString					[101] IMPLICIT RedirectingNumberString OPTIONAL,
	-- O 6.5.2.108 b
	redirectingSubaddress					[102] IMPLICIT RedirectingSubaddress OPTIONAL,
	-- O 6.5.2.109 b	
	meid									[390] IMPLICIT MEID OPTIONAL
	-- O
	}

-- InformationForward RETURN RESULT Parameters
InformationForwardRes ::= [PRIVATE 18] SET {
	alertResult								[129] IMPLICIT AlertResult OPTIONAL
	-- O 6.5.2.4 a
	}

-- 6.4.2.23 InterSystemAnswer

InterSystemAnswer ::= [PRIVATE 18] SET {
	interMSCCircuitID						[6] IMPLICIT InterMSCCircuitID,
	-- M 6.5.2.72
	mobileIdentificationNumber				[8] IMPLICIT MobileIdentificationNumber,
	-- M 6.5.2.81
	electronicSerialNumber					[9] IMPLICIT ElectronicSerialNumber OPTIONAL
	-- O 6.5.2.63 a
	}
-- InterSystemAnswer RETURN RESULT Parameters
-- zero octets

-- 6.4.2.24 InterSystemPage

InterSystemPage ::= [PRIVATE 18] SET {
	billingID								[1] IMPLICIT BillingID,
	-- (Originating) M 6.5.2.16
	electronicSerialNumber					[9] IMPLICIT ElectronicSerialNumber,
	-- M 6.5.2.63
	alertCode								[75] IMPLICIT AlertCode OPTIONAL,
	-- O 6.5.2.3 a
	callingPartyName						[243] IMPLICIT CallingPartyName OPTIONAL,
	-- O 6.5.2.bw a, m
	callingPartyNumberDigits1				[80] IMPLICIT CallingPartyNumberDigits1 OPTIONAL,
	-- O 6.5.2.21 a
	callingPartyNumberDigits2				[81] IMPLICIT CallingPartyNumberDigits2 OPTIONAL,
	-- O 6.5.2.22 a
	callingPartyNumberString1				[82] IMPLICIT CallingPartyNumberString1 OPTIONAL,
	-- O 6.5.2.23 a
	callingPartyNumberString2				[83] IMPLICIT CallingPartyNumberString2 OPTIONAL,
	-- O 6.5.2.24 a
	callingPartySubaddress					[84] IMPLICIT CallingPartySubaddress OPTIONAL,
	-- O 6.5.2.25 a
	cdmaBandClass							[170] IMPLICIT CDMABandClass OPTIONAL,
	-- O 6.5.2.a m
	cdmaMobileProtocolRevision				[66] IMPLICIT CDMAMobileProtocolRevision OPTIONAL,
	-- O 6.5.2.34 c
	cdmaServiceOption						[175] IMPLICIT CDMAServiceOption OPTIONAL,
	-- O 6.5.2.f m
	cdmaServiceOptionList					[176] IMPLICIT CDMAServiceOptionList OPTIONAL,
	-- O 6.5.2.g
	cdmaSlotCycleIndex						[166] IMPLICIT CDMASlotCycleIndex OPTIONAL,
	-- O 6.5.2.40 b
	cdmaStationClassMark					[59] IMPLICIT CDMAStationClassMark OPTIONAL,
	-- O 6.5.2.41 c
	cdmaStationClassMark2					[177] IMPLICIT CDMAStationClassMark2 OPTIONAL,
	-- O 6.5.2.h m
	controlChannelMode						[199] IMPLICIT ControlChannelMode OPTIONAL,
	-- O 6 .5.2.ac m
	displayText								[244] IMPLICIT DisplayText OPTIONAL,
	-- O 6.5.2.bx d, e, p
	displayText2							[299] IMPLICIT DisplayText2 OPTIONAL,
	-- 6.5.2.ec
	dmh-AccountCodeDigits					[140] IMPLICIT DMH-AccountCodeDigits OPTIONAL,
	-- O 6.5.2.59 a
	dmh-AlternateBillingDigits				[141] IMPLICIT DMH-AlternateBillingDigits OPTIONAL,
	-- O 6.5.2.60 a
	dmh-BillingDigits						[142] IMPLICIT DMH-BillingDigits OPTIONAL,
	-- O 6.5.2.61 a
	extendedMSCID							[53] IMPLICIT ExtendedMSCID OPTIONAL,
	-- (Serving MSC) O 6.5.2.64 d
	extendedSystemMyTypeCode				[54] IMPLICIT ExtendedSystemMyTypeCode OPTIONAL,
	-- (Serving MSC) O 6.5.2.65 e
	imsi									[242] IMPLICIT IMSI OPTIONAL,
	-- O 6.5.2.bu
	legInformation							[144] IMPLICIT LegInformation OPTIONAL,
	-- O 6.5.2.75 f
	locationAreaID							[33] IMPLICIT LocationAreaID OPTIONAL,
	-- O 6.5.2.77 f
	mobileDirectoryNumber					[93] IMPLICIT MobileDirectoryNumber OPTIONAL,
	-- O 6.5.2.80 a
	mobileIdentificationNumber				[8] IMPLICIT MobileIdentificationNumber OPTIONAL,
	-- O 6.5.2.81
	mscid									[21] IMPLICIT MSCID OPTIONAL,
	-- (Originating MSC) O 6.5.2.82 g
	mSCIdentificationNumber					[94] IMPLICIT MSCIdentificationNumber OPTIONAL,
	-- O 6.5.2.83 f
	mSIDUsage								[327] IMPLICIT MSIDUsage OPTIONAL,
	-- O 6.5.2.fe
	networkTMSI								[233] IMPLICIT NetworkTMSI OPTIONAL,
	-- O 6.5.2.bl o
	oneTimeFeatureIndicator					[97] IMPLICIT OneTimeFeatureIndicator OPTIONAL,
	-- O 6.5.2.88 f
	pageCount								[300] IMPLICIT PageCount OPTIONAL,
	-- O 6.5.2.ed
	pageIndicator							[71] IMPLICIT PageIndicator OPTIONAL,
	-- O 6.5.2.92 h
	pageResponseTime						[301] IMPLICIT PageResponseTime OPTIONAL,
	-- O 6.5.2.ee
	pc-ssn									[32] IMPLICIT PC-SSN OPTIONAL,
	-- (Originating MSC) O 6.5.2.93 i
	pilotBillingID							[169] IMPLICIT PilotBillingID OPTIONAL,
	-- O 6.5.2.94 j
	pilotNumber								[168] IMPLICIT PilotNumber OPTIONAL,
	-- O 6.5.2.95 k
	preferredLanguageIndicator				[147] IMPLICIT PreferredLanguageIndicator OPTIONAL,
	--  O 6.5.2.96 a
	redirectingNumberDigits					[100] IMPLICIT RedirectingNumberDigits OPTIONAL,
	--O 6.5.2.107 a
	redirectingNumberString					[101] IMPLICIT RedirectingNumberString OPTIONAL,
	-- O 6.5.2.108 a
	redirectingPartyName					[245] IMPLICIT RedirectingPartyName OPTIONAL,
	-- O 6.5.2.by a, m
	redirectingSubaddress					[102] IMPLICIT RedirectingSubaddress OPTIONAL,
	-- O 6.5.2.109 a
	senderIdentificationNumber				[103] IMPLICIT SenderIdentificationNumber OPTIONAL,
	-- O 6.5.2.116 f
	systemMyTypeCode						[22] IMPLICIT SystemMyTypeCode OPTIONAL,
	-- (Originating MSC) O 6.5.2.147 l
	tdmaDataFeaturesIndicator				[221] IMPLICIT TDMADataFeaturesIndicator OPTIONAL,
	-- O 6.5.2.az p
	tdmaServiceCode							[178] IMPLICIT TDMAServiceCode OPTIONAL,
	-- O 6.5.2.i
	terminalType							[47] IMPLICIT TerminalType OPTIONAL,
	-- O 6 .5.2.154 f
	terminationTreatment					[121] IMPLICIT TerminationTreatment OPTIONAL,
	-- O 6.5.2.158 f
	terminationTriggers						[122] IMPLICIT TerminationTriggers OPTIONAL,
	-- O 6.5.2.159 a
	triggerAddressList						[276] IMPLICIT TriggerAddressList OPTIONAL
	-- O 6.5.2.de a
	}

-- InterSystemPage RETURN RESULT Parameters
InterSystemPageRes ::= [PRIVATE 18] SET {
	accessDeniedReason						[20] IMPLICIT AccessDeniedReason OPTIONAL,
	-- O 6.5.2.1 a
	billingID								[1] IMPLICIT BillingID OPTIONAL,
	-- (Terminating) O 6.5.2.16 b, c
	cdmaServiceOption						[175] IMPLICIT CDMAServiceOption OPTIONAL,
	-- O 6.5.2.f
	conditionallyDeniedReason				[162] IMPLICIT ConditionallyDeniedReason OPTIONAL,
	-- O 6.5.2.48 d
	digits		 							[4] IMPLICIT Digits OPTIONAL,
	-- (Destination) O 6.5.2.58 c
	extendedMSCID							[53] IMPLICIT ExtendedMSCID OPTIONAL,
	-- (Border MSC) O 6.5.2.64 c
	extendedSystemMyTypeCode				[54] IMPLICIT ExtendedSystemMyTypeCode OPTIONAL,
	-- (Border MSC) O 6.5.2.65 c
	mSCIdentificationNumber					[94] IMPLICIT MSCIdentificationNumber OPTIONAL,
	-- O 6.5.2.83 e
	pc-ssn									[32] IMPLICIT PC-SSN OPTIONAL,
	-- (Border MSC) O 6.5.2.93 f
	tdmaServiceCode							[178] IMPLICIT TDMAServiceCode OPTIONAL
	-- O 6.5.2.i	
	}

-- 6.4.2.25 InterSystemPage2
InterSystemPage2 ::= [PRIVATE 18] SET {
	billingID								[1] IMPLICIT BillingID,
	-- (Anchor MSC) M 6.5.2.16
	electronicSerialNumber					[9] IMPLICIT ElectronicSerialNumber,
	-- M 6.5.2.63
	alertCode								[75] IMPLICIT AlertCode OPTIONAL,
	-- O 6.5.2.3 a
	callingPartyNumberString1				[82] IMPLICIT CallingPartyNumberString1 OPTIONAL,
	-- O 6.5.2.23 b
	callingPartyNumberString2				[83] IMPLICIT CallingPartyNumberString2 OPTIONAL,
	-- O 6.5.2.24 b
	callingPartySubaddress					[84] IMPLICIT CallingPartySubaddress OPTIONAL,
	-- O 6.5.2.25 b
	cdmaBandClass							[170] IMPLICIT CDMABandClass OPTIONAL,
	-- O 6.5.2.a f
	cdmaMobileProtocolRevision				[66] IMPLICIT CDMAMobileProtocolRevision OPTIONAL,
	-- O 6.5.2.34 c
	controlChannelMode						[199] IMPLICIT ControlChannelMode OPTIONAL,
	-- O 6 .5.2.ac f
	cdmaServiceOption						[175] IMPLICIT CDMAServiceOption OPTIONAL,
	-- O 6.5.2.f f
	cdmaServiceOptionList					[176] IMPLICIT CDMAServiceOptionList OPTIONAL,
	-- O 6.5.2.g h
	cdmaSlotCycleIndex						[166] IMPLICIT CDMASlotCycleIndex OPTIONAL,
	-- O 6.5.2.40 b
	cdmaStationClassMark					[59] IMPLICIT CDMAStationClassMark OPTIONAL,
	-- O 6.5.2.41 d
	cdmaStationClassMark2					[177] IMPLICIT CDMAStationClassMark2 OPTIONAL,
	-- O 6.5.2.h f
	displayText								[244] IMPLICIT DisplayText OPTIONAL,
	-- O 6.5.2.bx d, e, p
	displayText2							[299] IMPLICIT DisplayText2 OPTIONAL,
	-- 6.5.2.ec
	imsi									[242] IMPLICIT IMSI OPTIONAL,
	-- O 6.5.2.bu
	locationAreaID							[33] IMPLICIT LocationAreaID OPTIONAL,
	-- O 6.5.2.77 e
	mobileDirectoryNumber					[93] IMPLICIT MobileDirectoryNumber OPTIONAL,
	-- O 6.5.2.80 a
	mobileIdentificationNumber				[8] IMPLICIT MobileIdentificationNumber,
	-- M 6.5.2.81
	mSIDUsage								[327] IMPLICIT MSIDUsage OPTIONAL,
	-- O 6.5.2.fe k
	networkTMSI								[233] IMPLICIT NetworkTMSI OPTIONAL,
	-- O 6.5.2.bl h
	nonPublicData							[200] IMPLICIT NonPublicData OPTIONAL,
	-- O 6.5.2.ad IS-730 l
	pageCount								[300] IMPLICIT PageCount OPTIONAL,
	-- O 6.5.2.ed
	pageIndicator							[71] IMPLICIT PageIndicator OPTIONAL,
	-- O 6.5.2.92 f
	pagingFrameClass						[210] IMPLICIT PagingFrameClass OPTIONAL,
	-- O 6 .5.2.ae g
	pageResponseTime						[301] IMPLICIT PageResponseTime OPTIONAL,
	-- O 6.5.2.ee IS-730 h
	pSID-RSIDList							[203] IMPLICIT PSID-RSIDList OPTIONAL,
	-- O 6.5.2.ag IS-730 m,
	redirectingNumberString					[101] IMPLICIT RedirectingNumberString OPTIONAL,
	-- O 6.5.2.108 b
	redirectingSubaddress					[102] IMPLICIT RedirectingSubaddress OPTIONAL,
	-- O 6.5.2.109 b
	tdmaDataFeaturesIndicator				[221] IMPLICIT TDMADataFeaturesIndicator OPTIONAL,
	-- O 6.5.2.az i
	tdmaServiceCode							[178] IMPLICIT TDMAServiceCode OPTIONAL,
	-- O 6.5.2.i
	terminalType							[47] IMPLICIT TerminalType OPTIONAL,
	-- O 6 .5.2.154 d
	userZoneData							[209] IMPLICIT UserZoneData OPTIONAL
	-- O 6.5.2.am IS-730
	}

-- InterSystemPage2 RETURN RESULT Parameters

InterSystemPage2Res ::= [PRIVATE 18] SET {
	accessDeniedReason						[20] IMPLICIT AccessDeniedReason OPTIONAL,
	-- O 6.5.2.1 a
	authenticationResponseBaseStation		[36] IMPLICIT AuthenticationResponseBaseStation,
	-- O 6.5.2.10 b
	callHistoryCount						[38] IMPLICIT CallHistoryCount OPTIONAL,
	-- O 6.5.2.18 b
	cdmaServiceOption						[175] IMPLICIT CDMAServiceOption OPTIONAL,
	-- O 6.5.2.f
	randc									[67] IMPLICIT RANDC OPTIONAL,
	-- O 6.5.2.100 c
	randomVariableBaseStation				[41] IMPLICIT RandomVariableBaseStation,
	-- O 6.5.2.101 d
	systemAccessType						[34] IMPLICIT SystemAccessType,
	-- O 6.5.2.145 b	
	systemCapabilities						[49] IMPLICIT SystemCapabilities OPTIONAL,
	-- (Border) O 6.5.2.146 e
	tdmaDataMode							[222] IMPLICIT TDMADataMode OPTIONAL,
	-- O 6.5.2.ba e
	tdmaServiceCode							[178] IMPLICIT TDMAServiceCode OPTIONAL,
	-- O 6.5.2.i
	terminalType							[47] IMPLICIT TerminalType OPTIONAL
	-- O 6.5.2.154 e
	}

-- 6.4.2.26 InterSystemSetup
InterSystemSetup ::= [PRIVATE 18] SET {
	billingID								[1] IMPLICIT BillingID,
	-- (Anchor MSC) M 6.5.2.16
	electronicSerialNumber					[9] IMPLICIT ElectronicSerialNumber,
	-- M 6.5.2.63
	interMSCCircuitID						[6] IMPLICIT	InterMSCCircuitID,
	-- M 6.5.2.72
--	mobileIdentificationNumber				[8] IMPLICIT MobileIdentificationNumber,
	-- M 6.5.2.81
-- (IS-751)
	alertCode								[75] IMPLICIT AlertCode OPTIONAL,
	-- O 6.5.2.3 a, g
	callingPartyNumberString1				[82] IMPLICIT CallingPartyNumberString1 OPTIONAL,
	-- O 6.5.2.23 b, g
	callingPartyNumberString2				[83] IMPLICIT CallingPartyNumberString2 OPTIONAL,
	-- O 6.5.2.24 b, g

	callingPartySubaddress					[84] IMPLICIT CallingPartySubaddress OPTIONAL,
	-- O 6.5.2.25 b, g
	cdmaPrivateLongCodeMask					[67] IMPLICIT CDMAPrivateLongCodeMask OPTIONAL,
	-- O 6.5.2.36 a
	cdmaServiceOption						[175] IMPLICIT CDMAServiceOption OPTIONAL,
	-- O 6.5.2.f e, g
	cdmaServiceOptionList					[176] IMPLICIT CDMAServiceOptionList OPTIONAL,
	-- O 6.5.2.g f, g
	changeServiceAttributes					[214] IMPLICIT ChangeServiceAttributes OPTIONAL,
	-- O 6.5.2.as c
	dataKey									[215] IMPLICIT DataKey OPTIONAL,
	-- O 6.5.2.at b
	displayText								[244] IMPLICIT DisplayText OPTIONAL,
	-- O 6.5.2.bx a, b
	displayText2							[299] IMPLICIT DisplayText2 OPTIONAL,
	-- O 6.5.2.ec (misc 10.0) a, c, g
	imsi									[242] IMPLICIT IMSI OPTIONAL,
	-- O 6.5.2.bu (IS-751) d
	ilspInformation							[217] IMPLICIT ISLPInformation OPTIONAL,
	-- (Desired) O 6.5.2.av d
	mobileIdentificationNumber				[8] IMPLICIT MobileIdentificationNumber,
	-- M 6.5.2.81 (IS-751)
	redirectingNumberString					[101] IMPLICIT RedirectingNumberString OPTIONAL,
	-- O 6.5.2.108 b, g
	edirectingSubaddress					[102] IMPLICIT RedirectingSubaddress OPTIONAL,
	-- O 6.5.2.109 b, g
	signalingMessageEncryptionKey			[45] IMPLICIT SignalingMessageEncryptionKey OPTIONAL,
	-- O 6.5.2.120 a
	voicePrivacyMask						[48] IMPLICIT VoicePrivacyMask OPTIONAL,
	-- O 6.5.2.166 a	
	meid									[390] IMPLICIT MEID OPTIONAL
	-- O
	}

-- InterSystemSetup RETURN RESULT Parameters

InterSystemSetupRes ::= [PRIVATE 18] SET {
	cdmaConnectionReferenceList				[212] IMPLICIT CDMAConnectionReferenceList OPTIONAL,
	-- O 6.5.2.aq a
	cdmaServiceOption						[175] IMPLICIT CDMAServiceOption OPTIONAL,
	--O 6.5.2.f TSB76 b
	ilspInformation							[217] IMPLICIT ISLPInformation OPTIONAL,
	-- (Actual) O 6.5.2.av
	setupResult								[151] IMPLICIT SetupResult OPTIONAL
	-- O 6.5.2.118 a
	}

-- 6.4.2.27 LocationRequest Updated with N.S0023-0 v 1.0
LocationRequest ::= [PRIVATE 18] SET {
	billingID								[1] IMPLICIT BillingID,
	-- (Originating) M 6.5.2.16
	digits		 							[4] IMPLICIT Digits,
	-- (Dialed) M 6.5.2.58
	mscid									[21] IMPLICIT MSCID,
	-- (Originating) M 6.5.2.82
	systemMyTypeCode						[22] IMPLICIT SystemMyTypeCode,
	-- (Originating) M 6.5.2.147
	acgencountered							[340] IMPLICIT ACGEncountered OPTIONAL,
	-- O 6.5.2.fv
	callingPartyNumberDigits1				[80] IMPLICIT CallingPartyNumberDigits1 OPTIONAL,
	--O 6.5.2.21 a
	callingPartyNumberDigits2				[81] IMPLICIT CallingPartyNumberDigits2 OPTIONAL,
	--O 6.5.2.22 a
	callingPartySubaddress					[84] IMPLICIT CallingPartySubaddress OPTIONAL,
	--O 6.5.2.25 a
	cdmaServiceOption						[175] IMPLICIT CDMAServiceOption OPTIONAL,
	-- O 6.5.2.f g
	mSCIdentificationNumber					[94] IMPLICIT MSCIdentificationNumber OPTIONAL,
	-- O 6.5.2.83 b
	pc-ssn									[32] IMPLICIT PC-SSN OPTIONAL,
	-- (Originating) O 6.5.2.93 c
	redirectingNumberDigits					[100] IMPLICIT RedirectingNumberDigits OPTIONAL,
	-- O 6.5.2.107 a
	redirectingPartyName					[245] IMPLICIT RedirectingPartyName OPTIONAL,
	-- O 6.5.2.by
	redirectingSubaddress					[102] IMPLICIT RedirectingSubaddress OPTIONAL,
	-- O 6.5.2.109 a
	senderIdentificationNumber				[103] IMPLICIT SenderIdentificationNumber OPTIONAL,
	-- O 6.5.2.116 d
	terminationAccessType					[119] IMPLICIT TerminationAccessType OPTIONAL,
	-- O 6.5.2.155 d
	tdmaServiceCode							[178] IMPLICIT TDMAServiceCode OPTIONAL,
	-- O 6.5.2.i h	
	transactionCapability					[123] IMPLICIT TransactionCapability OPTIONAL,
	-- O 6.5.2.160 e
	triggerType								[279] IMPLICIT TriggerType OPTIONAL,
	-- O 6.5.2.dh f
	winCapability							[280] IMPLICIT WINCapability OPTIONAL,
	-- O 6.5.2.di
	callingPartyCategory					[355] IMPLICIT CallingPartyCategory OPTIONAL
	-- O 6.5.2.gl
	}
-- LocationRequest RETURN RESULT Parameters

LocationRequestRes ::= [PRIVATE 18] SET {
	electronicSerialNumber					[9] IMPLICIT ElectronicSerialNumber,
	-- M 6.5.2.63 a
	mobileIdentificationNumber				[8] IMPLICIT MobileIdentificationNumber,
	-- M 6.5.2.81 a
	mscid									[21] IMPLICIT MSCID,
	-- (Serving MSC) M 6.5.2.82 b
	accessDeniedReason						[20] IMPLICIT AccessDeniedReason OPTIONAL,
	-- O 6.5.2.1 c
	announcementList						[130] IMPLICIT AnnouncementList OPTIONAL,
	-- O 6.5.2.6 d
	callingPartyNumberString1				[82] IMPLICIT CallingPartyNumberString1 OPTIONAL,
	-- O 6.5.2.23 e
	callingPartyNumberString2				[83] IMPLICIT CallingPartyNumberString2 OPTIONAL,
	-- O 6.5.2.24 e
	cdmaServiceOption						[175] IMPLICIT CDMAServiceOption OPTIONAL,
	-- O 6.5.2.f
	controlNetworkID						[307] IMPLICIT ControlNetworkID OPTIONAL,
	-- O 6.5.2.ek s
	digits-carrier 							[4] IMPLICIT Digits OPTIONAL,
	-- (Carrier) O 6.5.2.58 f
	digits-dest 							[4] IMPLICIT Digits OPTIONAL,
	-- (Destination) O 6.5.2.58 g, h
	displayText								[244] IMPLICIT DisplayText OPTIONAL,
	-- O 6.5.2.bx d, e, p
	displayText2							[299] IMPLICIT DisplayText2 OPTIONAL,
	-- 6.5.2.ec
	dmh-AccountCodeDigits					[140] IMPLICIT DMH-AccountCodeDigits OPTIONAL,
	-- O 6.5.2.59 i
	dmh-AlternateBillingDigits				[141] IMPLICIT DMH-AlternateBillingDigits OPTIONAL,
	-- O 6.5.2.60 i
	dmh-BillingDigits						[142] IMPLICIT DMH-BillingDigits OPTIONAL,
	-- O 6.5.2.61 i
	dmh-RedirectionIndicator				[88] IMPLICIT DMH-RedirectionIndicator OPTIONAL,
	-- O 6.5.2.62 j
	dmh-ServiceID							[305] IMPLICIT DMH-ServiceID OPTIONAL,
	-- O 6.5.2.ei q
	groupInformation						[163] IMPLICIT GroupInformation OPTIONAL,
	-- O 6.5.2.69 k
	mobileDirectoryNumber					[93] IMPLICIT MobileDirectoryNumber OPTIONAL,
	-- O 6.5.2.80 i
	noAnswerTime							[96] IMPLICIT NoAnswerTime OPTIONAL,
	-- O 6.5.2.87 l
	oneTimeFeatureIndicator					[97] IMPLICIT OneTimeFeatureIndicator OPTIONAL,
	-- O 6.5.2.88 m
	pc-ssn									[32] IMPLICIT PC-SSN OPTIONAL,
	-- (Serving MSC or VLR) O 6.5.2.93 n
	preferredLanguageIndicator				[147] IMPLICIT PreferredLanguageIndicator OPTIONAL,
	-- O 6.5.2.96 f, r
	redirectingNumberDigits					[100] IMPLICIT RedirectingNumberDigits OPTIONAL,
	-- O 6.5.2.107 j
	redirectingNumberString					[101] IMPLICIT RedirectingNumberString OPTIONAL,
	-- O 6.5.2.108 f
	redirectingSubaddress					[102] IMPLICIT RedirectingSubaddress OPTIONAL,
	-- O 6.5.2.109 e, j
	routingDigits							[150] IMPLICIT RoutingDigits OPTIONAL,
	-- O 6.5.2.114 f
	tdmaServiceCode							[178] IMPLICIT TDMAServiceCode OPTIONAL,
	-- O 6.5.2.i
	terminationList							[120] IMPLICIT TerminationList OPTIONAL,
	-- O 6.5.2.156 o
	terminationTriggers						[122] IMPLICIT TerminationTriggers OPTIONAL,
	-- O 6.5.2.159 f
	triggerAddressList						[276] IMPLICIT TriggerAddressList OPTIONAL,
	-- O 6.5.2.de f, t
	meid									[390] IMPLICIT MEID OPTIONAL
	-- O
	}

-- 6.4.2.28 MobileOnChannel

--MobileOnChannel ::= [PRIVATE 18] SET {
-- zero octets
--	}

-- 6.4.2.29 MSInactive
MSInactive ::= [PRIVATE 18] SET {
	lectronicSerialNumber					[9] IMPLICIT ElectronicSerialNumber,
	-- M 6.5.2.63
	mobileIdentificationNumber				[8] IMPLICIT MobileIdentificationNumber,
	-- M 6.5.2.81
	callHistoryCount						[38] IMPLICIT CallHistoryCount OPTIONAL,
	-- O 6.5.2.18 a
	deregistrationType						[73] IMPLICIT DeregistrationType OPTIONAL,
	-- O 6.5.2.55 b
	destinationDigits						[87] IMPLICIT	DestinationDigits OPTIONAL,
	-- O 6.5.2.56
	locationAreaID							[33] IMPLICIT LocationAreaID OPTIONAL,
	-- O 6.5.2.77 c
	senderIdentificationNumber				[103] IMPLICIT SenderIdentificationNumber OPTIONAL,
	-- O 6.5.2.116 d
	servicesResult							[204] IMPLICIT ServicesResult OPTIONAL,
	-- O 6 .5.2.ah f
	sms-MessageWaitingIndicator				[118] IMPLICIT SMS-MessageWaitingIndicator OPTIONAL,
	-- O 6.5.2.129 e
	meid									[390] IMPLICIT MEID OPTIONAL
	-- O
	}

-- MSInactive RETURN RESULT Parameters
-- zero octets

-- 6.4.2.30
-- OriginationRequest INVOKE Parameters Updated with N.S0023-0 v 1.0
OriginationRequest ::= [PRIVATE 18] SET {
	billingID								[1] IMPLICIT BillingID,
	--(originating) M 6.5.2.16	1 0 0 0 0 0 0 1 (0x81)(0x1)
	digits		 							[4] IMPLICIT Digits,
	--(Dialed) M 6.5.2.58
	electronicSerialNumber					[9] IMPLICIT ElectronicSerialNumber,
	--M 6.5.2.63
	mobileIdentificationNumber				[8] IMPLICIT MobileIdentificationNumber,
	--M 6.5.2.81
	mscid									[21] IMPLICIT MSCID,
	--(Originating MSC) M 6.5.2.82	1 0 0 1 0 1 0 1 (0x95)(0x15)
	msid									MSID OPTIONAL,
	-- M 6.5.2.bv k
	transactionCapability					[123] IMPLICIT TransactionCapability,
	--M 6.5.2.160	1 0 0 1 1 1 1 1 (0x9f)
	acgencountered							[340] IMPLICIT ACGEncountered OPTIONAL,
	-- O 6.5.2.fv k
	callingPartyName						[243] IMPLICIT CallingPartyName OPTIONAL,
	-- O 6.5.2.bw g
	--	N.S0012-0_v1.0
	--				0 1 1 1 1 0 1 1 (0x7b)(123)
	callingPartyNumberDigits1				[80] IMPLICIT CallingPartyNumberDigits1 OPTIONAL,
	--O 6.5.2.21 a	1 0 0 1 1 1 1 1 (0x9f)
	--				0 1 0 1 0 0 0 0 (0x50)
	callingPartyNumberDigits2				[81] IMPLICIT CallingPartyNumberDigits2 OPTIONAL,
	--O 6.5.2.22 a	1 0 0 1 1 1 1 1 (0x9f)
	--				0 1 0 1 0 0 0 1 (0x51)
	callingPartySubaddress					[84] IMPLICIT CallingPartySubaddress OPTIONAL,
	--O 6.5.2.25 a	1 0 0 1 1 1 1 1 (0x9f)
	--				0 1 0 1 0 1 0 0 (0x54)
	locationAreaID							[33] IMPLICIT LocationAreaID OPTIONAL,
	--				0 1 0 1 1 1 0 1 (0x5d)
	featureIndicator						[306] IMPLICIT FeatureIndicator OPTIONAL,
	-- O 6.5.2.ej m
	mSCIdentificationNumber					[94] IMPLICIT MSCIdentificationNumber OPTIONAL,
	--O 6.5.2.83 c	1 0 0 1 1 1 1 1 (0x9f)
	--				0 1 0 1 1 1 1 0 (0x5e)
	oneTimeFeatureIndicator					[97] IMPLICIT OneTimeFeatureIndicator OPTIONAL,
	--O 6.5.2.88 d	1 0 0 1 1 1 1 1 (0x9f)
	--				0 1 1 0 0 0 0 1 (0x61)
	pc-ssn									[32] IMPLICIT PC-SSN OPTIONAL,
	--(Originating MSC), O 6.5.2.93 e	1 0 0 1 1 1 1 1 (0x9f)
	--									0 0 1 0 0 0 0 0 (0x20)
	senderIdentificationNumber				[103] IMPLICIT SenderIdentificationNumber OPTIONAL,
	--O 6.5.2.116 f		1 0 0 1 1 1 1 1 (0x9f)
	--					0 1 1 0 0 1 1 1 (0x67)
	servingCellID							[2] IMPLICIT ServingCellID OPTIONAL,
	--	O 6.5.2.117 a
	tdmaServiceCode							[178] IMPLICIT TDMAServiceCode OPTIONAL,
	-- O 6.5.2.i
	triggerType								[279] IMPLICIT TriggerType OPTIONAL,
	--	O 6.5.2.dh h
	winCapability							[280] IMPLICIT WINCapability OPTIONAL,
	--	O 6.5.2.di a
	-- NS0027
	meid									[390] IMPLICIT MEID OPTIONAL,
--	Profile **Macro** O 6.5.2.97 h
	authenticationCapability				[78] IMPLICIT AuthenticationCapability OPTIONAL,
	-- O 6.5.2.8 a
	callingFeaturesIndicator				[25] IMPLICIT CallingFeaturesIndicator OPTIONAL,
	-- O 6.5.2.20 b
	carrierDigits							[86] IMPLICIT CarrierDigits OPTIONAL,
	-- O 6.5.2.28 c
	cdmaServiceOptionList					[176] IMPLICIT CDMAServiceOptionList OPTIONAL,
	-- O 6.5.2.g d
	controlNetworkID						[307] IMPLICIT ControlNetworkID OPTIONAL,
	-- O 6.5.2.ek u
	dmh-AccountCodeDigits					[140] IMPLICIT DMH-AccountCodeDigits OPTIONAL,
	-- O 6.5.2.59 d
	dmh-AlternateBillingDigits				[141] IMPLICIT DMH-AlternateBillingDigits OPTIONAL,
	-- O 6.5.2.60 d
	dmh-BillingDigits						[142] IMPLICIT DMH-BillingDigits OPTIONAL,
	-- O 6.5.2.61 d
	geographicAuthorization					[143] IMPLICIT GeographicAuthorization OPTIONAL,
	-- O 6.5.2.68 e
	meidValidated							[401] IMPLICIT MEIDValidated OPTIONAL,
	-- O 3.2.2.98
	messageWaitingNotificationCount			[92] IMPLICIT MessageWaitingNotificationCount OPTIONAL,
	-- O 6.5.2.78 f
	messageWaitingNotificationType			[145] IMPLICIT MessageWaitingNotificationType OPTIONAL,
	-- O 6.5.2.79 g
	mobileDirectoryNumber					[93] IMPLICIT MobileDirectoryNumber OPTIONAL,
	--  O 6.5.2.80 d
	mobilePositionCapability				[335] IMPLICIT MobilePositionCapability OPTIONAL,
	-- O 6.5.2.fm t TIA/EIA/J-STD-036-A
	originationIndicator					[23] IMPLICIT OriginationIndicator OPTIONAL,
	-- O 6.5.2.89 h
	originationTriggers						[98] IMPLICIT OriginationTriggers OPTIONAL,
	-- O 6.5.2.90 i
	pACAIndicator							[146] IMPLICIT PACAIndicator OPTIONAL,
	-- O 6.5.2.91 j
	preferredLanguageIndicator				[147] IMPLICIT PreferredLanguageIndicator OPTIONAL,
	-- O 6.5.2.96 k
	qosPriority								[348] IMPLICIT QoSPriority OPTIONAL,
	--6.5.2.ge z
	restrictionDigits						[227] IMPLICIT RestrictionDigits OPTIONAL,
	-- O 6.5.2.113 l
	routingDigits							[150] IMPLICIT RoutingDigits OPTIONAL,
	-- O 6.5.2.114 m
	pSID-RSIDList							[203] IMPLICIT PSID-RSIDList OPTIONAL,
	-- O 6 .5.2.ag u , w
	sms-OriginationRestrictions				[115] IMPLICIT SMS-OriginationRestrictions OPTIONAL,
	-- O 6.5.2.136 n
	sms-TerminationRestrictions				[117] IMPLICIT SMS-TerminationRestrictions OPTIONAL,
	-- O 6.5.2.138 o
	spinipin								[154] IMPLICIT SPINIPIN OPTIONAL,
	-- O 6.5.2.139 p
	spiniTriggers							[155] IMPLICIT SPINITriggers OPTIONAL,
	-- O 6.5.2.140 q
	tdmaDataFeaturesIndicator				[221] IMPLICIT TDMADataFeaturesIndicator OPTIONAL,
	-- O 6.5.2.az s
	terminationRestrictionCode				[24] IMPLICIT TerminationRestrictionCode OPTIONAL,
	-- O 6.5.2.157 r
	terminationTriggers						[122] IMPLICIT TerminationTriggers OPTIONAL,
	-- O 6.5.2.159 s
	triggerAddressList						[276] IMPLICIT TriggerAddressList OPTIONAL,
	-- O 6.5.2.de t
	userGroup								[208] IMPLICIT UserGroup OPTIONAL,
	-- O 6 .5.2.al p
	nonPublicData							[200] IMPLICIT NonPublicData OPTIONAL,
	-- O 6 .5.2.ad v
	userZoneData							[209] IMPLICIT UserZoneData OPTIONAL,
	-- O 6 .5.2.am v , w
	callingPartyCategory					[355] IMPLICIT CallingPartyCategory OPTIONAL,
	-- O 6.5.2.gl z
	lirMode									[369] IMPLICIT LIRMode OPTIONAL,
	-- O 6.5.2.gz z
-- END MACRO
-- Mobinfo_CDMA **Macro** O 6.5.2.fo g expanded:
	cdmaChannelData							[63] IMPLICIT CDMAChannelData OPTIONAL,
	-- (Serving) O 6.5.2.30 c
	cdmaCodeChannel							[68] IMPLICIT CDMACodeChannel OPTIONAL,
	-- O 6.5.2.31 a
	cdmaMobileCapabilities					[330] IMPLICIT CDMAMobileCapabilities OPTIONAL,
	-- O 6.5.2.xx a
	cdmaPrivateLongCodeMask					[67] IMPLICIT CDMAPrivateLongCodeMask OPTIONAL,
	-- O 6.5.2.36 a
 	cdmaServingOneWayDelay2					[347] IMPLICIT	CDMAServingOneWayDelay2 OPTIONAL,
	-- O 6.5.2.gd a
	cdmaServiceOption						[175] IMPLICIT CDMAServiceOption OPTIONAL,
	-- O 6.5.2.f m
	cdmaTargetMAHOList						[136] IMPLICIT CDMATargetMAHOList OPTIONAL,
	-- O 6.5.2.43 g
	cdmaPSMMList							[346] IMPLICIT CDMAPSMMList OPTIONAL,
	-- O 6.5.2.gc a
	-- O
	mpcAddress							[370] IMPLICIT MPCAddress OPTIONAL,
	-- O 6.5.2.ha z, ab
	...
	}

-- OriginationRequest RETURN RESULT Parameters
OriginationRequestRes ::= [PRIVATE 18] SET {
	accessDeniedReason						[20] IMPLICIT AccessDeniedReason OPTIONAL,
	--	O 6.5.2.1 a
	actionCode								[128] IMPLICIT ActionCode OPTIONAL,
	--	O 6.5.2.2 b
	announcementList						[130] IMPLICIT AnnouncementList OPTIONAL,
	-- O 6.5.2.6 c
	callingPartyNumberString1				[82] IMPLICIT CallingPartyNumberString1 OPTIONAL,
	-- O 6.5.2.23 d, e
	callingPartyNumberString2				[83] IMPLICIT CallingPartyNumberString2 OPTIONAL,
	-- O 6.5.2.24 d, e
	callingPartySubaddress					[84] IMPLICIT CallingPartySubaddress OPTIONAL,
	--	O 6.5.2.25 d, e, f
	carrierDigits							[86] IMPLICIT CarrierDigits OPTIONAL,
	-- O 6.5.2.28 g
	digits		 							[4] IMPLICIT Digits OPTIONAL,
	-- (Dialed) O 6.5.2.58 h
	displayText								[244] IMPLICIT DisplayText OPTIONAL,
	-- O 6.5.2.bx d, e, p
	displayText2							[299] IMPLICIT DisplayText2 OPTIONAL,
	-- O 6.5.2.ec d, e, p
	dmh-AccountCodeDigits					[140] IMPLICIT DMH-AccountCodeDigits OPTIONAL,
	-- O 6.5.2.59 i
	dmh-AlternateBillingDigits				[141] IMPLICIT DMH-AlternateBillingDigits OPTIONAL,
	-- O 6.5.2.60 i
	dmh-BillingDigits						[142] IMPLICIT DMH-BillingDigits OPTIONAL,
	-- O 6.5.2.61 i
	dmh-ChargeInformation					[311] IMPLICIT DMH-ChargeInformation OPTIONAL,
	-- O 6.5.2.eo i, t
	dmh-RedirectionIndicator				[88] IMPLICIT DMH-RedirectionIndicator OPTIONAL,
	-- O 6.5.2.62 i, j
	dmh-ServiceID							[305] IMPLICIT DMH-ServiceID OPTIONAL,
	-- O 6.5.2.ei s
	groupInformation						[163] IMPLICIT GroupInformation OPTIONAL,
	-- O 6.5.2.69 k
	mobileDirectoryNumber					[93] IMPLICIT MobileDirectoryNumber OPTIONAL,
	--	 O 6.5.2.80 i
	noAnswerTime							[96] IMPLICIT NoAnswerTime OPTIONAL,
	-- O 6.5.2.87 l
	oneTimeFeatureIndicator					[97] IMPLICIT OneTimeFeatureIndicator OPTIONAL,
	--	O 6.5.2.88 m
	pilotNumber								[168] IMPLICIT PilotNumber OPTIONAL,
	-- O 6.5.2.95 k
	preferredLanguageIndicator				[147] IMPLICIT PreferredLanguageIndicator OPTIONAL,
	-- O 6.5.2.96 q, r
	redirectingNumberDigits					[100] IMPLICIT RedirectingNumberDigits OPTIONAL,
	-- O 6.5.2.107 f
	redirectingNumberString					[101] IMPLICIT RedirectingNumberString OPTIONAL,
	-- O 6.5.2.108 d
	redirectingSubaddress					[102] IMPLICIT RedirectingSubaddress OPTIONAL,
	-- O 6.5.2.109 d, e
	resumePIC								[266] IMPLICIT ResumePIC OPTIONAL,
	-- O 6.5.2.cu p
	routingDigits							[150] IMPLICIT RoutingDigits OPTIONAL,
	-- O 6.5.2.114 g
	terminationList							[120] IMPLICIT TerminationList OPTIONAL,
	-- O 6.5.2.156 n
	terminationTriggers						[122] IMPLICIT TerminationTriggers OPTIONAL,
	-- O 6.5.2.57 o
	triggerAddressList						[276] IMPLICIT TriggerAddressList OPTIONAL
	-- O 6.5.2.de q
	}

-- 6.4.2.31 QualificationDirective

QualificationDirective ::= [PRIVATE 18] SET {
	electronicSerialNumber					[9] IMPLICIT ElectronicSerialNumber,
	-- M 6.5.2.63
--	mobileIdentificationNumber				[8] IMPLICIT MobileIdentificationNumber,
	-- M 6.5.2.81
	msid									MSID OPTIONAL,
	-- M 6.5.2.bu j
	qualificationInformationCode			[17] IMPLICIT QualificationInformationCode,
	-- M 6.5.2.99
	systemMyTypeCode						[22] IMPLICIT SystemMyTypeCode,
	-- (HLR or VLR) M 6.5.2.147
	analogRedirectRecord					[225] IMPLICIT AnalogRedirectRecord OPTIONAL,
	-- O 6.5.2.bd k
	authorizationDenied						[13] IMPLICIT AuthorizationDenied OPTIONAL,
	-- O 6.5.2.13 a
	authorizationPeriod						[14] IMPLICIT AuthorizationPeriod OPTIONAL,
	-- O 6.5.2.14 b
	cdmaRedirectRecord						[229] IMPLICIT CDMARedirectRecord OPTIONAL,
	-- O 6.5.2.bh l
	controlChannelMode						[199] IMPLICIT ControlChannelMode OPTIONAL,
	-- O 6 .5.2.ac j
	deniedAuthorizationPeriod				[167] IMPLICIT DeniedAuthorizationPeriod OPTIONAL,
	-- O 6.5.2.53 c
	digits-carrier 							[4] IMPLICIT Digits OPTIONAL,
	-- (Carrier) O 6.5.2.58 d, e
	digits-dest 							[4] IMPLICIT Digits OPTIONAL,
	-- (Destination) O 6.5.2.58 d, f
	locationAreaID							[33] IMPLICIT LocationAreaID OPTIONAL,
	-- O 6.5.2.77 g
--	Profile **Macro** O 6.5.2.97 h
	authenticationCapability				[78] IMPLICIT AuthenticationCapability OPTIONAL,
	-- O 6.5.2.8 a
	callingFeaturesIndicator				[25] IMPLICIT CallingFeaturesIndicator OPTIONAL,
	-- O 6.5.2.20 b
	carrierDigits							[86] IMPLICIT CarrierDigits OPTIONAL,
	-- O 6.5.2.28 c
	cdmaServiceOptionList					[176] IMPLICIT CDMAServiceOptionList OPTIONAL,
	-- O 6.5.2.g d
	controlNetworkID						[307] IMPLICIT ControlNetworkID OPTIONAL,
	-- O 6.5.2.ek u
	dmh-AccountCodeDigits					[140] IMPLICIT DMH-AccountCodeDigits OPTIONAL,
	-- O 6.5.2.59 d
	dmh-AlternateBillingDigits				[141] IMPLICIT DMH-AlternateBillingDigits OPTIONAL,
	-- O 6.5.2.60 d
	dmh-BillingDigits						[142] IMPLICIT DMH-BillingDigits OPTIONAL,
	-- O 6.5.2.61 d
	geographicAuthorization					[143] IMPLICIT GeographicAuthorization OPTIONAL,
	-- O 6.5.2.68 e
	meidValidated							[401] IMPLICIT MEIDValidated OPTIONAL,
	-- O 3.2.2.98
	messageWaitingNotificationCount			[92] IMPLICIT MessageWaitingNotificationCount OPTIONAL,
	-- O 6.5.2.78 f
	messageWaitingNotificationType			[145] IMPLICIT MessageWaitingNotificationType OPTIONAL,
	-- O 6.5.2.79 g
	mobileDirectoryNumber					[93] IMPLICIT MobileDirectoryNumber OPTIONAL,
	--  O 6.5.2.80 d
	mobilePositionCapability				[335] IMPLICIT MobilePositionCapability OPTIONAL,
	-- O 6.5.2.fm t TIA/EIA/J-STD-036-A
	originationIndicator					[23] IMPLICIT OriginationIndicator OPTIONAL,
	-- O 6.5.2.89 h
	originationTriggers						[98] IMPLICIT OriginationTriggers OPTIONAL,
	-- O 6.5.2.90 i
	pACAIndicator							[146] IMPLICIT PACAIndicator OPTIONAL,
	-- O 6.5.2.91 j
	preferredLanguageIndicator				[147] IMPLICIT PreferredLanguageIndicator OPTIONAL,
	-- O 6.5.2.96 k
	qosPriority								[348] IMPLICIT QoSPriority OPTIONAL,
	--6.5.2.ge z
	restrictionDigits						[227] IMPLICIT RestrictionDigits OPTIONAL,
	-- O 6.5.2.113 l
	routingDigits							[150] IMPLICIT RoutingDigits OPTIONAL,
	-- O 6.5.2.114 m
	pSID-RSIDList							[203] IMPLICIT PSID-RSIDList OPTIONAL,
	-- O 6 .5.2.ag u , w
	sms-OriginationRestrictions				[115] IMPLICIT SMS-OriginationRestrictions OPTIONAL,
	-- O 6.5.2.136 n
	sms-TerminationRestrictions				[117] IMPLICIT SMS-TerminationRestrictions OPTIONAL,
	-- O 6.5.2.138 o
	spinipin								[154] IMPLICIT SPINIPIN OPTIONAL,
	-- O 6.5.2.139 p
	spiniTriggers							[155] IMPLICIT SPINITriggers OPTIONAL,
	-- O 6.5.2.140 q
	tdmaDataFeaturesIndicator				[221] IMPLICIT TDMADataFeaturesIndicator OPTIONAL,
	-- O 6.5.2.az s
	terminationRestrictionCode				[24] IMPLICIT TerminationRestrictionCode OPTIONAL,
	-- O 6.5.2.157 r
	terminationTriggers						[122] IMPLICIT TerminationTriggers OPTIONAL,
	-- O 6.5.2.159 s
	triggerAddressList						[276] IMPLICIT TriggerAddressList OPTIONAL,
	-- O 6.5.2.de t
	userGroup								[208] IMPLICIT UserGroup OPTIONAL,
	-- O 6 .5.2.al p
	nonPublicData							[200] IMPLICIT NonPublicData OPTIONAL,
	-- O 6 .5.2.ad v
	userZoneData							[209] IMPLICIT UserZoneData OPTIONAL,
	-- O 6 .5.2.am v , w
	callingPartyCategory					[355] IMPLICIT CallingPartyCategory OPTIONAL,
	-- O 6.5.2.gl z
	lirMode									[369] IMPLICIT LIRMode OPTIONAL,
	-- O 6.5.2.gz z
-- END MACRO
	serviceRedirectionInfo					[238] IMPLICIT ServiceRedirectionInfo OPTIONAL,
	-- O 6.5.2.bq k, l, m
	roamingIndication						[239] IMPLICIT RoamingIndication OPTIONAL,
	-- O 6.5.2.br n
	senderIdentificationNumber				[103] IMPLICIT SenderIdentificationNumber OPTIONAL
	-- O 6.5.2.116 i
	}

-- QualificationDirective RETURN RESULT Parameters
-- Zero octets
QualificationDirectiveRes ::= [PRIVATE 18] SET {

}
-- 6.4.2.32 QualificationRequest

QualificationRequest ::= [PRIVATE 18] SET {
	electronicSerialNumber					[9] IMPLICIT ElectronicSerialNumber,
	-- M 6.5.2.63
--	mobileIdentificationNumber				[8] IMPLICIT MobileIdentificationNumber,
	-- M 6.5.2.81
	msid									MSID OPTIONAL,
	-- M 6.5.2.bu c
	qualificationInformationCode			[17] IMPLICIT QualificationInformationCode,
	-- M 6.5.2.99
	systemMyTypeCode						[22] IMPLICIT SystemMyTypeCode,
	-- (MSC or VLR) M 6.5.2.147
	locationAreaID							[33] IMPLICIT LocationAreaID OPTIONAL,
	-- O 6.5.2.77 c
	cdmaNetworkIdentification				[232] IMPLICIT CDMANetworkIdentification OPTIONAL,
	-- (Serving) O 6.5.2.bk d
	controlChannelMode						[199] IMPLICIT ControlChannelMode OPTIONAL,
	-- O 6.5.2.ac e
	mscid									[21] IMPLICIT MSCID OPTIONAL,
	-- (Serving MSC or Originating MSC) O 6.5.2.82 a
--	ReturnCause O 6.5.2.bp f
	senderIdentificationNumber				[103] IMPLICIT SenderIdentificationNumber OPTIONAL,
	-- O 6.5.2.116 b
	systemAccessType						[34] IMPLICIT SystemAccessType OPTIONAL,
	-- O 6.5.2.145 a
	terminalType							[47] IMPLICIT TerminalType OPTIONAL,
	-- O 6.5.2.154 e
	transactionCapability					[123] IMPLICIT TransactionCapability OPTIONAL,
	-- O 6.5.2.160 a
	winCapability							[280] IMPLICIT WINCapability OPTIONAL,
	-- O 6.5.2.di c
	nonPublicData							[200] IMPLICIT NonPublicData OPTIONAL,
	-- O 6 .5.2.a d
	userZoneData							[209] IMPLICIT UserZoneData OPTIONAL,
	-- O 6 .5.2.am e
	meid									[390] IMPLICIT MEID OPTIONAL
	-- O
	}

-- QualificationRequest RETURN RESULT Parameters
QualificationRequestRes ::= [PRIVATE 18] SET {
	systemMyTypeCode						[22] IMPLICIT SystemMyTypeCode,
	-- (VLR or HLR) M 6.5.2.147
	analogRedirectRecord						[225] IMPLICIT AnalogRedirectRecord OPTIONAL,
	-- O 6.5.2.bc
	authorizationDenied						[13] IMPLICIT AuthorizationDenied OPTIONAL,
	-- O 6.5.2.13 a
	authorizationPeriod						[14] IMPLICIT AuthorizationPeriod OPTIONAL,
	-- O 6.5.2.14 b
	cdmaRedirectRecord						[229] IMPLICIT CDMARedirectRecord OPTIONAL,
	-- O 6.5.2.bh
	controlChannelMode						[199] IMPLICIT ControlChannelMode OPTIONAL,
	-- O 6 .5.2.ac h
	deniedAuthorizationPeriod					[167] IMPLICIT DeniedAuthorizationPeriod OPTIONAL,
	-- O 6.5.2.53 c
	digits-carrier 							[4] IMPLICIT Digits OPTIONAL,
	-- (Carrier) O 6.5.2.58 d
	digits-dest 							[4] IMPLICIT Digits OPTIONAL,
	-- (Destination) O 6.5.2.58 e
	mscid								[21] IMPLICIT MSCID OPTIONAL,
	-- (HLR) O 6.5.2.82 f
--	Profile **Macro** O 6.5.2.97 g	
	authenticationCapability					[78] IMPLICIT AuthenticationCapability OPTIONAL,
	-- O 6.5.2.8 a
	callingFeaturesIndicator					[25] IMPLICIT CallingFeaturesIndicator OPTIONAL,
	-- O 6.5.2.20 b
	carrierDigits							[86] IMPLICIT CarrierDigits OPTIONAL,
	-- O 6.5.2.28 c
	cdmaServiceOptionList						[176] IMPLICIT CDMAServiceOptionList OPTIONAL,
	-- O 6.5.2.g f, g
	controlNetworkID						[307] IMPLICIT ControlNetworkID OPTIONAL,
	-- O 6.5.2.ek u
	dmh-AccountCodeDigits						[140] IMPLICIT DMH-AccountCodeDigits OPTIONAL,
	-- O 6.5.2.59 d
	dmh-AlternateBillingDigits					[141] IMPLICIT DMH-AlternateBillingDigits OPTIONAL,
	-- O 6.5.2.60 d
	dmh-BillingDigits						[142] IMPLICIT DMH-BillingDigits OPTIONAL,
	-- O 6.5.2.61 d
	geographicAuthorization						[143] IMPLICIT GeographicAuthorization OPTIONAL,
	-- O 6.5.2.68 e
	meidValidated							[401] IMPLICIT MEIDValidated OPTIONAL,
	-- O 3.2.2.98
	messageWaitingNotificationCount					[92] IMPLICIT MessageWaitingNotificationCount OPTIONAL,
	-- O 6.5.2.78 f
	messageWaitingNotificationType					[145] IMPLICIT MessageWaitingNotificationType OPTIONAL,
	-- O 6.5.2.79 g
	mobileDirectoryNumber						[93] IMPLICIT MobileDirectoryNumber OPTIONAL,
	--  O 6.5.2.80 d
	mobilePositionCapability					[335] IMPLICIT MobilePositionCapability OPTIONAL,
	-- O 6.5.2.fm t TIA/EIA/J-STD-036-A
	originationIndicator						[23] IMPLICIT OriginationIndicator OPTIONAL,
	-- O 6.5.2.89 h
	originationTriggers						[98] IMPLICIT OriginationTriggers OPTIONAL,
	-- O 6.5.2.90 i
	pACAIndicator							[146] IMPLICIT PACAIndicator OPTIONAL,
	-- O 6.5.2.91 j
	preferredLanguageIndicator					[147] IMPLICIT PreferredLanguageIndicator OPTIONAL,
	-- O 6.5.2.96 k
	restrictionDigits						[227] IMPLICIT RestrictionDigits OPTIONAL,
	-- O 6.5.2.113 l
	routingDigits							[150] IMPLICIT RoutingDigits OPTIONAL,
	-- O 6.5.2.114 m
	sms-OriginationRestrictions					[115] IMPLICIT SMS-OriginationRestrictions OPTIONAL,
	-- O 6.5.2.136 n
	sms-TerminationRestrictions					[117] IMPLICIT SMS-TerminationRestrictions OPTIONAL,
	-- O 6.5.2.138 o
	spinipin							[154] IMPLICIT SPINIPIN OPTIONAL,
	-- O 6.5.2.139 p
	spiniTriggers							[155] IMPLICIT SPINITriggers OPTIONAL,
	-- O 6.5.2.140 q
	terminationRestrictionCode					[24] IMPLICIT TerminationRestrictionCode OPTIONAL,
	-- O 6.5.2.157 r
	terminationTriggers						[122] IMPLICIT TerminationTriggers OPTIONAL,
	-- O 6.5.2.159 s
	triggerAddressList						[276] IMPLICIT TriggerAddressList OPTIONAL,
	-- O 6.5.2.de t
	callingPartyCategory						[355] IMPLICIT CallingPartyCategory OPTIONAL,
	-- O 6.5.2.gl z
	lirMode								[369] IMPLICIT LIRMode OPTIONAL,
	-- O 6.5.2.gz z
-- END MACRO
	serviceRedirectionInfo						[238] IMPLICIT ServiceRedirectionInfo OPTIONAL,
	-- O 6.5.2.bq h, i
	roamingIndication						[239] IMPLICIT RoamingIndication OPTIONAL
	-- O 6.5.2.br
	}

-- 6.4.2.33 RandomVariableRequest
RandomVariableRequest ::= [PRIVATE 18] SET {
	mscid								[21] IMPLICIT MSCID,
	-- (Serving MSC) M 6.5.2.82
	randc								[67] IMPLICIT RANDC,
	-- M 6.5.2.100
	servingCellID							[2] IMPLICIT ServingCellID
	-- M 6.5.2.117
	}

-- RandomVariableRequest RETURN RESULT Parameters
RandomVariableRequestRes ::= [PRIVATE 18] SET {
	randomVariable							[40] IMPLICIT RandomVariable OPTIONAL,
	-- O 6.5.2.101 a
	randValidTime							[148] IMPLICIT RANDValidTime
	-- O 6.5.2.105 a
	}

-- 6.4.2.34 RedirectionDirective
RedirectionDirective ::= [PRIVATE 18] SET {
	billingID							[1] IMPLICIT BillingID,
	-- (Originating) M 6.5.2.16
	digits-dest 							[4] IMPLICIT Digits OPTIONAL,
	-- (Destination) M 6.5.2.58
	electronicSerialNumber						[9] IMPLICIT ElectronicSerialNumber,
	-- M 6.5.2.63
	mobileIdentificationNumber					[8] IMPLICIT MobileIdentificationNumber,
	-- M 6.5.2.81
	systemMyTypeCode						[22] IMPLICIT SystemMyTypeCode,
	-- (MSC) M 6.5.2.147
	digits-carrier 							[4] IMPLICIT Digits OPTIONAL,
	-- (Carrier) O 6.5.2.58 a
	dmh-AccountCodeDigits						[140] IMPLICIT DMH-AccountCodeDigits OPTIONAL,
	-- O 6.5.2.59 b
	dmh-AlternateBillingDigits					[141] IMPLICIT DMH-AlternateBillingDigits OPTIONAL,
	-- O 6.5.2.60 b
	dmh-BillingDigits						[142] IMPLICIT DMH-BillingDigits OPTIONAL,
	-- O 6.5.2.61 d
	mSCIdentificationNumber						[94] IMPLICIT MSCIdentificationNumber OPTIONAL,
	--O 6.5.2.83 c
	redirectingNumberString						[101] IMPLICIT RedirectingNumberString OPTIONAL,
	-- O 6.5.2.108 d
	redirectingSubaddress						[102] IMPLICIT RedirectingSubaddress OPTIONAL,
	-- O 6.5.2.109 d
	senderIdentificationNumber					[103] IMPLICIT SenderIdentificationNumber OPTIONAL
	-- O 6.5.2.116 e	
	}

-- RedirectionDirective RETURN RESULT Parameters
-- zero octets

-- 6.4.2.35 RedirectionRequest
RedirectionRequest ::= [PRIVATE 18] SET {
	billingID								[1] IMPLICIT BillingID,
	-- (Originating) M 6.5.2.16
	electronicSerialNumber					[9] IMPLICIT ElectronicSerialNumber,
	-- M 6.5.2.63
--	mobileIdentificationNumber				[8] IMPLICIT MobileIdentificationNumber,
	-- M 6.5.2.81
	msid									MSID,
	redirectionReason						[19] IMPLICIT RedirectionReason,
	-- M 6.5.2.110
	cdmaServiceOption						[175] IMPLICIT CDMAServiceOption OPTIONAL,
	-- O 6.5.2.f
	legInformation							[144] IMPLICIT LegInformation OPTIONAL,
	-- O 6.5.2.75 a
	mSCIdentificationNumber					[94] IMPLICIT MSCIdentificationNumber OPTIONAL,
	-- O 6.5.2.83 b
	tdmaServiceCode							[178] IMPLICIT TDMAServiceCode OPTIONAL
	-- O 6.5.2.i
	}
-- RedirectionRequest RETURN RESULT Parameters
-- Zero octets

-- 6.4.2.36 RegistrationCancellation

RegistrationCancellation ::= [PRIVATE 18] SET {
	electronicSerialNumber					[9] IMPLICIT ElectronicSerialNumber,
	-- M 6.5.2.63
	mobileIdentificationNumber				[8] IMPLICIT MobileIdentificationNumber,
	-- M 6.5.2.81
	cancellationType						[85] IMPLICIT CancellationType OPTIONAL,
	-- O 6.5.2.27 a
	controlChannelData						[55] IMPLICIT ControlChannelData OPTIONAL,
	-- O 6.5.2.51 b
	receivedSignalQuality					[72] IMPLICIT ReceivedSignalQuality OPTIONAL,
	-- O 6.5.2.106 b
	senderIdentificationNumber				[103] IMPLICIT SenderIdentificationNumber OPTIONAL,
	-- O 6.5.2.116 c
	systemAccessData						[56] IMPLICIT SystemAccessData OPTIONAL
	-- O 6.5.2.144 b
	}
-- RegistrationCancellation RETURN RESULT Parameters

RegistrationCancellationRes ::= [PRIVATE 18] SET {
	callHistoryCount						[38] IMPLICIT CallHistoryCount OPTIONAL,
	-- O 6.5.2.18 a
	cancellationDenied						[57] IMPLICIT CancellationDenied OPTIONAL,
	-- O 6.5.2.26 b
	controlChannelData						[55] IMPLICIT ControlChannelData OPTIONAL,
	-- O 6.5.2.51 b
	receivedSignalQuality					[72] IMPLICIT ReceivedSignalQuality OPTIONAL,
	-- O 6.5.2.106 b
	sms-MessageWaitingIndicator				[118] IMPLICIT SMS-MessageWaitingIndicator OPTIONAL,
	-- O 6.5.2.129 c
	systemAccessData						[56] IMPLICIT SystemAccessData OPTIONAL
	-- O 6.5.2.144 b
	}

-- 6.4.2.37 RegistrationNotification
-- RegistrationNotification INVOKE Parameters

RegistrationNotification ::= [PRIVATE 18] SET {
	electronicSerialNumber						[9] IMPLICIT ElectronicSerialNumber,
	-- M 6.5.2.63
--	mobileIdentificationNumber					[8] IMPLICIT MobileIdentificationNumber,
	-- M 6.5.2.81
	msid								MSID OPTIONAL,
	-- M 6.5.2.bu
	meid								[390] IMPLICIT MEID OPTIONAL,
	--
	mscid								[21] IMPLICIT MSCID,
	--(Serving MSC) M 6.5.2.82
	qualificationInformationCode					[17] IMPLICIT QualificationInformationCode,
	-- M 6.5.2.99
	systemMyTypeCode						[22] IMPLICIT SystemMyTypeCode,
	-- (Serving MSC or VLR) M 6.5.2.147
	availabilityType						[90] IMPLICIT AvailabilityType OPTIONAL,
	-- O 6.5.2.15 a
	borderCellAccess						[58] IMPLICIT BorderCellAccess OPTIONAL,
	-- O 6.5.2.17 b
	cdmaNetworkIdentification					[232] IMPLICIT CDMANetworkIdentification OPTIONAL,
	-- (Serving) O 6.5.2.bk
	controlChannelData						[55] IMPLICIT ControlChannelData OPTIONAL,
	-- O 6.5.2.51 b
	controlChannelMode						[199] IMPLICIT ControlChannelMode OPTIONAL,
	-- O 6 .5.2.ac h
	extendedMSCID							[53] IMPLICIT ExtendedMSCID OPTIONAL,
	-- (VLR) O 6.5.2.64 c
	locationAreaID							[33] IMPLICIT LocationAreaID OPTIONAL,
	-- O 6.5.2.77 d
	msc-Address							[284] IMPLICIT MSC-Address OPTIONAL,
	-- O 6.5.2.dnC l
	mSCIdentificationNumber						[94] IMPLICIT MSCIdentificationNumber OPTIONAL,
	-- O 2.152 t
	pc-ssn								[32] IMPLICIT PC-SSN OPTIONAL,
	--(Serving MSC or VLR) O 6.5.2.93 e
	receivedSignalQuality						[72] IMPLICIT ReceivedSignalQuality OPTIONAL,
	-- O 6.5.2.106 b
	reportType							[44] IMPLICIT ReportType OPTIONAL,
	-- O 6.5.2.112 f
	serviceRedirectionCause						[237] IMPLICIT ServiceRedirectionCause OPTIONAL,
	-- O 6.5.2.bp
	senderIdentificationNumber					[103] IMPLICIT SenderIdentificationNumber OPTIONAL,
	-- O 6.5.2.116 g
	sms-Address							[104] IMPLICIT	SMS-Address OPTIONAL,
	-- O 6.5.2.123 h
	sms-MessageWaitingIndicator					[118] IMPLICIT SMS-MessageWaitingIndicator OPTIONAL,
	-- O 6.5.2.129 i
	systemAccessData						[56] IMPLICIT SystemAccessData OPTIONAL,
	-- O 6.5.2.144 b
	systemAccessType						[34] IMPLICIT SystemAccessType OPTIONAL,
	-- O 6.5.2.145 j
	systemCapabilities						[49] IMPLICIT SystemCapabilities OPTIONAL,
	-- O 6.5.2.146 k
	terminalType							[47] IMPLICIT TerminalType OPTIONAL,
	-- O 6.5.2.154 j
	transactionCapability						[123] IMPLICIT TransactionCapability OPTIONAL,
	-- O 6.5.2.160 j
	winCapability							[280] IMPLICIT WINCapability OPTIONAL,
	-- O 6.5.2.di l
	...,
	mpcAddress							[370] IMPLICIT MPCAddress OPTIONAL,
	-- O 6.5.2.ha z, ab
	mpcAddressList							[381] IMPLICIT MPCAddressList OPTIONAL
	-- O 6.5.2.hm aa, ab	
	}
-- RegistrationNotification RETURN RESULT Parameters
RegistrationNotificationRes ::= [PRIVATE 18] SET {
	systemMyTypeCode						[22] IMPLICIT SystemMyTypeCode,
	-- (VLR or HLR) M 6.5.2.147
	analogRedirectRecord						[225] IMPLICIT AnalogRedirectRecord OPTIONAL,
	-- O 6.5.2.bd
	authorizationDenied						[13] IMPLICIT AuthorizationDenied OPTIONAL,
	-- O 6.5.2.13 a
	authorizationPeriod						[14] IMPLICIT AuthorizationPeriod OPTIONAL,
	-- O 6.5.2.14 b
	cdmaRedirectRecord						[229] IMPLICIT CDMARedirectRecord OPTIONAL,
	-- O 6.5.2.bh
	controlChannelData						[55] IMPLICIT ControlChannelData OPTIONAL,
	-- O 6.5.2.51 c
	deniedAuthorizationPeriod				[167] IMPLICIT DeniedAuthorizationPeriod OPTIONAL,
	-- O 6.5.2.53 d
	digits-Carrier	 						[4] IMPLICIT Digits OPTIONAL,
	--(Carrier) O 6.5.2.58 e
	digits-Destination						[4] IMPLICIT Digits OPTIONAL,
	-- (Destination) O 6.5.2.58 f
	mscid									[21] IMPLICIT MSCID OPTIONAL,
	--(HLR) O 6.5.2.82 g
	msid									MSID OPTIONAL,
	-- O 6.5.2.bu
--Profile **Macro** O 6.5.2.97 h
	authenticationCapability				[78] IMPLICIT AuthenticationCapability OPTIONAL,
	-- O 6.5.2.8 a
	callingFeaturesIndicator				[25] IMPLICIT CallingFeaturesIndicator OPTIONAL,
	-- O 6.5.2.20 b
	carrierDigits							[86] IMPLICIT CarrierDigits OPTIONAL,
	-- O 6.5.2.28 c
	cdmaServiceOptionList					[176] IMPLICIT CDMAServiceOptionList OPTIONAL,
	-- O 6.5.2.g d
	controlNetworkID						[307] IMPLICIT ControlNetworkID OPTIONAL,
	-- O 6.5.2.ek u
	dmh-AccountCodeDigits					[140] IMPLICIT DMH-AccountCodeDigits OPTIONAL,
	-- O 6.5.2.59 d
	dmh-AlternateBillingDigits				[141] IMPLICIT DMH-AlternateBillingDigits OPTIONAL,
	-- O 6.5.2.60 d
	dmh-BillingDigits						[142] IMPLICIT DMH-BillingDigits OPTIONAL,
	-- O 6.5.2.61 d
	geographicAuthorization					[143] IMPLICIT GeographicAuthorization OPTIONAL,
	-- O 6.5.2.68 e
	meidValidated							[401] IMPLICIT MEIDValidated OPTIONAL,
	-- O 3.2.2.98
	messageWaitingNotificationCount			[92] IMPLICIT MessageWaitingNotificationCount OPTIONAL,
	-- O 6.5.2.78 f
	messageWaitingNotificationType			[145] IMPLICIT MessageWaitingNotificationType OPTIONAL,
	-- O 6.5.2.79 g
	mobileDirectoryNumber					[93] IMPLICIT MobileDirectoryNumber OPTIONAL,
	--  O 6.5.2.80 d
	mobilePositionCapability				[335] IMPLICIT MobilePositionCapability OPTIONAL,
	-- O 6.5.2.fm t TIA/EIA/J-STD-036-A
	originationIndicator					[23] IMPLICIT OriginationIndicator OPTIONAL,
	-- O 6.5.2.89 h
	originationTriggers						[98] IMPLICIT OriginationTriggers OPTIONAL,
	-- O 6.5.2.90 i
	pACAIndicator							[146] IMPLICIT PACAIndicator OPTIONAL,
	-- O 6.5.2.91 j
	preferredLanguageIndicator				[147] IMPLICIT PreferredLanguageIndicator OPTIONAL,
	-- O 6.5.2.96 k
	qosPriority								[348] IMPLICIT QoSPriority OPTIONAL,
	--6.5.2.ge z
	restrictionDigits						[227] IMPLICIT RestrictionDigits OPTIONAL,
	-- O 6.5.2.113 l
	routingDigits							[150] IMPLICIT RoutingDigits OPTIONAL,
	-- O 6.5.2.114 m
	pSID-RSIDList							[203] IMPLICIT PSID-RSIDList OPTIONAL,
	-- O 6 .5.2.ag u , w
	sms-OriginationRestrictions				[115] IMPLICIT SMS-OriginationRestrictions OPTIONAL,
	-- O 6.5.2.136 n
	sms-TerminationRestrictions				[117] IMPLICIT SMS-TerminationRestrictions OPTIONAL,
	-- O 6.5.2.138 o
	spinipin								[154] IMPLICIT SPINIPIN OPTIONAL,
	-- O 6.5.2.139 p
	spiniTriggers							[155] IMPLICIT SPINITriggers OPTIONAL,
	-- O 6.5.2.140 q
	tdmaDataFeaturesIndicator				[221] IMPLICIT TDMADataFeaturesIndicator OPTIONAL,
	-- O 6.5.2.az s
	terminationRestrictionCode				[24] IMPLICIT TerminationRestrictionCode OPTIONAL,
	-- O 6.5.2.157 r
	terminationTriggers						[122] IMPLICIT TerminationTriggers OPTIONAL,
	-- O 6.5.2.159 s
	triggerAddressList						[276] IMPLICIT TriggerAddressList OPTIONAL,
	-- O 6.5.2.de t
	userGroup								[208] IMPLICIT UserGroup OPTIONAL,
	-- O 6 .5.2.al p
	nonPublicData							[200] IMPLICIT NonPublicData OPTIONAL,
	-- O 6 .5.2.ad v
	userZoneData							[209] IMPLICIT UserZoneData OPTIONAL,
	-- O 6 .5.2.am v , w
	callingPartyCategory					[355] IMPLICIT CallingPartyCategory OPTIONAL,
	-- O 6.5.2.gl z
	lirMode									[369] IMPLICIT LIRMode OPTIONAL,
	-- O 6.5.2.gz z
-- END MACRO
	receivedSignalQuality					[72] IMPLICIT ReceivedSignalQuality OPTIONAL,
	-- O 6.5.2.106 c
	serviceRedirectionInfo					[238] IMPLICIT ServiceRedirectionInfo OPTIONAL,
	-- O 6.5.2.bq k, l
	roamingIndication						[239] IMPLICIT RoamingIndication OPTIONAL,
	-- O 6.5.2.br
	senderIdentificationNumber				[103] IMPLICIT SenderIdentificationNumber OPTIONAL,
	-- O 6.5.2.116 i
	sms-MessageWaitingIndicator				[118] IMPLICIT SMS-MessageWaitingIndicator OPTIONAL,
	-- O 6.5.2.129 j
	systemAccessData						[56] IMPLICIT SystemAccessData OPTIONAL
	-- O 6.5.2.144 c
	}

-- 6.4.2.38 RemoteUserInteractionDirective
RemoteUserInteractionDirective ::= [PRIVATE 18] SET {
	announcementList						[130] IMPLICIT AnnouncementList,
	-- M 6.5.2.6
	digitCollectionControl					[139] IMPLICIT DigitCollectionControl
	-- M 6.5.2.57
	}

-- RemoteUserInteractionDirective RETURN RESULT Parameters
RemoteUserInteractionDirectiveRes ::= [PRIVATE 18] SET {
	digits		 							[4] IMPLICIT Digits OPTIONAL
	-- (Dialed) O 6.5.2.58 a
	}

-- 6.4.2.39 ResetCircuit
ResetCircuit ::= [PRIVATE 18] SET {
	interMSCCircuitID						[6] IMPLICIT	InterMSCCircuitID
	-- M 6.5.2.72
	}
-- ResetCircuit RETURN RESULT Parameters
ResetCircuitRes ::= [PRIVATE 18] SET {
	trunkStatus								[16] IMPLICIT TrunkStatus
	-- M 6.5.2.161
	}

-- 6.4.2.40 RoutingRequest
RoutingRequest ::= [PRIVATE 18] SET {
	billingID								[1] IMPLICIT BillingID,
	-- (Originating) M 6.5.2.16 a
	electronicSerialNumber					[9] IMPLICIT ElectronicSerialNumber,
	-- M 6.5.2.63
	mscid									[21] IMPLICIT MSCID,
	-- (Originating MSC) M 6.5.2.82
	systemMyTypeCode						[22] IMPLICIT SystemMyTypeCode,
	-- (Originating MSC) M 6.5.2.147
	alertCode								[75] IMPLICIT AlertCode OPTIONAL,
	-- O 6.5.2.3 b
	callingPartyName						[243] IMPLICIT CallingPartyName OPTIONAL,
	-- O 6.5.2.bw r, u, v
	callingPartyNumberDigits1				[80] IMPLICIT CallingPartyNumberDigits1 OPTIONAL,
	-- O 6.5.2.21 c, t	
	callingPartyNumberDigits2				[81] IMPLICIT CallingPartyNumberDigits2 OPTIONAL,
	-- O 6.5.2.22 c, t	
	callingPartyNumberString1				[82] IMPLICIT CallingPartyNumberString1 OPTIONAL,
	-- O 6.5.2.23 c
	callingPartyNumberString2				[83] IMPLICIT CallingPartyNumberString2 OPTIONAL,
	--, O 6.5.2.24 c
	callingPartySubaddress					[84] IMPLICIT CallingPartySubaddress OPTIONAL,
	-- O 6.5.2.25 c
	cdmaServiceOption						[175] IMPLICIT CDMAServiceOption OPTIONAL,
	-- O 6.5.2.f
	controlChannelMode						[199] IMPLICIT ControlChannelMode OPTIONAL,
	-- O 6 .5.2.ac r
	destinationDigits						[87] IMPLICIT	DestinationDigits OPTIONAL,
	-- O 6.5.2.56 d, e
	displayText								[244] IMPLICIT DisplayText OPTIONAL,
	-- O 6.5.2.bx d, e, p
	displayText2							[299] IMPLICIT DisplayText2 OPTIONAL,
	-- O 6.5.2.ec d, e, p
	dmh-AccountCodeDigits					[140] IMPLICIT DMH-AccountCodeDigits OPTIONAL,
	-- O 6.5.2.59 f
	dmh-AlternateBillingDigits				[141] IMPLICIT DMH-AlternateBillingDigits OPTIONAL,
	-- O 6.5.2.60 f
	dmh-BillingDigits						[142] IMPLICIT DMH-BillingDigits OPTIONAL,
	-- O 6.5.2.61 f
	legInformation							[144] IMPLICIT LegInformation OPTIONAL,
	-- O 6.5.2.75 g
	locationAreaID							[33] IMPLICIT LocationAreaID OPTIONAL,
	-- O 6.5.2.77 f, h
	mobileDirectoryNumber					[93] IMPLICIT MobileDirectoryNumber OPTIONAL,
	-- O 6.5.2.80 f
--	mobileIdentificationNumber				[8] IMPLICIT MobileIdentificationNumber,
	-- M 6.5.2.81
	msid									MSID,
	mSCIdentificationNumber					[94] IMPLICIT MSCIdentificationNumber OPTIONAL,
	-- O 6.5.2.83 i
	noAnswerTime							[96] IMPLICIT NoAnswerTime OPTIONAL,
	-- O 6.5.2.87 j
	oneTimeFeatureIndicator					[97] IMPLICIT OneTimeFeatureIndicator OPTIONAL,
	--  O 6.5.2.88 k
	pc-ssn									[32] IMPLICIT PC-SSN OPTIONAL,
	-- (Originating MSC) O 6.5.2.93 l
	pilotBillingID							[169] IMPLICIT PilotBillingID OPTIONAL,
	-- O 6.5.2.94 m
	pilotNumber								[168] IMPLICIT PilotNumber OPTIONAL,
	-- O 6.5.2.95 m
	redirectingNumberDigits					[100] IMPLICIT RedirectingNumberDigits OPTIONAL,
	-- OO 6.5.2.107 c, t
	redirectingNumberString					[101] IMPLICIT RedirectingNumberString OPTIONAL,
	-- O 6.5.2.108 c
	redirectingPartyName					[245] IMPLICIT RedirectingPartyName OPTIONAL,
	-- O 6.5.2.by s, u, v
	redirectingSubaddress					[102] IMPLICIT RedirectingSubaddress OPTIONAL,
	-- O 6.5.2.109 c
	senderIdentificationNumber				[103] IMPLICIT SenderIdentificationNumber OPTIONAL,
	-- O 6.5.2.116 n
	tdmaServiceCode							[178] IMPLICIT TDMAServiceCode OPTIONAL,
	-- O 6.5.2.i
	terminationTreatment					[121] IMPLICIT TerminationTreatment OPTIONAL,
	-- O 6.5.2.158 o
	terminationTriggers						[122] IMPLICIT TerminationTriggers OPTIONAL,
	-- O 6.5.2.159 f
	triggerAddressList						[276] IMPLICIT TriggerAddressList OPTIONAL,
	-- O 6.5.2.de u
	userGroup								[208] IMPLICIT UserGroup OPTIONAL,
	-- O 6 .5.2.al s
	transactionCapability					[123] IMPLICIT TransactionCapability OPTIONAL,
	-- (Originating MSC) O M 6.5.2.160
	voiceMailboxNumber						[160] IMPLICIT VoiceMailboxNumber OPTIONAL,
	-- O 6.5.2.164 p
	voiceMailboxPIN							[159] IMPLICIT VoiceMailboxPIN OPTIONAL
	-- O 6.5.2.165 q
	}

-- RoutingRequest RETURN RESULT Parameters
RoutingRequestRes ::= [PRIVATE 18] SET {
	mscid									[21] IMPLICIT MSCID,
	-- (Serving) M 6.5.2.82
	accessDeniedReason						[20] IMPLICIT AccessDeniedReason OPTIONAL,
	-- O 6.5.2.1 a
	billingID								[1] IMPLICIT BillingID OPTIONAL,
	-- (Anchor) O 6.5.2.16 b
	cdmaServiceOption						[175] IMPLICIT CDMAServiceOption OPTIONAL,
	-- O 6.5.2.f
	conditionallyDeniedReason				[162] IMPLICIT ConditionallyDeniedReason OPTIONAL,
	-- O 6.5.2.48 c
	digits-Destination						[4] IMPLICIT Digits OPTIONAL,
	-- (Destination) O 6.5.2.58 d
	mSCIdentificationNumber					[94] IMPLICIT MSCIdentificationNumber OPTIONAL,
	-- O 6.5.2.83 e
	pc-ssn									[32] IMPLICIT PC-SSN OPTIONAL,
	-- (Serving MSC) O 6.5.2.93 f
	tdmaServiceCode							[178] IMPLICIT TDMAServiceCode OPTIONAL
	-- O 6.5.2.i
	}

-- 6.4.2.41 SMSDeliveryBackward
SMSDeliveryBackward ::= [PRIVATE 18] SET {
	interMSCCircuitID						[6] IMPLICIT	InterMSCCircuitID,
	-- M 6.5.2.72
	mobileIdentificationNumber				[8] IMPLICIT MobileIdentificationNumber,
	-- M 6.5.2.81 a
	sms-BearerData							[105] IMPLICIT SMS-BearerData,
	-- M 6.5.2.124
	sms-TeleserviceIdentifier				[116] IMPLICIT SMS-TeleserviceIdentifier,
	--M 6.5.2.137
	electronicSerialNumber					[9] IMPLICIT ElectronicSerialNumber OPTIONAL,
	-- O 6.5.2.63 b
	sms-ChargeIndicator						[106] IMPLICIT SMS-ChargeIndicator OPTIONAL,
	-- O 6.5.2.126 c
	sms-DestinationAddress					[107] IMPLICIT SMS-DestinationAddress OPTIONAL,
	-- O 6.5.2.127 d
	sms-OriginalDestinationAddress			[110] IMPLICIT SMS-OriginalDestinationAddress OPTIONAL,
	-- O 6.5.2.131 e
	sms-OriginalDestinationSubaddress		[111] IMPLICIT SMS-OriginalDestinationSubaddress OPTIONAL,
	-- O 6.5.2.132 b
	sms-OriginalOriginatingAddress			[112] IMPLICIT SMS-OriginalOriginatingAddress OPTIONAL,
	-- O 6.5.2.133 f
	sms-OriginalOriginatingSubaddress		[113] IMPLICIT SMS-OriginalOriginatingSubaddress OPTIONAL,
	-- O 6.5.2.134 b
	sms-OriginatingAddress					[114] IMPLICIT SMS-OriginatingAddress OPTIONAL
	-- O 6.5.2.135 g
	}

-- SMSDeliveryBackward RETURN RESULT Parameters
SMSDeliveryBackwardRes ::= [PRIVATE 18] SET {
	sms-BearerData							[105] IMPLICIT SMS-BearerData OPTIONAL,
	-- O 6.5.2.124 a
	sms-CauseCode							[153] IMPLICIT SMS-CauseCode OPTIONAL
	-- O 6.5.2.125 b
	}


-- 6.4.2.42 SMSDeliveryForward
SMSDeliveryForward ::= [PRIVATE 18] SET {
	interMSCCircuitID						[6] IMPLICIT	InterMSCCircuitID,
	-- M 6.5.2.72
	mobileIdentificationNumber				[8] IMPLICIT MobileIdentificationNumber,
	-- M 6.5.2.81 a
	sms-BearerData							[105] IMPLICIT SMS-BearerData,
	-- M 6.5.2.124
	sms-TeleserviceIdentifier				[116] IMPLICIT SMS-TeleserviceIdentifier,
	-- M 6.5.2.137
	electronicSerialNumber					[9] IMPLICIT ElectronicSerialNumber,
	-- O 6.5.2.63 b
	sms-ChargeIndicator						[106] IMPLICIT SMS-ChargeIndicator OPTIONAL,
	-- O 6.5.2.126 c
	sms-DestinationAddress					[107] IMPLICIT SMS-DestinationAddress OPTIONAL,
	--O 6.5.2.127 d
	sms-OriginalDestinationAddress			[110] IMPLICIT SMS-OriginalDestinationAddress OPTIONAL,
	-- O 6.5.2.131 e
	sms-OriginalDestinationSubaddress		[111] IMPLICIT SMS-OriginalDestinationSubaddress OPTIONAL,
	-- O 6.5.2.132 b
	sms-OriginalOriginatingAddress			[112] IMPLICIT SMS-OriginalOriginatingAddress OPTIONAL,
	-- O 6.5.2.133 f
	sms-OriginalOriginatingSubaddress		[113] IMPLICIT SMS-OriginalOriginatingSubaddress OPTIONAL,
	--  O 6.5.2.134 b
	sms-OriginatingAddress					[114] IMPLICIT SMS-OriginatingAddress OPTIONAL
	-- O 6.5.2.135 g
	}

-- SMSDeliveryForward RETURN RESULT Parameters
SMSDeliveryForwardRes ::= [PRIVATE 18] SET {
	sms-BearerData							[105] IMPLICIT SMS-BearerData OPTIONAL,
	--, O 6.5.2.124 a
	sms-CauseCode							[153] IMPLICIT SMS-CauseCode OPTIONAL
	-- O 6.5.2.125 b
	}

-- N.S0005-0 v 1.0
-- 6.4.2.43 SMSDeliveryPointToPoint
SMSDeliveryPointToPoint ::= [PRIVATE 18] SET {
	sms-BearerData							[105] IMPLICIT SMS-BearerData,
	-- M 6.5.2.124
	sms-TeleserviceIdentifier				[116] IMPLICIT SMS-TeleserviceIdentifier,
	-- M 6.5.2.137
	actionCode								[128] IMPLICIT ActionCode OPTIONAL,
	-- O 6.5.2.2
	cdmaServingOneWayDelay2					[347] IMPLICIT	CDMAServingOneWayDelay2 OPTIONAL,
	-- O 6.5.2.gd n, r
	electronicSerialNumber					[9] IMPLICIT ElectronicSerialNumber OPTIONAL,
	-- O 6.5.2.63 a
	meid									[390] IMPLICIT MEID OPTIONAL,
	--  O 6.5.2.hv
	interMessageTime						[325] IMPLICIT InterMessageTime OPTIONAL,
	-- O 6.5.2.fd
--	mobileIdentificationNumber				[8] IMPLICIT MobileIdentificationNumber OPTIONAL,
	-- O 6.5.2.81 a
	-- Exchanged by MSID
	mscid									[21] IMPLICIT MSCID OPTIONAL,
	-- O 6.5.2.82 f
--	msid									MSID OPTIONAL,
	imsi									[242] IMPLICIT IMSI OPTIONAL,
	mobileIdentificationNumber				[8] IMPLICIT MobileIdentificationNumber OPTIONAL,
	--6.5.2.bv
	newlyAssignedIMSI						[287] IMPLICIT NewlyAssignedIMSI OPTIONAL,
	-- O 6.5.2.dqB j
	newlyAssignedMIN						[187] IMPLICIT NewlyAssignedMIN OPTIONAL,
	-- O 6.5.2.rB j
	newMINExtension							[328] IMPLICIT NewMINExtension OPTIONAL,
	-- O 6.5.2.ff n
	serviceIndicator						[193] IMPLICIT ServiceIndicator OPTIONAL,
	-- O 6.5.2.wB
	sms-ChargeIndicator						[106] IMPLICIT SMS-ChargeIndicator OPTIONAL,
	-- O 6.5.2.126 b
	sms-DestinationAddress					[107] IMPLICIT SMS-DestinationAddress OPTIONAL,
	-- O 6.5.2.127 c
	sms-MessageCount						[108] IMPLICIT SMS-MessageCount OPTIONAL,
	-- O 6.5.2.128 d
	sms-NotificationIndicator				[109] IMPLICIT SMS-NotificationIndicator OPTIONAL,
	-- O 6.5.2.130 e
	sms-OriginalDestinationAddress			[110] IMPLICIT SMS-OriginalDestinationAddress OPTIONAL,
	-- O 6.5.2.131 f
	sms-OriginalDestinationSubaddress		[111] IMPLICIT SMS-OriginalDestinationSubaddress OPTIONAL,
	-- O 6.5.2.132 g
	sms-OriginalOriginatingAddress			[112] IMPLICIT SMS-OriginalOriginatingAddress OPTIONAL,
	-- O 6.5.2.133 f
	sms-OriginalOriginatingSubaddress		[113] IMPLICIT SMS-OriginalOriginatingSubaddress OPTIONAL,
	--  O 6.5.2.134 b
	sms-OriginatingAddress					[114] IMPLICIT SMS-OriginatingAddress OPTIONAL,
	-- O 6.5.2.135 g
	teleservice-Priority					[290] IMPLICIT Teleservice-Priority OPTIONAL,
	-- O 6.5.2.dt
	temporaryReferenceNumber				[195] IMPLICIT TemporaryReferenceNumber OPTIONAL
	-- O 6.5.2.yC
	}

-- SMSDeliveryPointToPoint RETURN RESULT Parameters
SMSDeliveryPointToPointRes ::= [PRIVATE 18] SET {
	actionCode								[128] IMPLICIT ActionCode OPTIONAL,
	-- O 6.5.2.2 k
	authorizationDenied						[13] IMPLICIT AuthorizationDenied OPTIONAL,
	-- O 6.5.2.13 h
	denyAccess								[50] IMPLICIT DenyAccess OPTIONAL,
	-- O 6.5.2.54 c
	electronicSerialNumber					[9] IMPLICIT ElectronicSerialNumber OPTIONAL,
	-- O 6.5.2.63 d
	meid									[390] IMPLICIT MEID OPTIONAL,
	-- O 6.5.2.hv
	mobileStationMSID						MobileStationMSID OPTIONAL,
	-- O 6.5.2.oC e
	mscid									[21] IMPLICIT MSCID OPTIONAL,
	-- O 6.5.2.82 f
	servingCellID							[2]	IMPLICIT ServingCellID OPTIONAL,
	-- O 6.5.2.117 TIA/EIA/J-STD-036-A
	sms-BearerData							[105] IMPLICIT SMS-BearerData OPTIONAL,
	-- O 6.5.2.124 a
	sms-CauseCode							[153] IMPLICIT SMS-CauseCode OPTIONAL,
	-- O 6.5.2.125 b
	systemCapabilities						[49] IMPLICIT SystemCapabilities OPTIONAL
	-- O 6.5.2.146 g
	}
-- 2.65 SMSDeliveryPointToPointAck X.S0004-540-E v2.0
SMSDeliveryPointToPointAck ::= [PRIVATE 18] SET {
	interMSCCircuitID						[6] IMPLICIT	InterMSCCircuitID,
	-- M 2.129
	imsi									[242] IMPLICIT IMSI OPTIONAL,
	-- O 2.127 d
	msid									MSID OPTIONAL,
	-- MobileIdentificationNumber O 2.140 d ( exchanged for msid RAB).
	sms-BearerData							[105] IMPLICIT SMS-BearerData OPTIONAL,
	-- O 2.233 a
	sms-CauseCode							[153] IMPLICIT SMS-CauseCode OPTIONAL,
	-- O 2.234 b
	sms-TransactionID						[302] IMPLICIT SMS-TransactionID OPTIONAL
	-- O 2.248 c
}


-- 6.4.2.44 SMSNotification
SMSNotification ::= [PRIVATE 18] SET {
	electronicSerialNumber					[9] IMPLICIT ElectronicSerialNumber,
	-- M 6.5.2.63
--	mobileIdentificationNumber				[8] IMPLICIT MobileIdentificationNumber,
	-- M 6.5.2.81
	-- Exchanged by MCID
	msid									MSID OPTIONAL,
	--6.5.2.bv
	mobileDirectoryNumber					[93] IMPLICIT MobileDirectoryNumber OPTIONAL,
	-- O 6.5.2.80 f
	sms-AccessDeniedReason					[152] IMPLICIT SMS-AccessDeniedReason OPTIONAL,
	-- O 6.5.2.122 a
	sms-Address								[104] IMPLICIT SMS-Address OPTIONAL,
	-- O 6.5.2.123 a, b
	sms-TeleserviceIdentifier				[116] IMPLICIT SMS-TeleserviceIdentifier OPTIONAL,
	-- O 6.5.2.137
	meid									[390] IMPLICIT MEID OPTIONAL
	-- O
	}

-- SMSNotification RETURN RESULT Parameters
SMSNotificationRes ::= [PRIVATE 18] SET {
	sms-MessageCount						[108] IMPLICIT SMS-MessageCount OPTIONAL
	-- O 6.5.2.128
}

-- 6.4.2.45 SMSRequest
SMSRequest ::= [PRIVATE 18] SET {
--	mobileIdentificationNumber				[8] IMPLICIT MobileIdentificationNumber,
	-- M 6.5.2.81
	msid									MSID OPTIONAL,
	-- 6.5.2.bv e, f, g
	electronicSerialNumber					[9] IMPLICIT ElectronicSerialNumber OPTIONAL,
	-- O 6.5.2.63
	mobileDirectoryNumber					[93] IMPLICIT MobileDirectoryNumber OPTIONAL,
	-- O 6.5.2.80 e
	serviceIndicator						[193] IMPLICIT ServiceIndicator OPTIONAL,
	-- O 6.5.2.wB d
	-- O 6.5.2.63 a
	sms-NotificationIndicator				[109] IMPLICIT SMS-NotificationIndicator OPTIONAL,
	-- O 6.5.2.130 b
	sms-TeleserviceIdentifier				[116] IMPLICIT SMS-TeleserviceIdentifier OPTIONAL
	-- O 6.5.2.137 c
	}

-- SMSRequest RETURN RESULT Parameters
-- X.S0004-540-E v2.0
SMSRequestRes ::= [PRIVATE 18] SET {
	electronicSerialNumber					[9] IMPLICIT ElectronicSerialNumber OPTIONAL,
	-- O 6.5.2.63 a
	msid									MSID OPTIONAL,
	-- 6.5.2.bv
	sms-AccessDeniedReason					[152] IMPLICIT SMS-AccessDeniedReason OPTIONAL,
	-- O 6.5.2.122 b, c
	sms-Address								[104] IMPLICIT SMS-Address OPTIONAL,
	-- O 6.5.2.123 c, d
	sms-CauseCode							[153] IMPLICIT SMS-CauseCode OPTIONAL,
	-- O 6.5.2.125
	transactionCapability					[123] IMPLICIT TransactionCapability OPTIONAL
	-- O 2.285 f
	}

-- 6.4.2.46 TransferToNumberRequest Updated with N.S0023-0 v 1.0
TransferToNumberRequest ::= [PRIVATE 18] SET {
	electronicSerialNumber					[9] IMPLICIT ElectronicSerialNumber,
	-- M 6.5.2.63
	msid									MSID OPTIONAL,
	-- M 6.5.2.bv h
	mobileIdentificationNumber				[8] IMPLICIT MobileIdentificationNumber,
	-- M 6.5.2.81
	redirectionReason						[19] IMPLICIT RedirectionReason,
	-- M 6.5.2.110
	systemMyTypeCode						[22] IMPLICIT SystemMyTypeCode,
	-- (MSC) M 6.5.2.147
	acgencountered							[340] IMPLICIT ACGEncountered OPTIONAL,
	-- O 6.5.2.fv h
	billingID								[1] IMPLICIT BillingID OPTIONAL,
	-- (Originating) O 6.5.2.16 a
	callingPartyName						[243] IMPLICIT CallingPartyName OPTIONAL,
	-- O 6.5.2.bw r, u, v
	callingPartyNumberDigits1				[80] IMPLICIT CallingPartyNumberDigits1 OPTIONAL,
	-- O 6.5.2.21 c, t	
	callingPartyNumberDigits2				[81] IMPLICIT CallingPartyNumberDigits2 OPTIONAL,
	-- O 6.5.2.22 c, t	
	callingPartySubaddress					[84] IMPLICIT CallingPartySubaddress OPTIONAL,
	-- O 6.5.2.25 c
	cdmaServiceOption						[175] IMPLICIT CDMAServiceOption OPTIONAL,
	-- O 6.5.2.f
	groupInformation						[163] IMPLICIT GroupInformation OPTIONAL,
	-- O 6.5.2.69 b
	legInformation							[144] IMPLICIT LegInformation OPTIONAL,
	-- O 6.5.2.75 c
	mscid									[21] IMPLICIT MSCID OPTIONAL,
	-- (Originating) O 6.5.2.82 d
	mSCIdentificationNumber					[94] IMPLICIT MSCIdentificationNumber OPTIONAL,
	-- O 6.5.2.83 e
	pilotBillingID							[169] IMPLICIT PilotBillingID OPTIONAL,
	-- O 6.5.2.94 f
	pilotNumber								[168] IMPLICIT PilotNumber OPTIONAL,
	-- O 6.5.2.95 f
	senderIdentificationNumber				[103] IMPLICIT SenderIdentificationNumber OPTIONAL,
	-- O 6.5.2.116 g N.S.00013
	tdmaServiceCode							[178] IMPLICIT TDMAServiceCode OPTIONAL,
	-- O 6.5.2.i
	transactionCapability					[123] IMPLICIT TransactionCapability OPTIONAL,
	-- O 6.5.2.160 e
	winCapability							[280] IMPLICIT WINCapability OPTIONAL,
	-- O 6.5.2.di i
	meid									[390] IMPLICIT MEID OPTIONAL
	-- O
	}

-- TransferToNumberRequest RETURN RESULT Parameters
TransferToNumberRequestRes ::= [PRIVATE 18] SET {
	digits-Destination						[4] IMPLICIT Digits OPTIONAL,
	-- (Destination) M 6.5.2.58 a
	accessDeniedReason						[20] IMPLICIT AccessDeniedReason OPTIONAL,
	-- O 6.5.2.1 b
	actionCode								[128] IMPLICIT ActionCode OPTIONAL,
	-- O 6.5.2.2 c
	announcementList						[130] IMPLICIT AnnouncementList OPTIONAL,
	-- O 6.5.2.6 d
	callingPartyNumberString1				[82] IMPLICIT CallingPartyNumberString1 OPTIONAL,
	-- O 6.5.2.23 e
	callingPartyNumberString2				[83] IMPLICIT CallingPartyNumberString2 OPTIONAL,
	-- O 6.5.2.24 e
	callingPartySubaddress					[84] IMPLICIT CallingPartySubaddress OPTIONAL,
	-- O 6.5.2.25 e, f
	digits-Carrier	 						[4] IMPLICIT Digits OPTIONAL,
	-- (Carrier) O 6.5.2.58 g
	displayText								[244] IMPLICIT DisplayText OPTIONAL,
	-- O 6.5.2.bx d, e, p
	displayText2							[299] IMPLICIT DisplayText2 OPTIONAL,
	-- O 6.5.2.ec d, e, p
	dmh-AccountCodeDigits					[140] IMPLICIT DMH-AccountCodeDigits OPTIONAL,
	-- O 6.5.2.59 h
	dmh-AlternateBillingDigits				[141] IMPLICIT DMH-AlternateBillingDigits OPTIONAL,
	-- O 6.5.2.60 h
	dmh-BillingDigits						[142] IMPLICIT DMH-BillingDigits OPTIONAL,
	-- O 6.5.2.61 h
	dmh-RedirectionIndicator				[88] IMPLICIT DMH-RedirectionIndicator OPTIONAL,
	-- O 6.5.2.62 h
	dmh-ServiceID							[305] IMPLICIT DMH-ServiceID OPTIONAL,
	-- O 6.5.2.ei k
	groupInformation						[163] GroupInformation OPTIONAL,
	-- O 6.5.2.69 i
	mobileDirectoryNumber					[93] IMPLICIT MobileDirectoryNumber OPTIONAL,
	-- O 6.5.2.80 h
	noAnswerTime							[96] IMPLICIT NoAnswerTime OPTIONAL,
	-- O 6.5.2.87 g
	preferredLanguageIndicator				[147] IMPLICIT PreferredLanguageIndicator OPTIONAL,
	-- O 6.5.2.96 g, m
	redirectingNumberDigits					[100] IMPLICIT RedirectingNumberDigits OPTIONAL,
	-- O 6.5.2.107 f
	redirectingNumberString					[101] IMPLICIT RedirectingNumberString OPTIONAL,
	-- O 6.5.2.108 e
	redirectingSubaddress					[102] IMPLICIT RedirectingSubaddress OPTIONAL,
	-- O 6.5.2.109 e, f
	terminationList							[120] IMPLICIT TerminationList OPTIONAL,
	-- O 6.5.2.156 j
	terminationTriggers						[122] IMPLICIT TerminationTriggers OPTIONAL,
	-- O 6.5.2.159 g
	triggerAddressList						[276] IMPLICIT TriggerAddressList OPTIONAL
	-- O 6.5.2.de l
	}

-- 6.4.2.47 TrunkTest
TrunkTest ::= [PRIVATE 18] SET {
	interMSCCircuitID						[6] IMPLICIT	InterMSCCircuitID,
	-- M 6.5.2.72
	seizureType								[15] IMPLICIT SeizureType
	-- M 6.5.2.115
	}

-- TrunkTest RETURN RESULT Parameters
-- zero octets

-- 6.4.2.48 TrunkTestDisconnect
TrunkTestDisconnect ::= [PRIVATE 18] SET {
	interMSCCircuitID						[6] IMPLICIT	InterMSCCircuitID
	-- M 6.5.2.72
	}

-- TrunkTestDisconnect RETURN RESULT Parameters
-- zero octets

-- 6.4.2.49 Unblocking
Unblocking ::= [PRIVATE 18] SET {
	interMSCCircuitID						[6] IMPLICIT	InterMSCCircuitID
	-- M 6.5.2.72
	}

-- Unblocking RETURN RESULT Parameters
-- zero octets

-- 6.4.2.50 UnreliableRoamerDataDirective
UnreliableRoamerDataDirective ::= [PRIVATE 18] SET {
	mscid									[21] IMPLICIT MSCID OPTIONAL,
	-- (HLR) O 6.5.2.82 a
	senderIdentificationNumber				[103] IMPLICIT SenderIdentificationNumber OPTIONAL
	-- O 6.5.2.116 b	
	}
-- UnreliableRoamerDataDirective RETURN RESULT Parameters
-- zero octets

-- 6.4.2.51 UnsolicitedResponse
UnsolicitedResponse ::= [PRIVATE 18] SET {
	billingID								[1] IMPLICIT BillingID,
	-- (Anchor) M 6.5.2.16
	electronicSerialNumber					[9] IMPLICIT ElectronicSerialNumber,
	-- M 6.5.2.63
	mobileIdentificationNumber				[8] IMPLICIT MobileIdentificationNumber,
	-- M 6.5.2.81
	cdmaServiceOption						[175] IMPLICIT CDMAServiceOption OPTIONAL,
	-- O 6.5.2.f
	digits-Destination						[4] IMPLICIT Digits OPTIONAL,
	-- (Destination) O 6.5.2.58 a
	extendedMSCID							[53] IMPLICIT ExtendedMSCID OPTIONAL,
	-- (Border MSC) O 6.5.2.64 a
	extendedSystemMyTypeCode				[54] IMPLICIT ExtendedSystemMyTypeCode OPTIONAL,
	-- (Border MSC) O 6.5.2.65 a
	pc-ssn									[32] IMPLICIT PC-SSN OPTIONAL,
	-- (Border MSC) O 6.5.2.93 a, b
	systemAccessType						[34] IMPLICIT SystemAccessType OPTIONAL,
	-- O 6.5.2.145 c
	tdmaServiceCode							[178] IMPLICIT TDMAServiceCode OPTIONAL,
	-- O 6.5.2.i
	meid									[390] IMPLICIT MEID OPTIONAL
	-- O
	}

-- UnsolicitedResponse RETURN RESULT Parameters
UnsolicitedResponseRes ::= [PRIVATE 18] SET {
	accessDeniedReason						[20] IMPLICIT AccessDeniedReason OPTIONAL,
	-- O 6.5.2.1
	alertCode								[75] IMPLICIT AlertCode OPTIONAL,
	-- O 6.5.2.3 a
	billingID								[1] IMPLICIT BillingID OPTIONAL,
	-- (Originating) O 6.5.2.16 b
	callingPartyName						[243] IMPLICIT CallingPartyName OPTIONAL,
	-- O 6.5.2.bw g, i
	callingPartyNumberDigits1				[80] IMPLICIT CallingPartyNumberDigits1 OPTIONAL,
	-- O 6.5.2.21 d	
	callingPartyNumberDigits2				[81] IMPLICIT CallingPartyNumberDigits2 OPTIONAL,
	-- O 6.5.2.22 d
	callingPartyNumberString1				[82] IMPLICIT CallingPartyNumberString1 OPTIONAL,
	-- O 6.5.2.23 c
	callingPartyNumberString2				[83] IMPLICIT CallingPartyNumberString2 OPTIONAL,
	-- O 6.5.2.24 c
	callingPartySubaddress					[84] IMPLICIT CallingPartySubaddress OPTIONAL,
	-- O 6.5.2.25 c
	displayText								[244] IMPLICIT DisplayText OPTIONAL,
	-- O 6.5.2.bx d, e, p
	displayText2							[299] IMPLICIT DisplayText2 OPTIONAL,
	-- O 6.5.2.ec d, e, p
	dmh-AccountCodeDigits					[140] IMPLICIT DMH-AccountCodeDigits OPTIONAL,
	-- O 6.5.2.59 d
	dmh-AlternateBillingDigits				[141] IMPLICIT DMH-AlternateBillingDigits OPTIONAL,
	-- O 6.5.2.60 d
	dmh-BillingDigits						[142] IMPLICIT DMH-BillingDigits OPTIONAL,
	-- O 6.5.2.61 d
	extendedMSCID							[53] IMPLICIT ExtendedMSCID OPTIONAL,
	-- (Originating MSC) O 6.5.2.64 e
	extendedSystemMyTypeCode				[54] IMPLICIT ExtendedSystemMyTypeCode OPTIONAL,
	-- (Originating MSC) O 6.5.2.65 f
	legInformation							[144] IMPLICIT LegInformation OPTIONAL,
	-- O 6.5.2.75 g
	mobileDirectoryNumber					[93] IMPLICIT MobileDirectoryNumber OPTIONAL,
	-- O 6.5.2.80 d
	mSCIdentificationNumber					[94] IMPLICIT MSCIdentificationNumber OPTIONAL,
	-- (Origination MSC) O 6.5.2.83 g
	oneTimeFeatureIndicator					[97] IMPLICIT OneTimeFeatureIndicator OPTIONAL,
	--  O 6.5.2.88 g
	pc-ssn									[32] IMPLICIT PC-SSN OPTIONAL,
	-- (Originating MSC) O 6.5.2.93 h
	pilotBillingID							[169] IMPLICIT PilotBillingID OPTIONAL,
	-- O 6.5.2.94 g
	pilotNumber								[168] IMPLICIT PilotNumber OPTIONAL,
	-- O 6.5.2.95 g
	preferredLanguageIndicator				[147] IMPLICIT PreferredLanguageIndicator OPTIONAL,
	-- O 6.5.2.96 g
	redirectingNumberDigits					[100] IMPLICIT RedirectingNumberDigits OPTIONAL,
	-- O 6.5.2.107 d
	redirectingNumberString					[101] IMPLICIT RedirectingNumberString OPTIONAL,
	-- O 6.5.2.108 c
	redirectingPartyName					[245] IMPLICIT RedirectingPartyName OPTIONAL,
	-- O 6.5.2.by g, i
	redirectingSubaddress					[102] IMPLICIT RedirectingSubaddress OPTIONAL,
	-- O 6.5.2.109 c
	terminationTreatment					[121] IMPLICIT TerminationTreatment OPTIONAL,
	-- O 6.5.2.158 g
	terminationTriggers						[122] IMPLICIT TerminationTriggers OPTIONAL,
	-- O 6.5.2.159 g
	triggerAddressList						[276] IMPLICIT TriggerAddressList OPTIONAL
	-- O 6.5.2.de g
	}

-- N.S0010-0 v 1.0
-- 6.4.2.e ParameterRequest
ParameterRequest ::= [PRIVATE 18] SET {
	requiredParametersMask					[236] IMPLICIT RequiredParametersMask,
	-- M 6.5.2.j
	electronicSerialNumber					[9] IMPLICIT ElectronicSerialNumber OPTIONAL,
	-- O 6.5.2.63 a
	msid									MSID OPTIONAL,
	-- O 6.5.2.bu b
	mscid									[21] IMPLICIT MSCID OPTIONAL,
	--O 6.5.2.82 c
	networkTMSI								[233] IMPLICIT NetworkTMSI OPTIONAL,
	-- O 6.5.2.bl b
	pc-ssn									[32] IMPLICIT PC-SSN OPTIONAL,
	-- O 6.5.2.93 d
	senderIdentificationNumber				[103] IMPLICIT SenderIdentificationNumber OPTIONAL,
	-- O 6.5.2.116 e
	systemMyTypeCode						[22] IMPLICIT SystemMyTypeCode OPTIONAL
	-- O 6.5.2.147 f
	}
-- Table 6.4.2.e-2 ParameterRequest RETURN RESULT Parameters
ParameterRequestRes ::= [PRIVATE 18] SET {
	electronicSerialNumber					[9] IMPLICIT ElectronicSerialNumber OPTIONAL,
	-- O 6.5.2.63 a
	imsi									[242] IMPLICIT IMSI OPTIONAL,
	-- O 6.5.2.bu a
	locationAreaID							[33] IMPLICIT LocationAreaID OPTIONAL,
	-- O 6.5.2.77 a
	mobileIdentificationNumber				[8] IMPLICIT MobileIdentificationNumber OPTIONAL,
	-- O 6.5.2.81 a
	networkTMSI								[233] IMPLICIT NetworkTMSI OPTIONAL,
	-- O 6.5.2.bl a
	reasonList								[218] IMPLICIT ReasonList OPTIONAL
	-- O 6.5.2.aw
	}

-- 6.4.2.f TMSIDirective (N.S0005-0 v 1.0 Chapter 5, page 1
TMSIDirective ::= [PRIVATE 18] SET {
	electronicSerialNumber					[9] IMPLICIT ElectronicSerialNumber,
	-- M 6.5.2.63
	mscid									[21] IMPLICIT MSCID,
	-- M 6.5.2.bu
	networkTMSIExpirationTime				[234] IMPLICIT NetworkTMSIExpirationTime,
	-- M 6.5.2.bm
	newNetworkTMSI							[235] IMPLICIT NewNetworkTMSI,
	--M 6.5.2.bn
	locationAreaID							[33] IMPLICIT LocationAreaID OPTIONAL,
	-- O 6.5.2.83 a
	networkTMSI								[233] IMPLICIT NetworkTMSI OPTIONAL
	-- O 6.5.2.bl
	}

--Table 6.4.2.f-2 TMSIDirective RETURN RESULT Parameters
TMSIDirectiveRes ::= [PRIVATE 18] SET {
	denyAccess								[50] IMPLICIT DenyAccess OPTIONAL,
	-- O 6.5.2.54 b
	electronicSerialNumber					[9] IMPLICIT ElectronicSerialNumber OPTIONAL,
	-- O 6.5.2.63 b
	mscid									[21] IMPLICIT MSCID OPTIONAL,
	-- O 6.5.2.bu b
	reasonList								[218] IMPLICIT ReasonList OPTIONAL,
	-- O 6.5.2.aw
	meid									[390] IMPLICIT MEID OPTIONAL
	-- O
	}

--X.S0004-540-E v2.0 2.42 NumberPortabilityRequest
-- 6.4.2.g NumberPortabilityRequest Updated with N.S0023-0 v 1.0
NumberPortabilityRequest ::= [PRIVATE 18] SET {
	digits		 							[4] IMPLICIT Digits,
	-- (Dialed) M 6.5.2.58
	acgencountered							[340] IMPLICIT ACGEncountered OPTIONAL,
	-- O 6.5.2.fv d
	callingPartyNumberDigits1				[80] IMPLICIT CallingPartyNumberDigits1 OPTIONAL,
	-- O 6.5.2.21 a
	mscid									[21] IMPLICIT MSCID OPTIONAL,
	-- O 6.5.2.82 b
	msid									MSID OPTIONAL
	-- (Originating) O 6.5.2.bv c
	}

NumberPortabilityRequestRes ::= [PRIVATE 18] SET {
	routingDigits							[150] IMPLICIT RoutingDigits OPTIONAL
	-- O 2.209
	}

-- 6.4.2.h ServiceRequest Updated with N.S0023-0 v 1.0

ServiceRequest ::= [PRIVATE 18] SET {
	serviceID								[246] IMPLICIT ServiceID,
	-- M 6.5.2.bz
	accessDeniedReason						[20] IMPLICIT AccessDeniedReason OPTIONAL,
	-- O 6.5.2.1 c d
	acgencountered							[340] IMPLICIT ACGEncountered OPTIONAL,
	-- O 6.5.2.fv p
	availabilityType						[90] IMPLICIT AvailabilityType OPTIONAL,
	-- O 6.5.2.15 c, e
	billingID								[1] IMPLICIT BillingID OPTIONAL,
	-- O 6.5.2.16 a, f
	callingPartyName						[243] IMPLICIT CallingPartyName OPTIONAL,
	-- O 6.5.2.bw a
	callingPartyNumberDigits1				[80] IMPLICIT CallingPartyNumberDigits1 OPTIONAL,
	--O 6.5.2.21 a	1 0 0 1 1 1 1 1 (0x9f)
	--				0 1 0 1 0 0 0 0 (0x50)
	callingPartyNumberDigits2				[81] IMPLICIT CallingPartyNumberDigits2 OPTIONAL,
	--O 6.5.2.22 b	1 0 0 1 1 1 1 1 (0x9f)
	--				0 1 0 1 0 0 0 1 (0x51)
	callingPartySubaddress					[84] IMPLICIT CallingPartySubaddress OPTIONAL,
	--O 6.5.2.25 a	1 0 0 1 1 1 1 1 (0x9f)
	--				0 1 0 1 0 1 0 0 (0x54)

	carrierDigits							[86] IMPLICIT CarrierDigits OPTIONAL,
	-- O 6.5.2.28 p
	conditionallyDeniedReason				[162] IMPLICIT ConditionallyDeniedReason OPTIONAL,
	-- O 6.5.2.48 c, d
	dataAccessElementList					[250] IMPLICIT DataAccessElementList OPTIONAL,
	-- O 6.5.2.cd c
	destinationDigits						[87] IMPLICIT	DestinationDigits OPTIONAL,
	-- O 6.5.2.56 q
	digits		 							[4] IMPLICIT Digits OPTIONAL,
	-- (Dialed) O 6.5.2.58 a
	dmh-RedirectionIndicator				[88] IMPLICIT DMH-RedirectionIndicator OPTIONAL,
	-- O 6.5.2.62 c
	dmh-ServiceID							[305] IMPLICIT DMH-ServiceID OPTIONAL,
	-- O 6.5.2.ej c, r
	electronicSerialNumber					[9] IMPLICIT ElectronicSerialNumber OPTIONAL,
	-- O 6.5.2.63 c, s
	extendedMSCID							[53] IMPLICIT ExtendedMSCID OPTIONAL,
	-- O 6.5.2.64 c, t
	featureIndicator						[306] IMPLICIT FeatureIndicator OPTIONAL,
	-- O 6.5.2.ej c, u
	groupInformation						[163] GroupInformation OPTIONAL,
	-- O 6.5.2.69 c
	legInformation							[144] IMPLICIT LegInformation OPTIONAL,
	-- O 6.5.2.75 c
	locationAreaID							[33] IMPLICIT LocationAreaID OPTIONAL,
	-- O 6.5.2.77 c
	mobileDirectoryNumber					[93] IMPLICIT MobileDirectoryNumber OPTIONAL,
	-- O 6.5.2.80 c, g
-- Removed MobileIdentificationNumber O 6.5.2.81 c
	mscid									[21] IMPLICIT MSCID OPTIONAL,
	-- (Invoking) O 6.5.2.82 c, h
	mSCIdentificationNumber					[94] IMPLICIT MSCIdentificationNumber OPTIONAL,
	-- (Invoking) O 6.5.2.83 c, i
	msid									MSID OPTIONAL,
	-- O 6.5.2.bv p
	pc-ssn									[32] IMPLICIT PC-SSN OPTIONAL,
	-- O 6.5.2.93 i, j
	pilotBillingID							[169] IMPLICIT PilotBillingID OPTIONAL,
	-- O 6.5.2.94 c
	pilotNumber								[168] IMPLICIT PilotNumber OPTIONAL,
	-- O 6.5.2.95 c
	preferredLanguageIndicator				[147] IMPLICIT PreferredLanguageIndicator OPTIONAL,
	-- O 6.5.2.96 a
	redirectingPartyName					[245] IMPLICIT RedirectingPartyName OPTIONAL,
	-- O 6.5.2.by a
	redirectingNumberDigits					[100] IMPLICIT RedirectingNumberDigits OPTIONAL,
	-- O 6.5.2.107 a
	redirectingSubaddress					[102] IMPLICIT RedirectingSubaddress OPTIONAL,
	-- O 6.5.2.109 a
	redirectionReason						[19] IMPLICIT RedirectionReason OPTIONAL,
	-- O 6.5.2.110 a, c
	routingDigits							[150] IMPLICIT RoutingDigits OPTIONAL,
	-- O 6.5.2.114 v
	senderIdentificationNumber				[103] IMPLICIT SenderIdentificationNumber OPTIONAL,
	-- O 6.5.2.116 k
	servingCellID							[2] IMPLICIT ServingCellID OPTIONAL,
	-- O 6.5.2.117 c
	systemMyTypeCode						[22] IMPLICIT SystemMyTypeCode OPTIONAL,
	-- O 6.5.2.147 l
	terminationAccessType					[119] IMPLICIT TerminationAccessType OPTIONAL,
	-- O 6.5.2.155 c
	timeDateOffset							[275] IMPLICIT TimeDateOffset OPTIONAL,
	-- O 6.5.2.dd c, w
	timeOfDay								[309] IMPLICIT TimeOfDay OPTIONAL,
	-- O 6.5.2.em c, x
	transactionCapability					[123] IMPLICIT TransactionCapability OPTIONAL,
	-- O 6.5.2.160 m
	triggerType								[279] IMPLICIT TriggerType OPTIONAL,
	--	O 6.5.2.dh n
	winCapability							[280] IMPLICIT WINCapability OPTIONAL
	-- O 6.5.2.di o
}

-- ServiceRequest RETURN RESULT Parameters
ServiceRequestRes ::= [PRIVATE 18] SET {
	accessDeniedReason						[20] IMPLICIT AccessDeniedReason OPTIONAL,
	-- O 6.5.2.1 b
	actionCode								[128] IMPLICIT ActionCode OPTIONAL,
	-- O 6.5.2.2 c
	alertCode								[75] IMPLICIT AlertCode OPTIONAL,
	-- O 6.5.2.3 d
	announcementList						[130] IMPLICIT AnnouncementList OPTIONAL,
	-- O 6.5.2.6 e
	callingPartyName						[243] IMPLICIT CallingPartyName OPTIONAL,
	-- O 6.5.2.bw a
	callingPartyNumberString1				[82] IMPLICIT CallingPartyNumberString1 OPTIONAL,
	-- O 6.5.2.23 a
	callingPartyNumberString2				[83] IMPLICIT CallingPartyNumberString2 OPTIONAL,
	-- O 6.5.2.24 a
	callingPartySubaddress					[84] IMPLICIT CallingPartySubaddress OPTIONAL,
	-- O 6.5.2.25 a
	carrierDigits							[86] IMPLICIT CarrierDigits OPTIONAL,
	-- O 6.5.2.28 a
	digits		 							[4] IMPLICIT Digits OPTIONAL,
	-- (Dialed) O 6.5.2.58 f
	displayText								[244] IMPLICIT DisplayText OPTIONAL,
	-- O 6.5.2.bx d, e, p
	displayText2							[299] IMPLICIT DisplayText2 OPTIONAL,
	-- O 6.5.2.ec d, e, p
	dmh-AccountCodeDigits					[140] IMPLICIT DMH-AccountCodeDigits OPTIONAL,
	-- O 6.5.2.59 a
	dmh-AlternateBillingDigits				[141] IMPLICIT DMH-AlternateBillingDigits OPTIONAL,
	-- O 6.5.2.60 a
	dmh-BillingDigits						[142] IMPLICIT DMH-BillingDigits OPTIONAL,
	-- O 6.5.2.61 a
	dmh-ChargeInformation					[311] IMPLICIT DMH-ChargeInformation OPTIONAL,
	-- O 6.5.2.eo a, k
	dmh-RedirectionIndicator				[88] IMPLICIT DMH-RedirectionIndicator OPTIONAL,
	-- O 6.5.2.62 a
	dmh-ServiceID							[305] IMPLICIT DMH-ServiceID OPTIONAL,
	-- O 6.5.2.ei i
	groupInformation						[163] IMPLICIT GroupInformation OPTIONAL,
	-- O 6.5.2.69 a
	mobileDirectoryNumber					[93] IMPLICIT MobileDirectoryNumber OPTIONAL,
	-- O 6.5.2.80 a
	noAnswerTime							[96] IMPLICIT NoAnswerTime OPTIONAL,
	-- O 6.5.2.87 a
	redirectingNumberDigits					[100] IMPLICIT RedirectingNumberDigits OPTIONAL,
	-- O 6.5.2.107 a
	redirectingNumberString					[101] IMPLICIT RedirectingNumberString OPTIONAL,
	-- O 6.5.2.108 a
	redirectingSubaddress					[102] IMPLICIT RedirectingSubaddress OPTIONAL,
	-- O 6.5.2.109 a
	resumePIC								[266] IMPLICIT ResumePIC OPTIONAL,
	-- O 6.5.2.cu g
	routingDigits							[150] IMPLICIT RoutingDigits OPTIONAL,
	-- O 6.5.2.114 a
	terminationList							[120] IMPLICIT TerminationList OPTIONAL,
	-- O 6.5.2.156 h
	triggerAddressList						[276] IMPLICIT TriggerAddressList OPTIONAL
	-- O 6.5.2.de j

}

-- 6.4.2.i AnalyzedInformation Updated with N.S0023-0 v 1.0
AnalyzedInformation ::= [PRIVATE 18] SET {
	billingID								[1] IMPLICIT BillingID,
	-- (Originating) M 6.5.2.16 a
	digits		 							[4] IMPLICIT Digits,
	-- (Dialed) M 6.5.2.58
	mscid									[21] IMPLICIT MSCID,
	-- (Originating) M 6.5.2.82 b
	transactionCapability					[123] IMPLICIT TransactionCapability,
	-- M 6.5.2.160
	triggerType								[279] IMPLICIT TriggerType,
	-- M 6.5.2.dh c
	winCapability							[280] IMPLICIT WINCapability,
	-- M 6.5.2.di d
	acgencountered							[340] IMPLICIT ACGEncountered OPTIONAL,
	-- O 6.5.2.fv n
	callingPartyName						[243] IMPLICIT CallingPartyName OPTIONAL,
	-- O 6.5.2.bw e, m
	callingPartyNumberDigits1				[80] IMPLICIT CallingPartyNumberDigits1 OPTIONAL,
	-- O 6.5.2.21 e
	callingPartyNumberDigits2				[81] IMPLICIT CallingPartyNumberDigits2 OPTIONAL,
	-- O 6.5.2.22 e
	callingPartySubaddress					[84] IMPLICIT CallingPartySubaddress OPTIONAL,
	-- O 6.5.2.25 e
	carrierDigits							[86] IMPLICIT CarrierDigits OPTIONAL,
	-- O 6.5.2.28 n, o
	conferenceCallingIndicator				[137] IMPLICIT ConferenceCallingIndicator OPTIONAL,
	-- O 6.5.2.49 f
	destinationDigits						[87] IMPLICIT	DestinationDigits OPTIONAL,
	-- O 6.5.2.56 n, p
	dmd-BillingIndicator					[312] IMPLICIT DMH-BillingIndicator OPTIONAL,
	-- O 6.5.2.ep y
	dmh-ChargeInformation					[311] IMPLICIT DMH-ChargeInformation OPTIONAL,
	--	 O 6.5.2.eo g, r
	dmh-RedirectionIndicator				[88] IMPLICIT DMH-RedirectionIndicator OPTIONAL,
	-- O 6.5.2.62 q
	electronicSerialNumber					[9] IMPLICIT ElectronicSerialNumber OPTIONAL,
		-- O 6.5.2.63 g, r
	featureIndicator						[306] IMPLICIT FeatureIndicator OPTIONAL,
	-- O 6.5.2.ej s
	locationAreaID							[33] IMPLICIT LocationAreaID OPTIONAL,
	-- O 6.5.2.77 h, t
	mobileDirectoryNumber					[93] IMPLICIT MobileDirectoryNumber OPTIONAL,
	-- O 6.5.2.80 i
	mobileIdentificationNumber				[8] IMPLICIT MobileIdentificationNumber OPTIONAL,
	-- O 6.5.2.81 g
	mSCIdentificationNumber					[94] IMPLICIT MSCIdentificationNumber OPTIONAL,
	-- O 6.5.2.83 j
	msid									MSID OPTIONAL,
	-- O 6.5.2.bv n
	oneTimeFeatureIndicator					[97] IMPLICIT OneTimeFeatureIndicator OPTIONAL,
	-- O 6.5.2.88 k
	preferredLanguageIndicator				[147] IMPLICIT PreferredLanguageIndicator OPTIONAL,
	-- O 6.5.2.96
	redirectingNumberDigits					[100] IMPLICIT RedirectingNumberDigits OPTIONAL,
	-- O 6.5.2.107 e
	redirectingPartyName					[245] IMPLICIT RedirectingPartyName OPTIONAL,
	-- O 6.5.2.by b, m
	redirectingSubaddress					[102] IMPLICIT RedirectingSubaddress OPTIONAL,
	-- O 6.5.2.109 e
	routingDigits							[150] IMPLICIT RoutingDigits OPTIONAL,
	-- O 6.5.2.114 n, u
	servingCellID							[2] IMPLICIT ServingCellID OPTIONAL,
	-- O 6.5.2.117 h, v
	systemMyTypeCode						[22] IMPLICIT SystemMyTypeCode OPTIONAL,
	-- O 6.5.2.147
	terminationAccessType					[119] IMPLICIT TerminationAccessType OPTIONAL,
	-- O 6.5.2.155 l
	timeDateOffset							[275] IMPLICIT TimeDateOffset OPTIONAL,
	-- O 6.5.2.dd w
	timeOfDay								[309] IMPLICIT TimeOfDay OPTIONAL
	-- O 6.5.2.em x
	}

--AnalyzedInformation RETURN RESULT Parameters
-- Analyzed Information Request
AnalyzedInformationRes ::= [PRIVATE 18] SET {
	accessDeniedReason						[20] IMPLICIT AccessDeniedReason OPTIONAL,
	-- O 6.5.2.1 a
	actionCode								[128] IMPLICIT ActionCode OPTIONAL,
	-- O 6.5.2.2 b
	announcementList						[130] IMPLICIT AnnouncementList OPTIONAL,
	-- O 6.5.2.6 c
	carrierDigits							[86] IMPLICIT CarrierDigits OPTIONAL,
	-- O 6.5.2.28 d
	conferenceCallingIndicator				[137] IMPLICIT ConferenceCallingIndicator OPTIONAL,
	-- O 6.5.2.49 e
	digits		 							[4] IMPLICIT Digits OPTIONAL,
	-- (Dialed) O 6.5.2.58 f
	displayText								[244] IMPLICIT DisplayText OPTIONAL,
	-- O 6.5.2.bx d, m
	dmh-AccountCodeDigits					[140] IMPLICIT DMH-AccountCodeDigits OPTIONAL,
	-- O 6.5.2.59 g
	dmh-AlternateBillingDigits				[141] IMPLICIT DMH-AlternateBillingDigits OPTIONAL,
	-- O 6.5.2.60 g
	dmh-BillingDigits						[142] IMPLICIT DMH-BillingDigits OPTIONAL,
	-- O 6.5.2.61 g
	dmh-RedirectionIndicator				[88] IMPLICIT DMH-RedirectionIndicator OPTIONAL,
	-- O 6.5.2.62 h
	dmh-ServiceID							[305] IMPLICIT DMH-ServiceID OPTIONAL,
	-- O 6.5.2.ei n
	noAnswerTime							[96] IMPLICIT NoAnswerTime OPTIONAL,
	-- O 6.5.2.87 i
	oneTimeFeatureIndicator					[97] IMPLICIT OneTimeFeatureIndicator OPTIONAL,
	-- O 6.5.2.88 j
	redirectingNumberDigits					[100] IMPLICIT RedirectingNumberDigits OPTIONAL,
	-- O 6.5.2.107 d
	resumePIC								[266] IMPLICIT ResumePIC OPTIONAL,
	-- O 6.5.2.cu k
	routingDigits							[150] IMPLICIT RoutingDigits OPTIONAL,
	-- O 6.5.2.114 d
	terminationList							[120] IMPLICIT TerminationList OPTIONAL,
	-- O 6.5.2.156 l
	terminationTriggers						[122] IMPLICIT TerminationTriggers OPTIONAL,
	-- O 6.5.2.159 d
	triggerAddressList						[276] IMPLICIT TriggerAddressList OPTIONAL
	-- O 6.5.2.de d, o
	}
-- 6.4.2.j ConnectionFailureReport

ConnectionFailureReport ::= [PRIVATE 18] SET {
	failureType								[260] IMPLICIT FailureType,
	-- M 6.5.2.cn
	failureCause							[387] IMPLICIT FailureCause OPTIONAL
	-- O 6.5.2.cm
	}

-- 6.4.2.k ConnectResource
ConnectResource ::= [PRIVATE 18] SET {
	destinationDigits						[87] IMPLICIT	DestinationDigits,
	-- M 6.5.2.56
	carrierDigits							[86] IMPLICIT CarrierDigits OPTIONAL,
	-- O 6.5.2.28 a
	outingDigits							[150] IMPLICIT RoutingDigits OPTIONAL
	-- O 6.5.2.114 a	
	}

-- 6.4.2.l DisconnectResource
-- NO data
--DisconnectResource ::= [PRIVATE 18] SET {
--	}

-- 6.4.2.m FacilitySelectedAndAvailable updated with N.S0023-0 v 1.0
FacilitySelectedAndAvailable ::= [PRIVATE 18] SET {
	billingID								[1] IMPLICIT BillingID,
	-- (Serving) M 6.5.2.16
	mscid									[21] IMPLICIT MSCID,
	-- (Serving) M 6.5.2.82
	transactionCapability					[123] IMPLICIT TransactionCapability,
	-- M 6.5.2.160
	triggerType								[279] IMPLICIT TriggerType,
	-- M 6.5.2.dh a
	winCapability							[280] IMPLICIT WINCapability,
	-- M 6.5.2.di b
	acgencountered							[340] IMPLICIT ACGEncountered OPTIONAL,
	-- O 6.5.2.fv
	callingPartyName						[243] IMPLICIT CallingPartyName OPTIONAL,
	-- O 6.5.2.bw c, i
	callingPartyNumberDigits1				[80] IMPLICIT CallingPartyNumberDigits1 OPTIONAL,
	-- O 6.5.2.21 c
	callingPartyNumberDigits2				[81] IMPLICIT CallingPartyNumberDigits2 OPTIONAL,
	-- O 6.5.2.22 c
	callingPartySubaddress					[84] IMPLICIT CallingPartySubaddress OPTIONAL,
	-- O 6.5.2.25 c
	electronicSerialNumber					[9] IMPLICIT ElectronicSerialNumber OPTIONAL,
	-- O 6.5.2.63
	groupInformation						[163] IMPLICIT GroupInformation OPTIONAL,
	-- O 6.5.2.69 c
	legInformation							[144] IMPLICIT LegInformation OPTIONAL,
	-- O 6.5.2.75 c
	locationAreaID							[33] IMPLICIT LocationAreaID OPTIONAL,
	-- O 6.5.2.77 c
	mobileDirectoryNumber					[93] IMPLICIT MobileDirectoryNumber OPTIONAL,
	-- O 6.5.2.80 d, e
--MobileIdentificationNumber O 6.5.2.81 d
	mSCIdentificationNumber					[94] IMPLICIT MSCIdentificationNumber OPTIONAL,
	-- O 6.5.2.83 f
	msid									MSID OPTIONAL,
	-- O 6.5.2.bv d, j
	oneTimeFeatureIndicator					[97] IMPLICIT OneTimeFeatureIndicator OPTIONAL,
	-- O 6.5.2.88 g
	pilotBillingID							[169] IMPLICIT PilotBillingID OPTIONAL,
	-- O 6.5.2.94 c
	pilotNumber								[168] IMPLICIT PilotNumber OPTIONAL,
	-- O 6.5.2.95 c
	preferredLanguageIndicator				[147] IMPLICIT PreferredLanguageIndicator OPTIONAL,
	-- O 6.5.2.96 c
	redirectingNumberDigits					[100] IMPLICIT RedirectingNumberDigits OPTIONAL,
	-- O 6.5.2.107 c
	redirectingPartyName					[245] IMPLICIT RedirectingPartyName OPTIONAL,
	-- O 6.5.2.by c, i
	redirectingSubaddress					[102] IMPLICIT RedirectingSubaddress OPTIONAL,
	-- O 6.5.2.109 c
	servingCellID							[2] IMPLICIT ServingCellID OPTIONAL,
	-- O 6.5.2.117 c
	systemMyTypeCode						[22] IMPLICIT SystemMyTypeCode OPTIONAL,
	-- O 6.5.2.147
	terminationAccessType					[119] IMPLICIT TerminationAccessType OPTIONAL
	-- O 6.5.2.155 h
	}

-- FacilitySelectedAndAvailable RETURN RESULT Parameters

FacilitySelectedAndAvailableRes ::= [PRIVATE 18] SET {
	accessDeniedReason						[20] IMPLICIT AccessDeniedReason OPTIONAL,
	-- O 6.5.2.1 a
	actionCode								[128] IMPLICIT ActionCode OPTIONAL,
	-- O 6.5.2.2 b
	alertCode								[75] IMPLICIT AlertCode OPTIONAL,
	-- O 6.5.2.3 c
	displayText								[244] IMPLICIT DisplayText OPTIONAL,
	-- O 6.5.2.bx d, j
	dmh-AccountCodeDigits					[140] IMPLICIT DMH-AccountCodeDigits OPTIONAL,
	-- O 6.5.2.59 e
	dmh-AlternateBillingDigits				[141] IMPLICIT DMH-AlternateBillingDigits OPTIONAL,
	-- O 6.5.2.60 e
	dmh-BillingDigits						[142] IMPLICIT DMH-BillingDigits OPTIONAL,
	-- O 6.5.2.61 e
	dmh-ChargeInformation					[311] IMPLICIT DMH-ChargeInformation OPTIONAL,
	-- O 6.5.2.eo e, l
	dmh-RedirectionIndicator				[88] IMPLICIT DMH-RedirectionIndicator OPTIONAL,
	-- O 6.5.2.62 e, f
	dmh-ServiceID							[305] IMPLICIT DMH-ServiceID OPTIONAL,
	-- O 6.5.2.ei k
	noAnswerTime							[96] IMPLICIT NoAnswerTime OPTIONAL,
	-- O 6.5.2.87 g
	oneTimeFeatureIndicator					[97] IMPLICIT OneTimeFeatureIndicator OPTIONAL,
	-- O 6.5.2.88 h
	resumePIC								[266] IMPLICIT ResumePIC OPTIONAL,
	-- O 6.5.2.cu i
	terminationTriggers						[122] IMPLICIT TerminationTriggers OPTIONAL,
	-- O 6.5.2.159 d
	triggerAddressList						[276] IMPLICIT TriggerAddressList OPTIONAL
	-- O 6.5.2.de d, l
	}

-- 6.4.2.n InstructionRequest
-- InstructionRequest ::= [PRIVATE 18] SET {
-- Length zero octets
--	}

-- InstructionRequest RETURN RESULT Parameters
-- zero octets M 6.3.2.2

-- 6.4.2.o Modify
Modify ::= [PRIVATE 18] SET {
	databaseKey								[252] IMPLICIT DatabaseKey,
	-- M 6.5.2.cf a
	modificationRequestList					[263] IMPLICIT ModificationRequestList
	-- M 6.5.2.cq
	}
-- Modify RETURN RESULT Parameters
ModifyRes ::= [PRIVATE 18] SET {
	modificationResultList					[264] IMPLICIT ModificationResultList
	-- M 6.5.2.cs a
	}

-- 6.4.2.p ResetTimer
-- NO data

-- 6.4.2.q Search
Search ::= [PRIVATE 18] SET {
	databaseKey								[252] IMPLICIT DatabaseKey,
	-- M 6.5.2.cf a
	serviceDataAccessElementList			[271] IMPLICIT ServiceDataAccessElementList
	--M 6.5.2.cz b
	}

-- Search RETURN RESULT Parameters
SearchRes ::= [PRIVATE 18] SET {
	serviceDataAccessElementList			[271] IMPLICIT ServiceDataAccessElementList
	-- M 6.5.2.cz a
	}

-- 6.4.2.r SeizeResource
SeizeResource ::= [PRIVATE 18] SET {
	preferredLanguageIndicator				[147] IMPLICIT PreferredLanguageIndicator OPTIONAL,
	-- O 6.5.2.96
	privateSpecializedResource				[265] IMPLICIT PrivateSpecializedResource OPTIONAL,
	--O 6.5.2.u a
	specializedResource						[274] IMPLICIT SpecializedResource OPTIONAL
	--O 6.5.2.dc a
	}

-- SeizeResource RETURN RESULT Parameters
SeizeResourceRes ::= [PRIVATE 18] SET {
	destinationDigits						[87] IMPLICIT	DestinationDigits
	-- M 6.5.2.56 a
	}

--6.4.2.s SRFDirective
SRFDirective ::= [PRIVATE 18] SET {
	announcementList						[130] IMPLICIT AnnouncementList OPTIONAL,
	-- O 6.5.2.6 a, d
	digitCollectionControl					[139] IMPLICIT DigitCollectionControl OPTIONAL,
	-- O 6.5.2.57 b
	executeScript							[386] IMPLICIT ExecuteScript OPTIONAL,
	-- O 6.5.2.cl c, d
	mobileDirectoryNumber					[93] IMPLICIT MobileDirectoryNumber OPTIONAL
	-- O 6.5.2.80 e
	}
-- SRFDirective RETURN RESULT Parameters
SRFDirectiveRes ::= [PRIVATE 18] SET {
	digits		 							[4] IMPLICIT Digits OPTIONAL,
	-- (Dialed) O 6.5.2.58 a, b
	scriptResult							[269] IMPLICIT ScriptResult OPTIONAL
	-- O 6.5.2.cx c
	}

-- 6.4.2.t TBusy updated with N.S0023-0 v 1.0
TBusy ::= [PRIVATE 18] SET {
	billingID								[1] IMPLICIT BillingID,
	-- (Invoking) M 6.5.2.16 a
	mscid									[21] IMPLICIT MSCID,
	-- M 6.5.2.82 b
	transactionCapability					[123] IMPLICIT TransactionCapability,
	-- M 6.5.2.160
	triggerType								[279] IMPLICIT TriggerType,
	-- M 6.5.2.dh c
	winCapability							[280] IMPLICIT WINCapability,
	-- M 6.5.2.di d
	acgencountered							[340] IMPLICIT ACGEncountered OPTIONAL,
	-- O 6.5.2.fv
	callingPartyNumberDigits1				[80] IMPLICIT CallingPartyNumberDigits1 OPTIONAL,
	-- O 6.5.2.21 e
	callingPartyNumberDigits2				[81] IMPLICIT CallingPartyNumberDigits2 OPTIONAL,
	-- O 6.5.2.22 e
	callingPartySubaddress					[84] IMPLICIT CallingPartySubaddress OPTIONAL,
	-- O 6.5.2.25 e
	electronicSerialNumber					[9] IMPLICIT ElectronicSerialNumber OPTIONAL,
	-- O 6.5.2.63 f
	groupInformation						[163] IMPLICIT GroupInformation OPTIONAL,
	-- O 6.5.2.69 f
	legInformation							[144] IMPLICIT LegInformation OPTIONAL,
	-- O 6.5.2.75 f
	locationAreaID							[33] IMPLICIT LocationAreaID OPTIONAL,
	-- O 6.5.2.77 g
	mobileDirectoryNumber					[93] IMPLICIT MobileDirectoryNumber OPTIONAL,
	-- O 6.5.2.80 h, i
--	mobileIdentificationNumber				[8] IMPLICIT MobileIdentificationNumber OPTIONAL,
	-- O 6.5.2.81 h
	mSCIdentificationNumber					[94] IMPLICIT MSCIdentificationNumber OPTIONAL,
	-- O 6.5.2.83 b
	msid									MSID OPTIONAL,
	-- O 6.5.2.bv h
	oneTimeFeatureIndicator					[97] IMPLICIT OneTimeFeatureIndicator OPTIONAL,
	-- O 6.5.2.88 j
	pilotBillingID							[169] IMPLICIT PilotBillingID OPTIONAL,
	-- O 6.5.2.94 f
	pilotNumber								[168] IMPLICIT PilotNumber OPTIONAL,
	-- O 6.5.2.95 f
	preferredLanguageIndicator				[147] IMPLICIT PreferredLanguageIndicator OPTIONAL,
	-- O 6.5.2.96 g
	redirectingNumberDigits					[100] IMPLICIT RedirectingNumberDigits OPTIONAL,
	-- O 6.5.2.107 e
	redirectingSubaddress					[102] IMPLICIT RedirectingSubaddress OPTIONAL,
	-- O 6.5.2.109 e
	redirectionReason						[19] IMPLICIT RedirectionReason OPTIONAL,
	--: TBusy O 6.5.2.110 f
	servingCellID							[2] IMPLICIT ServingCellID OPTIONAL,
	-- O 6.5.2.117 g
	systemMyTypeCode						[22] IMPLICIT SystemMyTypeCode OPTIONAL,
	-- O 6.5.2.147
	terminationAccessType					[119] IMPLICIT TerminationAccessType OPTIONAL
	-- O 6.5.2.155 f
	}


-- TBusy RETURN RESULT Parameters

TBusyRes ::= [PRIVATE 18] SET {
	accessDeniedReason						[20] IMPLICIT AccessDeniedReason OPTIONAL,
	-- O 6.5.2.1 a
	actionCode								[128] IMPLICIT ActionCode OPTIONAL,
	-- O 6.5.2.2 b
	announcementList						[130] IMPLICIT AnnouncementList OPTIONAL,
	-- O 6.5.2.6 c
	callingPartyNumberString1				[82] IMPLICIT CallingPartyNumberString1 OPTIONAL,
	-- O 6.5.2.23 d, e
	callingPartyNumberString2				[83] IMPLICIT CallingPartyNumberString2 OPTIONAL,
	-- O 6.5.2.24 d, e
	carrierDigits							[86] IMPLICIT CarrierDigits OPTIONAL,
	-- O 6.5.2.28 l
	displayText								[244] IMPLICIT DisplayText OPTIONAL,
	-- O 6.5.2.bx d, e, m
	dmh-AlternateBillingDigits				[141] IMPLICIT DMH-AlternateBillingDigits OPTIONAL,
	-- O 6.5.2.60 g
	dmh-BillingDigits						[142] IMPLICIT DMH-BillingDigits OPTIONAL,
	-- O 6.5.2.61 f
	dmh-RedirectionIndicator				[88] IMPLICIT DMH-RedirectionIndicator OPTIONAL,
	-- O 6.5.2.62 f
	dmh-ServiceID							[305] IMPLICIT DMH-ServiceID OPTIONAL,
	-- O 6.5.2.ei n
	groupInformation						[163] IMPLICIT GroupInformation OPTIONAL,
	-- O 6.5.2.69 g
	oneTimeFeatureIndicator					[97] IMPLICIT OneTimeFeatureIndicator OPTIONAL,
	-- O 6.5.2.88 h
	pilotNumber								[168] IMPLICIT PilotNumber OPTIONAL,
	-- O 6.5.2.95 g
	preferredLanguageIndicator				[147] IMPLICIT PreferredLanguageIndicator OPTIONAL,
	-- O 6.5.2.96 l, o
	redirectingNumberDigits					[100] IMPLICIT RedirectingNumberDigits OPTIONAL,
	-- O 6.5.2.107 i
	resumePIC								[266] IMPLICIT ResumePIC OPTIONAL,
	-- O 6.5.2.cu j
	routingDigits							[150] IMPLICIT RoutingDigits OPTIONAL,
	-- O 6.5.2.114 l
	terminationList							[120] IMPLICIT TerminationList OPTIONAL,
	-- O 6.5.2.156 k
	terminationTriggers						[122] IMPLICIT TerminationTriggers OPTIONAL,
	-- O 6.5.2.159 l
	triggerAddressList						[276] IMPLICIT TriggerAddressList OPTIONAL
	-- O 6.5.2.de l
	}
-- 6.4.2.u TNoAnswer updated with N.S0023-0 v 1.0
TNoAnswer ::= [PRIVATE 18] SET {
	billingID								[1] IMPLICIT BillingID,
	-- (Invoking) M 6.5.2.16 a
	mscid									[21] IMPLICIT MSCID,
	-- M 6.5.2.82 b
	transactionCapability					[123] IMPLICIT TransactionCapability,
	-- M 6.5.2.160
	triggerType								[279] IMPLICIT TriggerType,
	-- M 6.5.2.dh c
	winCapability							[280] IMPLICIT WINCapability,
	-- M 6.5.2.di d
	acgencountered							[340] IMPLICIT ACGEncountered OPTIONAL,
	-- O 6.5.2.fv
	callingPartyNumberDigits1				[80] IMPLICIT CallingPartyNumberDigits1 OPTIONAL,
	-- O 6.5.2.21 e
	callingPartyNumberDigits2				[81] IMPLICIT CallingPartyNumberDigits2 OPTIONAL,
	-- O 6.5.2.22 e
	callingPartySubaddress					[84] IMPLICIT CallingPartySubaddress OPTIONAL,
	-- O 6.5.2.25 e
	electronicSerialNumber					[9] IMPLICIT ElectronicSerialNumber OPTIONAL,
	-- O 6.5.2.63 f
	groupInformation						[163] IMPLICIT GroupInformation OPTIONAL,
	-- O 6.5.2.69 f
	legInformation							[144] IMPLICIT LegInformation OPTIONAL,
	-- O 6.5.2.75 f
	locationAreaID							[33] IMPLICIT LocationAreaID OPTIONAL,
	-- O 6.5.2.77 g
	mobileDirectoryNumber					[93] IMPLICIT MobileDirectoryNumber OPTIONAL,
	-- O 6.5.2.80 h, i
--	mobileIdentificationNumber				[8] IMPLICIT MobileIdentificationNumber OPTIONAL,
	-- O 6.5.2.81 h
	mSCIdentificationNumber					[94] IMPLICIT MSCIdentificationNumber OPTIONAL,
	-- O 6.5.2.83 b
	msid									MSID OPTIONAL,
	-- O 6.5.2.bv h
	oneTimeFeatureIndicator					[97] IMPLICIT OneTimeFeatureIndicator OPTIONAL,
	-- O 6.5.2.88 j
	pilotBillingID							[169] IMPLICIT PilotBillingID OPTIONAL,
	-- O 6.5.2.94 f
	pilotNumber								[168] IMPLICIT PilotNumber OPTIONAL,
	-- O 6.5.2.95 f
	preferredLanguageIndicator				[147] IMPLICIT PreferredLanguageIndicator OPTIONAL,
	-- O 6.5.2.96 g
	redirectingNumberDigits					[100] IMPLICIT RedirectingNumberDigits OPTIONAL,
	-- O 6.5.2.107 e
	redirectingSubaddress					[102] IMPLICIT RedirectingSubaddress OPTIONAL,
	-- O 6.5.2.109 e
	redirectionReason						[19] IMPLICIT RedirectionReason OPTIONAL,
	--:TNoAnswer O 6.5.2.110 f
	servingCellID							[2] IMPLICIT ServingCellID OPTIONAL,
	-- O 6.5.2.117 g
	systemMyTypeCode						[22] IMPLICIT SystemMyTypeCode OPTIONAL,
	-- O 6.5.2.147
	terminationAccessType					[119] IMPLICIT TerminationAccessType OPTIONAL
	-- O 6.5.2.155 f
}
-- TNoAnswer RETURN RESULT Parameters
-- 6.4.2.u TNoAnswer
TNoAnswerRes ::= [PRIVATE 18] SET {
	accessDeniedReason						[20] IMPLICIT AccessDeniedReason OPTIONAL,
	-- O 6.5.2.1 a
	actionCode								[128] IMPLICIT ActionCode OPTIONAL,
	-- O 6.5.2.2 b
	announcementList						[130] IMPLICIT AnnouncementList OPTIONAL,
	-- O 6.5.2.6 c
	callingPartyNumberString1				[82] IMPLICIT CallingPartyNumberString1 OPTIONAL,
	-- O 6.5.2.23 d, e
	callingPartyNumberString2				[83] IMPLICIT CallingPartyNumberString2 OPTIONAL,
	-- O 6.5.2.24 d, e
	carrierDigits							[86] IMPLICIT CarrierDigits OPTIONAL,
	-- O 6.5.2.28 l
	displayText								[244] IMPLICIT DisplayText OPTIONAL,
	-- O 6.5.2.bx d, e, m
	dmh-AccountCodeDigits					[140] IMPLICIT DMH-AccountCodeDigits OPTIONAL,
	-- O 6.5.2.59 f
	dmh-AlternateBillingDigits				[141] IMPLICIT DMH-AlternateBillingDigits OPTIONAL,
	-- O 6.5.2.60 f
	dmh-BillingDigits						[142] IMPLICIT DMH-BillingDigits OPTIONAL,
	-- O 6.5.2.61 f
	dmh-RedirectionIndicator				[88] IMPLICIT DMH-RedirectionIndicator OPTIONAL,
	-- O 6.5.2.62 f
	dmh-ServiceID							[305] IMPLICIT DMH-ServiceID OPTIONAL,
	-- O 6.5.2.ei n
	groupInformation						[163] IMPLICIT GroupInformation OPTIONAL,
	-- O 6.5.2.69 g
	oneTimeFeatureIndicator					[97] IMPLICIT OneTimeFeatureIndicator OPTIONAL,
	-- O 6.5.2.88 h
	pilotNumber								[168] IMPLICIT PilotNumber OPTIONAL,
	-- O 6.5.2.95 g
	preferredLanguageIndicator				[147] IMPLICIT PreferredLanguageIndicator OPTIONAL,
	-- O 6.5.2.96 l, o
	redirectingNumberDigits					[100] IMPLICIT RedirectingNumberDigits OPTIONAL,
	-- O 6.5.2.107 i
	resumePIC								[266] IMPLICIT ResumePIC OPTIONAL,
	-- O 6.5.2.cu j
	routingDigits							[150] IMPLICIT RoutingDigits OPTIONAL,
	-- O 6.5.2.114 l
	terminationList							[120] IMPLICIT TerminationList OPTIONAL,
	-- O 6.5.2.156 k
	terminationTriggers						[122] IMPLICIT TerminationTriggers OPTIONAL,
	-- O 6.5.2.159 l
	triggerAddressList						[276] IMPLICIT TriggerAddressList OPTIONAL
	-- O 6.5.2.de l, p
}

-- 6.4.2.x.1. ChangeFacilities N.S0008-0 v 1.0
ChangeFacilities ::= [PRIVATE 18] SET {
	cdmaPrivateLongCodeMask					[67] IMPLICIT CDMAPrivateLongCodeMask OPTIONAL,
	-- O 6.5.2.36 f
	cdmaServiceConfigurationRecord			[174] IMPLICIT CDMAServiceConfigurationRecord OPTIONAL,
	-- O 6.5.2.e b
	dataKey									[215] IMPLICIT DataKey OPTIONAL,
	-- O 6.5.2.at f
	dataPrivacyParameters					[216] IMPLICIT DataPrivacyParameters OPTIONAL,
	-- O 6.5.2.au i, f
	electronicSerialNumber					[9] IMPLICIT ElectronicSerialNumber OPTIONAL,
	-- O 6.5.2.63 c
	interMSCCircuitID						[6] IMPLICIT InterMSCCircuitID OPTIONAL,
	-- O 6.5.2.72 a, c
	ilspInformation							[217] IMPLICIT ISLPInformation OPTIONAL,
	-- O 6.5.2.av d
	mobileIdentificationNumber				[8] IMPLICIT MobileIdentificationNumber OPTIONAL,
	-- O 6.5.2.81 c
	randomVariable							[40] IMPLICIT RandomVariable OPTIONAL,
	-- O 6.5.2.101 f
--	SecondInterMSCCircuitID O 6.5.2.aj c, g
	tdmaBandwidth							[220] IMPLICIT TDMABandwidth OPTIONAL,
	-- O 6.5.2.ay h
	tdmaServiceCode							[178] IMPLICIT TDMAServiceCode OPTIONAL,
	-- O 6.5.2.i e
	voicePrivacyMask						[48] IMPLICIT VoicePrivacyMask OPTIONAL
	-- O 6.5.2.167 f
	}
-- Table 6.4.2.x.1r ChangeFacilities RETURN RESULT Parameters

ChangeFacilitiesRes ::= [PRIVATE 18] SET {
	reasonList								[218] IMPLICIT ReasonList OPTIONAL
	-- O 6.5.2.aw a
	}

-- 6.4.2.x.2. ChangeService N.S0008-0 v 1.0
ChangeService ::= [PRIVATE 18] SET {
	cdmaServiceConfigurationRecord			[174] IMPLICIT CDMAServiceConfigurationRecord OPTIONAL,
	-- O 6.5.2.e a
	cdmaServiceOptionList					[176] IMPLICIT CDMAServiceOptionList OPTIONAL,
	-- O 6.5.2.g b
	changeServiceAttributes					[214] IMPLICIT ChangeServiceAttributes OPTIONAL,
	-- O 6.5.2.as c
	electronicSerialNumber					[9] IMPLICIT ElectronicSerialNumber OPTIONAL,
	-- O 6.5.2.63 d
	ilspInformation							[217] IMPLICIT ISLPInformation OPTIONAL,
	-- O 6.5.2.av e
	mobileIdentificationNumber				[8] IMPLICIT MobileIdentificationNumber OPTIONAL,
	-- O 6.5.2.72 j
	tdmaBandwidth							[220] IMPLICIT TDMABandwidth OPTIONAL,
	-- O 6.5.2.ay g
	tdmaDataMode							[222] IMPLICIT TDMADataMode OPTIONAL,
	-- O 6.5.2.ba i
	tdmaServiceCode							[178] IMPLICIT TDMAServiceCode OPTIONAL,
	-- O 6.5.2.i f
	tdmaVoiceMode							[223] IMPLICIT TDMAVoiceMode OPTIONAL
	-- O 6.5.2.bb h
	}

-- ChangeService RETURN RESULT Parameters
ChangeServiceRes ::= [PRIVATE 18] SET {
	cdmaPrivateLongCodeMask					[67] IMPLICIT CDMAPrivateLongCodeMask OPTIONAL,
	-- O 6.5.2.36 f
	cdmaServiceConfigurationRecord			[174] IMPLICIT CDMAServiceConfigurationRecord OPTIONAL,
	-- O 6.5.2.e b
	cdmaServiceOptionList					[176] IMPLICIT CDMAServiceOptionList OPTIONAL,
	-- O 6.5.2.g c
	changeServiceAttributes					[214] IMPLICIT ChangeServiceAttributes OPTIONAL,
	-- O 6.5.2.as d
	dataKey									[215] IMPLICIT DataKey OPTIONAL,
	-- O 6.5.2.au f
	dataPrivacyParameters					[216] IMPLICIT DataPrivacyParameters OPTIONAL,
	-- O 6.5.2.au g, f
	randomVariable							[40] IMPLICIT RandomVariable OPTIONAL,
	-- O 6.5.2.101 f
	reasonList								[218] IMPLICIT ReasonList OPTIONAL,
	-- O 6.5.2.aw a
	tdmaServiceCode							[178] IMPLICIT TDMAServiceCode OPTIONAL,
	-- O 6.5.2.i e
	voicePrivacyMask						[48] IMPLICIT VoicePrivacyMask OPTIONAL
	-- O 6.5.2.167 f
	}


-- 6.4.2.X MessageDirective
MessageDirective ::= [PRIVATE 18] SET {
	messageWaitingNotificationCount			[92] IMPLICIT MessageWaitingNotificationCount,
	--	 O 6.5.2.78 a
	mobileDirectoryNumber					[93] IMPLICIT MobileDirectoryNumber OPTIONAL,
	-- O 6.5.2.80 b, c
	msid									MSID OPTIONAL
	-- O 6.5.2.bv IS-751 b, c
	}
-- 6.4.2.X2 MessageDirective RETURN RESULT Parameters
--zero octets

-- 6.4.2.y BulkDisconnection
BulkDisconnection ::= [PRIVATE 18] SET {
	mscid									[21] IMPLICIT MSCID,
	-- M 6.5.2.82
	timeDateOffset							[275] IMPLICIT TimeDateOffset OPTIONAL,
	-- M 6.5.2.2 a
	timeOfDay								[309] IMPLICIT TimeOfDay OPTIONAL,
	-- M 6.5.2.em b
	mSCIdentificationNumber					[94] IMPLICIT MSCIdentificationNumber OPTIONAL,
	-- O 6.5.2.83 c
	senderIdentificationNumber				[103] IMPLICIT SenderIdentificationNumber OPTIONAL
	-- O 6.5.2.116 d
	}

-- BulkDisconnection RETURN RESULT Parameters
-- Length zero octets M 6.3.2.2
--BulkDisconnectionRes ::= [PRIVATE 18] SET {
--	}


-- 6.4.2.z CallControlDirective
CallControlDirective ::= [PRIVATE 18] SET {
	billingID								[1] IMPLICIT BillingID,
	-- M 6.5.2.16 a
	mscid									[21] IMPLICIT MSCID,
	-- M 6.5.2.82 b
	msid									MSID OPTIONAL,
	-- M 6.5.2.bv c
	actionCode								[128] IMPLICIT ActionCode OPTIONAL,
	-- O 6.5.2.2 d
	announcementList						[130] IMPLICIT AnnouncementList OPTIONAL,
	-- O 6.5.2.6 e
	displayText								[244] IMPLICIT DisplayText OPTIONAL,
	-- O 6.5.2.bx f
	dmh-AccountCodeDigits					[140] IMPLICIT DMH-AccountCodeDigits OPTIONAL,
	-- O 6.5.2.59 g
	dmh-AlternateBillingDigits				[141] IMPLICIT DMH-AlternateBillingDigits OPTIONAL,
	-- O 6.5.2.60 g
	dmh-BillingDigits						[142] IMPLICIT DMH-BillingDigits OPTIONAL,
	-- O 6.5.2.61 g
	dmh-ChargeInformation					[311] IMPLICIT DMH-ChargeInformation OPTIONAL,
	-- O 6.5.2.eo g, o
	dmh-RedirectionIndicator				[88] IMPLICIT DMH-RedirectionIndicator OPTIONAL,
	-- O 6.5.2.62 g, h
	electronicSerialNumber					[9] IMPLICIT ElectronicSerialNumber OPTIONAL,
	-- O 6.5.2.63 i, j
	mobileDirectoryNumber					[93] IMPLICIT MobileDirectoryNumber OPTIONAL,
	-- O 6.5.2.80 k
	preferredLanguageIndicator				[147] IMPLICIT PreferredLanguageIndicator OPTIONAL,
	-- O 6.5.2.96 l, m
	terminationList							[120] IMPLICIT TerminationList OPTIONAL,
	-- O 6.5.2.156 k
	triggerAddressList						[276] IMPLICIT TriggerAddressList OPTIONAL
	-- O 6.5.2.de h
}

-- z-2 CallControlDirective RETURN RESULT Parameters
CallControlDirectiveRes ::= [PRIVATE 18] SET {
	callStatus								[310] IMPLICIT CallStatus OPTIONAL
	-- O 6.5.2.en a

	}

-- 6.4.2.aa OAnswer
OAnswer ::= [PRIVATE 18] SET {
	billingID								[1] IMPLICIT BillingID,
	-- (Originating) M 6.5.2.16 a
	electronicSerialNumber					[9] IMPLICIT ElectronicSerialNumber OPTIONAL,
	-- M 6.5.2.63 b
	mscid									[21] IMPLICIT MSCID,
	-- (Originating) M 6.5.2.82 c
	msid									MSID OPTIONAL,
	-- M 6.5.2.bv d
	timeDateOffset							[275] IMPLICIT TimeDateOffset,
	-- M 6.5.2.dd e
	timeOfDay								[309] IMPLICIT TimeOfDay,
	-- M 6.5.2.em f
	triggerType								[279] IMPLICIT TriggerType,
	-- M 6.5.2.dh g
	locationAreaID							[33] IMPLICIT LocationAreaID OPTIONAL,
	-- O 6.5.2.77 h, i
	mobileDirectoryNumber					[93] IMPLICIT MobileDirectoryNumber OPTIONAL,
	-- O 6.5.2.80 j
	featureIndicator						[306] IMPLICIT FeatureIndicator OPTIONAL,
	-- O 6.5.2.ej k
	mSCIdentificationNumber					[94] IMPLICIT MSCIdentificationNumber OPTIONAL,
	-- O 6.5.2.83 l
	servingCellID							[2] IMPLICIT ServingCellID OPTIONAL,
	-- O 6.5.2.117 h, m
	systemMyTypeCode						[22] IMPLICIT SystemMyTypeCode OPTIONAL
	-- O 6.5.2.147
	}


--6.4.2.ab ODisconnect
ODisconnect ::= [PRIVATE 18] SET {
	billingID								[1] IMPLICIT BillingID,
	-- (Originating) M 6.5.2.16 a
	electronicSerialNumber					[9] IMPLICIT ElectronicSerialNumber OPTIONAL,
	-- M 6.5.2.63 b
	mscid									[21] IMPLICIT MSCID,
	-- (Originating) M 6.5.2.82 c
	msid									MSID OPTIONAL,
	-- M 6.5.2.bv d
	releaseCause							[308] IMPLICIT ReleaseCause OPTIONAL,
	-- M 6.5.2.el e
	timeDateOffset							[275] IMPLICIT TimeDateOffset OPTIONAL,
	-- M 6.5.2.dd f
	timeOfDay								[309] IMPLICIT TimeOfDay,
	-- M 6.5.2.em g
	transactionCapability					[123] IMPLICIT TransactionCapability,
	-- M 6.5.2.160
	winCapability							[280] IMPLICIT WINCapability,
	-- M 6.5.2.di
	triggerType								[279] IMPLICIT TriggerType,
	-- M 6.5.2.dh h
	locationAreaID							[33] IMPLICIT LocationAreaID OPTIONAL,
	-- O 6.5.2.77 i, j
	mobileDirectoryNumber					[93] IMPLICIT MobileDirectoryNumber OPTIONAL,
	-- O 6.5.2.80 k
	mSCIdentificationNumber					[94] IMPLICIT MSCIdentificationNumber OPTIONAL,
	-- O 6.5.2.83 l
	servingCellID							[2] IMPLICIT ServingCellID OPTIONAL,
	-- O 6.5.2.117 i, m
	systemMyTypeCode						[22] IMPLICIT SystemMyTypeCode OPTIONAL
	-- O 6.5.2.147
}

-- ab-2 ODisconnect RETURN RESULT Parameters
ODisconnectRes ::= [PRIVATE 18] SET {
	announcementList						[130] IMPLICIT AnnouncementList OPTIONAL,
	-- O 6.5.2.6 a
	dmh-ServiceID							[305] IMPLICIT DMH-ServiceID OPTIONAL
	-- O 6.5.2.ei b
	}
-- 6.4.2.ac CallRecoveryReport

CallRecoveryReport ::= [PRIVATE 18] SET {
	callRecoveryIDList						[304] IMPLICIT CallRecoveryIDList
	-- M 6.5.2.eh a
	}

-- ac-2 CallRecoveryReport RETURN RESULT Parameters
--CallRecoveryReportRes ::= [PRIVATE 18] SET {
--	}

-- 6.4.2.ad TAnswer
TAnswer ::= [PRIVATE 18] SET {
	billingID								[1] IMPLICIT BillingID,
	-- (Originating) M 6.5.2.16 a
	electronicSerialNumber					[9] IMPLICIT ElectronicSerialNumber OPTIONAL,
	-- M 6.5.2.63 b
	mscid									[21] IMPLICIT MSCID,
	-- M 6.5.2.82 c
	msid									MSID OPTIONAL,
	-- M 6.5.2.bv b
	timeDateOffset							[275] IMPLICIT TimeDateOffset OPTIONAL,
	-- M 6.5.2.dd d
	timeOfDay								[309] IMPLICIT TimeOfDay,
	-- M 6.5.2.em e
	transactionCapability					[123] IMPLICIT TransactionCapability,
	-- M 6.5.2.160
	triggerType								[279] IMPLICIT TriggerType,
	-- M 6.5.2.dh f
	winCapability							[280] IMPLICIT WINCapability,
	-- M 6.5.2.di
	locationAreaID							[33] IMPLICIT LocationAreaID OPTIONAL,
	-- O 6.5.2.77 g, h
	mobileDirectoryNumber					[93] IMPLICIT MobileDirectoryNumber OPTIONAL,
	-- O 6.5.2.80 i
	featureIndicator						[306] IMPLICIT FeatureIndicator OPTIONAL,
	-- O 6.5.2.ej j
	mSCIdentificationNumber					[94] IMPLICIT MSCIdentificationNumber OPTIONAL,
	-- O 6.5.2.83 k
	servingCellID							[2] IMPLICIT ServingCellID OPTIONAL,
	-- O 6.5.2.117 g, l
	systemMyTypeCode						[22] IMPLICIT SystemMyTypeCode OPTIONAL,
	-- O 6.5.2.147
	terminationAccessType					[119] IMPLICIT TerminationAccessType OPTIONAL
	-- O 6.5.2.155 m
	}
-- 6.4.2.ae TDisconnect
TDisconnect ::= [PRIVATE 18] SET {
	billingID								[1] IMPLICIT BillingID,
	-- (Originating) M 6.5.2.16 a
	electronicSerialNumber					[9] IMPLICIT ElectronicSerialNumber OPTIONAL,
	-- M 6.5.2.63 b
	mscid									[21] IMPLICIT MSCID,
	-- M 6.5.2.82 c
	msid									MSID OPTIONAL,
	-- M 6.5.2.bv d
	timeDateOffset							[275] IMPLICIT TimeDateOffset OPTIONAL,
	-- M 6.5.2.dd e
	timeOfDay								[309] IMPLICIT TimeOfDay,
	-- M 6.5.2.em f
	triggerType								[279] IMPLICIT TriggerType,
	-- M 6.5.2.dh g
	callingPartyNumberDigits1				[80] IMPLICIT CallingPartyNumberDigits1 OPTIONAL,
	-- O 6.5.2.21 n
	callingPartyNumberDigits2				[81] IMPLICIT CallingPartyNumberDigits2 OPTIONAL,
	-- O 6.5.2.22 n
	locationAreaID							[33] IMPLICIT LocationAreaID OPTIONAL,
	-- O 6.5.2.77 h, i
	mobileDirectoryNumber					[93] IMPLICIT MobileDirectoryNumber OPTIONAL,
	-- O 6.5.2.80 j
	mSCIdentificationNumber					[94] IMPLICIT MSCIdentificationNumber OPTIONAL,
	-- O 6.5.2.83 k
	releaseCause							[308] IMPLICIT ReleaseCause OPTIONAL,
	-- O 6.5.2.el l
	servingCellID							[2] IMPLICIT ServingCellID OPTIONAL,
	-- O 6.5.2.117 h, m
	systemMyTypeCode						[22] IMPLICIT SystemMyTypeCode OPTIONAL
	-- O 6.5.2.147
	}

-- Table ae-2 TDisconnect RETURN RESULT Parameters
TDisconnectRes ::= [PRIVATE 18] SET {
	dmh-ServiceID							[305] IMPLICIT DMH-ServiceID OPTIONAL
	-- O 6.5.2.ei a
	}

-- 6.4.2.af UnreliableCallData
UnreliableCallData ::= [PRIVATE 18] SET {
	controlNetworkID						[307] IMPLICIT ControlNetworkID,
	-- M 6.5.2.ek a
	mscid									[21] IMPLICIT MSCID
	-- M 6.5.2.82 b
}

-- UnreliableCallData RETURN RESULT Parameters
--UnreliableCallData ::= [PRIVATE 18] SET {
--
--}

-- 6.4.2.ag OCalledPartyBusy

OCalledPartyBusy ::= [PRIVATE 18] SET {
	billingID								[1] IMPLICIT BillingID,
	-- (Originating) M 6.5.2.16
	electronicSerialNumber					[9] IMPLICIT ElectronicSerialNumber OPTIONAL,
	-- M 6.5.2.63 a
	mscid									[21] IMPLICIT MSCID,
	-- (Originating MSC) M 6.5.2.82
	msid									MSID,
	-- M 6.5.2.bv b
	transactionCapability					[123] IMPLICIT TransactionCapability,
	-- M 6.5.2.160
	triggerType								[279] IMPLICIT TriggerType,
	-- M 6.5.2.dh
	winCapability							[280] IMPLICIT WINCapability,
	-- M 6.5.2.di
	callingPartyName						[243] IMPLICIT CallingPartyName OPTIONAL,
	-- O 6.5.2.bw c
	callingPartyNumberDigits1				[80] IMPLICIT CallingPartyNumberDigits1 OPTIONAL,
	-- O 6.5.2.21 c
	callingPartyNumberDigits2				[81] IMPLICIT CallingPartyNumberDigits2 OPTIONAL,
	-- O 6.5.2.22 c
	callingPartySubaddress					[84] IMPLICIT CallingPartySubaddress OPTIONAL,
	-- O 6.5.2.25 c
	carrierDigits							[86] IMPLICIT CarrierDigits OPTIONAL,
	-- O 6.5.2.28 d
	destinationDigits						[87] IMPLICIT	DestinationDigits OPTIONAL,
	-- O 6.5.2.56 e
	digits		 							[4] IMPLICIT Digits OPTIONAL,
	-- (Dialed) O 6.5.2.58 d
	failureCause							[387] IMPLICIT FailureCause OPTIONAL,
	--  O 6.5.2.cm f
	locationAreaID							[33] IMPLICIT LocationAreaID OPTIONAL,
	-- O 6.5.2.77 d, g
	mobileDirectoryNumber					[93] IMPLICIT MobileDirectoryNumber OPTIONAL,
	-- O 6.5.2.80 h
	mSCIdentificationNumber					[94] IMPLICIT MSCIdentificationNumber OPTIONAL,
	-- O 6.5.2.83 i
	pc-ssn									[32] IMPLICIT PC-SSN OPTIONAL,
	-- (Originating MSC) O 6.5.2.93 j
	redirectingNumberDigits					[100] IMPLICIT RedirectingNumberDigits OPTIONAL,
	-- O 6.5.2.114 c
	redirectingPartyName					[245] IMPLICIT RedirectingPartyName OPTIONAL,
	-- O 6.5.2.114 c
	routingDigits							[150] IMPLICIT RoutingDigits OPTIONAL,
	-- O 6.5.2.114 d
	servingCellID							[2] IMPLICIT ServingCellID OPTIONAL
	-- O 6.5.2.117 d, k
	}

-- OCalledPartyBusy RETURN RESULT Parameters
OCalledPartyBusyRes ::= [PRIVATE 18] SET {
	actionCode								[128] IMPLICIT ActionCode OPTIONAL,
	-- O 6.5.2.2 a
	announcementList						[130] IMPLICIT AnnouncementList OPTIONAL,
	-- O 6.5.2.6 b
	carrierDigits							[86] IMPLICIT CarrierDigits OPTIONAL,
	-- O 6.5.2.28 c
	dmh-AccountCodeDigits					[140] IMPLICIT DMH-AccountCodeDigits OPTIONAL,
	-- O 6.5.2.59 e
	dmh-AlternateBillingDigits				[141] IMPLICIT DMH-AlternateBillingDigits OPTIONAL,
	-- O 6.5.2.60 e
	dmh-BillingDigits						[142] IMPLICIT DMH-BillingDigits OPTIONAL,
	-- O 6.5.2.61 e
	dmh-ChargeInformation					[311] IMPLICIT DMH-ChargeInformation OPTIONAL,
	-- O 6.5.2.eo e, d
	dmh-RedirectionIndicator				[88] IMPLICIT DMH-RedirectionIndicator OPTIONAL,
	-- O 6.5.2.62 e, f
	dmh-ServiceID							[305] IMPLICIT DMH-ServiceID OPTIONAL,
	-- O 6.5.2.ei g
	noAnswerTime							[96] IMPLICIT NoAnswerTime OPTIONAL,
	-- O 6.5.2.87 h
	oneTimeFeatureIndicator					[97] IMPLICIT OneTimeFeatureIndicator OPTIONAL,
	-- O 6.5.2.88 i
	preferredLanguageIndicator				[147] IMPLICIT PreferredLanguageIndicator OPTIONAL,
	-- O 6.5.2.96 c, j
	redirectingNumberDigits					[100] IMPLICIT RedirectingNumberDigits OPTIONAL,
	-- O 6.5.2.107 k
	routingDigits							[150] IMPLICIT RoutingDigits OPTIONAL,
	-- O 6.5.2.114 c
	terminationList							[120] IMPLICIT TerminationList OPTIONAL,
	-- O 6.5.2.156 l
	triggerAddressList						[276] IMPLICIT TriggerAddressList OPTIONAL
	-- O 6.5.2.de m
	}

-- 6.4.2.ah ONoAnswer
ONoAnswer ::= [PRIVATE 18] SET {
	billingID								[1] IMPLICIT BillingID,
	-- (Originating) M 6.5.2.16
	electronicSerialNumber					[9] IMPLICIT ElectronicSerialNumber OPTIONAL,
	-- M 6.5.2.63 a
	mscid									[21] IMPLICIT MSCID,
	-- (Originating MSC) M 6.5.2.82
	msid									MSID OPTIONAL,
	-- M 6.5.2.bv b
	transactionCapability					[123] IMPLICIT TransactionCapability,
	-- M 6.5.2.160
	triggerType								[279] IMPLICIT TriggerType,
	-- M 6.5.2.dh
	winCapability							[280] IMPLICIT WINCapability,
	-- M 6.5.2.di
	callingPartyName						[243] IMPLICIT CallingPartyName OPTIONAL,
	-- O 6.5.2.bw c
	callingPartyNumberDigits1				[80] IMPLICIT CallingPartyNumberDigits1 OPTIONAL,
	-- O 6.5.2.21 c
	callingPartyNumberDigits2				[81] IMPLICIT CallingPartyNumberDigits2 OPTIONAL,
	-- O 6.5.2.22 c
	callingPartySubaddress					[84] IMPLICIT CallingPartySubaddress OPTIONAL,
	-- O 6.5.2.25 c
	carrierDigits							[86] IMPLICIT CarrierDigits OPTIONAL,
	-- O 6.5.2.28 d
	destinationDigits						[87] IMPLICIT	DestinationDigits OPTIONAL,
	-- O 6.5.2.56 e
	digits		 							[4] IMPLICIT Digits OPTIONAL,
	-- (Dialed) O 6.5.2.58 d
	locationAreaID							[33] IMPLICIT LocationAreaID OPTIONAL,
	-- O 6.5.2.77 d, f
	mobileDirectoryNumber					[93] IMPLICIT MobileDirectoryNumber OPTIONAL,
	-- O 6.5.2.80 g
	mSCIdentificationNumber					[94] IMPLICIT MSCIdentificationNumber OPTIONAL,
	-- O 6.5.2.83 h
	pc-ssn									[32] IMPLICIT PC-SSN OPTIONAL,
	-- (Originating MSC) O 6.5.2.93 i
	redirectingNumberDigits					[100] IMPLICIT RedirectingNumberDigits OPTIONAL,
	-- O 6.5.2.114 c
	redirectingPartyName					[245] IMPLICIT RedirectingPartyName OPTIONAL,
	-- O 6.5.2.114 c
	routingDigits							[150] IMPLICIT RoutingDigits OPTIONAL,
	-- O 6.5.2.114 d
	servingCellID							[2] IMPLICIT ServingCellID OPTIONAL
	-- O 6.5.2.117 d, j
	}

-- ONoAnswer RETURN RESULT Parameters
ONoAnswerRes ::= [PRIVATE 18] SET {
	actionCode								[128] IMPLICIT ActionCode OPTIONAL,
	-- O 6.5.2.2 a
	announcementList						[130] IMPLICIT AnnouncementList OPTIONAL,
	-- O 6.5.2.6 b
	carrierDigits							[86] IMPLICIT CarrierDigits OPTIONAL,
	-- O 6.5.2.28 c
	dmh-AccountCodeDigits					[140] IMPLICIT DMH-AccountCodeDigits OPTIONAL,
	-- O 6.5.2.59 e
	dmh-AlternateBillingDigits				[141] IMPLICIT DMH-AlternateBillingDigits OPTIONAL,
	-- O 6.5.2.60 e
	dmh-BillingDigits						[142] IMPLICIT DMH-BillingDigits OPTIONAL,
	-- O 6.5.2.61 e
	dmh-ChargeInformation					[311] IMPLICIT DMH-ChargeInformation OPTIONAL,
	-- O 6.5.2.eo e, d
	dmh-RedirectionIndicator				[88] IMPLICIT DMH-RedirectionIndicator OPTIONAL,
	-- O 6.5.2.62 e, f
	dmh-ServiceID							[305] IMPLICIT DMH-ServiceID OPTIONAL,
	-- O 6.5.2.ei g
	noAnswerTime							[96] IMPLICIT NoAnswerTime OPTIONAL,
	-- O 6.5.2.87 h
	oneTimeFeatureIndicator					[97] IMPLICIT OneTimeFeatureIndicator OPTIONAL,
	-- O 6.5.2.88 i
	preferredLanguageIndicator				[147] IMPLICIT PreferredLanguageIndicator OPTIONAL,
	-- O 6.5.2.96 c, j
	redirectingNumberDigits					[100] IMPLICIT RedirectingNumberDigits OPTIONAL,
	-- O 6.5.2.107 k
	routingDigits							[150] IMPLICIT RoutingDigits OPTIONAL,
	-- O 6.5.2.114 c
	terminationList							[120] IMPLICIT TerminationList OPTIONAL,
	-- O 6.5.2.156 l
	triggerAddressList						[276] IMPLICIT TriggerAddressList OPTIONAL
	-- O 6.5.2.de m
	}

-- 6.4.2.ai PositionRequest
PositionRequest ::= [PRIVATE 18] SET {
	mscid									[21] IMPLICIT MSCID,
	-- (Requesting) M 6.5.2.82 a
	positionInformationCode					[315] IMPLICIT PositionInformationCode,
	-- M 6.5.2.er b
	electronicSerialNumber					[9] IMPLICIT ElectronicSerialNumber OPTIONAL,
	-- O 6.5.2.63 c
	mobileDirectoryNumber					[93] IMPLICIT MobileDirectoryNumber OPTIONAL,
	-- O 6.5.2.80 d, e
	msid									MSID OPTIONAL,
	-- O 6.5.2.bv c, e
	senderIdentificationNumber				[103] IMPLICIT SenderIdentificationNumber OPTIONAL
	-- O 6.5.2.116 f
	}

-- PositionRequest RETURN RESULT Parameters
PositionRequestRes ::= [PRIVATE 18] SET {
	electronicSerialNumber					[9] IMPLICIT ElectronicSerialNumber OPTIONAL,
	-- O 6.5.2.63 a, b
	extendedMSCID							[53] IMPLICIT ExtendedMSCID OPTIONAL,
	-- O 6.5.2.64 c, d
	mSCIdentificationNumber					[94] IMPLICIT MSCIdentificationNumber OPTIONAL,
	-- (Serving MSC) O 6.5.2.83 a, d, e, f
	mscid									[21] IMPLICIT MSCID OPTIONAL,
	-- (Serving) O 6.5.2.82 g, d, h
	msid									MSID OPTIONAL,
	-- O 6.5.2.bv a, b
	mSStatus								[313] IMPLICIT MSStatus OPTIONAL,
	-- O 6.5.2.eq i, d
	pc-ssn									[32] IMPLICIT PC-SSN OPTIONAL,
	-- (Serving MSC) O 6.5.2.93 a, d, e, f
	pSID-RSIDInformation					[202] IMPLICIT PSID-RSIDInformation OPTIONAL,
	-- O 6.5.2.f j, a, d
	locationAreaID							[33] IMPLICIT LocationAreaID OPTIONAL,
	-- O 6.5.2.77 k, a, d
	servingCellID							[2] IMPLICIT ServingCellID OPTIONAL
	-- O 6.5.2.117 l, a, d
	}


-- 6.4.2.aj PositionRequestForward
PositionRequestForward ::= [PRIVATE 18] SET {
	interMSCCircuitID						[6] IMPLICIT InterMSCCircuitID,
	-- M 6.5.2.72
	positionInformationCode					[315] IMPLICIT PositionInformationCode,
	-- M 6.5.2.er a
	electronicSerialNumber					[9] IMPLICIT ElectronicSerialNumber OPTIONAL,
	-- O 6.5.2.bu b
	imsi									[242] IMPLICIT IMSI OPTIONAL,
	-- O 6.5.2.bu c, d
	mobileIdentificationNumber				[8] IMPLICIT MobileIdentificationNumber OPTIONAL
	-- O 6.5.2.81 c, d
	}

-- PositionRequestForward RETURN RESULT Parameters
PositionRequestForwardRes ::= [PRIVATE 18] SET {
	mscid									[21] IMPLICIT MSCID OPTIONAL,
	-- (Serving) O 6.5.2.82 a
	mSStatus								[313] IMPLICIT MSStatus OPTIONAL,
	-- O 6.5.2.eq b
	locationAreaID							[33] IMPLICIT LocationAreaID OPTIONAL,
	-- O 6.5.2.77 c, d
	servingCellID							[2] IMPLICIT ServingCellID OPTIONAL
	-- O 6.5.2.117 c, e
	}

-- J-STD-036-AD-2
CallTerminationReport ::= [PRIVATE 18] SET {
	billingID								[1] IMPLICIT BillingID OPTIONAL,
	-- O 6.5.2.16 a
	imsi									[242] IMPLICIT IMSI OPTIONAL,
	-- O 6.5.2.bu
	mobileIdentificationNumber				[8] IMPLICIT MobileIdentificationNumber OPTIONAL,
	-- O 6.5.2.81 b, c
	networkTMSI								[233] IMPLICIT NetworkTMSI OPTIONAL
	-- O 6.5.2.117 c
}

-- 6.4.2.am GeoPositionRequest (See J-STD-036, page 8-7) X.S0002-0 v2.0
GeoPositionRequest ::= [PRIVATE 18] SET {
	positionRequestType						[337] IMPLICIT PositionRequestType,
	--  M 6.5.2.fs
	billingID								[1] IMPLICIT BillingID OPTIONAL,
	-- O 6.5.2.16 h
	electronicSerialNumber					[9] IMPLICIT ElectronicSerialNumber OPTIONAL,
	-- O 6.5.2.63 b
	imsi									[242] IMPLICIT IMSI OPTIONAL,
	-- O 6.5.2.bu b
	lcsBillingID							[367] IMPLICIT LCSBillingID OPTIONAL,
	-- O 6.5.2.gx i
	lcs-Client-ID							[358] IMPLICIT LCS-Client-ID OPTIONAL,
	-- O 6.5.2.go b
	meid									[390] IMPLICIT MEID OPTIONAL,
	-- O 6.5.2.hv b
	mobileIdentificationNumber				[8] IMPLICIT MobileIdentificationNumber OPTIONAL,
	-- O 6.5.2.81 b
	mobilePositionCapability				[335] IMPLICIT MobilePositionCapability OPTIONAL,
	-- O 6.5.2.fm a
-- Mobinfo_AMPS **Macro** O 6.5.2.fn f expanded
 	channelData								[5] IMPLICIT ChannelData OPTIONAL,
	-- (Serving) M 6.5.2.47
	dtxIndication							[329] IMPLICIT DTXIndication OPTIONAL,
	-- O 6.5.2.fg a
 	receivedSignalQuality					[72] IMPLICIT ReceivedSignalQuality OPTIONAL,
	-- O 6.5.2.106 a
-- Mobinfo_CDMA **Macro** O 6.5.2.fo g expanded:
	cdmaChannelData							[63] IMPLICIT CDMAChannelData OPTIONAL,
	-- (Serving) O 6.5.2.30 c
	cdmaCodeChannel							[68] IMPLICIT CDMACodeChannel OPTIONAL,
	-- O 6.5.2.31 a
	cdmaMobileCapabilities					[330] IMPLICIT CDMAMobileCapabilities OPTIONAL,
	-- O 6.5.2.xx a
	cdmaPrivateLongCodeMask					[67] IMPLICIT CDMAPrivateLongCodeMask OPTIONAL,
	-- O 6.5.2.36 a
 	cdmaServingOneWayDelay2					[347] IMPLICIT	CDMAServingOneWayDelay2 OPTIONAL,
	-- O 6.5.2.gd a
	cdmaServiceOption						[175] IMPLICIT CDMAServiceOption OPTIONAL,
	-- O 6.5.2.f m
	cdmaTargetMAHOList						[136] IMPLICIT CDMATargetMAHOList OPTIONAL,
	-- O 6.5.2.43 g
	cdmaPSMMList							[346] IMPLICIT CDMAPSMMList OPTIONAL,
	-- O 6.5.2.gc a

-- Mobinfo_NAMPS **Macro** O 6.5.2.fp e expanded:
-- 	channelData								[5] IMPLICIT ChannelData OPTIONAL,
	-- (Serving) M 6.5.2.47
	 nampsChannelData							[76] IMPLICIT NAMPSChannelData OPTIONAL,
	-- (Serving) M 6.5.2.86
--	dtxIndication							[329] IMPLICIT DTXIndication OPTIONAL,
	-- O 6.5.2.fg a
-- 	receivedSignalQuality					[72] IMPLICIT ReceivedSignalQuality OPTIONAL,
	-- O 6.5.2.106 a
-- Mobinfo_TDMA **Macro** O 6.5.2.fq d expanded:
	tdmaChannelData							[28] IMPLICIT TDMAChannelData,
	-- M 6.5.2.153
--	dtxIndication							[329] IMPLICIT DTXIndication OPTIONAL,
	-- O 6.5.2.fg a
--	receivedSignalQuality					[72] IMPLICIT ReceivedSignalQuality OPTIONAL,
	-- O 6.5.2.106 a
	targetMeasurementList					[157] IMPLICIT TargetMeasurementList OPTIONAL,
	-- O 6.5.2.150 a
	tdma-MAHO-CELLID						[359] IMPLICIT TDMA-MAHO-CELLID OPTIONAL,
	-- O 2.3.2.26 b
	tdma-MAHO-CHANNEL						[360] IMPLICIT TDMA-MAHO-CHANNEL OPTIONAL,
	-- O 2.3.2.27 c
	tdma-TimeAlignment						[362] IMPLICIT TDMA-TimeAlignment OPTIONAL,
	-- O 2.3.2.29 d
	tdmaVoiceMode							[223] IMPLICIT TDMAVoiceMode OPTIONAL,
	-- O ANSI-41-E a
	voicePrivacyMask							[48] IMPLICIT VoicePrivacyMask OPTIONAL,
	-- O 6.5.2.166 a

	mscid									[21] IMPLICIT MSCID OPTIONAL,
	-- (Serving) O 6.5.2.82 b
	networkTMSI								[233] IMPLICIT NetworkTMSI OPTIONAL,
	-- O 6.5.2.bl b
-- PositionQualityOfService O 6.5.2.hc j MACRO expanded:
	pqos-HorizontalPosition					[372] IMPLICIT PQOS-HorizontalPosition OPTIONAL,
	-- O 6.5.2.hd a, b
	pqos-HorizontalVelocity					[373] IMPLICIT PQOS-HorizontalVelocity OPTIONAL,
	-- O 6.5.2.he c
	pqos-MaximumPositionAge					[374] IMPLICIT PQOS-MaximumPositionAge OPTIONAL,
	-- O 6.5.2.hf d
	pqos-PositionPriority					[375] IMPLICIT	PQOS-PositionPriority OPTIONAL,
	-- O 6.5.2.hg e
	pqos-ResponseTime						[376] IMPLICIT PQOS-ResponseTime OPTIONAL,
	-- O 6.5.2.hh f
	pqos-VerticalPosition					[377] IMPLICIT	PQOS-VerticalPosition OPTIONAL,
	-- O 6.5.2.hi g
	pqos-VerticalVelocity					[378] IMPLICIT PQOS-VerticalVelocity OPTIONAL,
	-- O 6.5.2.hj h
	servingCellID							[2] IMPLICIT ServingCellID OPTIONAL,
	-- O 6.5.2.117 b
	teleservice-Priority					[290] IMPLICIT Teleservice-Priority OPTIONAL
	-- O 6.5.2.dt c
}

-- 6.4.2.an InterSystemPositionRequest
InterSystemPositionRequest ::= [PRIVATE 18] SET {
	positionRequestType						[337] IMPLICIT PositionRequestType,
	--  M 6.5.2.fs
	actionCode								[128] IMPLICIT ActionCode OPTIONAL,
	-- O 6.5.2.2 o
	cdmaPSMMCount							[345] IMPLICIT CDMAPSMMCount OPTIONAL,
	-- O 6.5.2.gbh
	digits		 							[4] IMPLICIT Digits OPTIONAL,
	-- (Dialed) O 6.5.2.58 j
	electronicSerialNumber					[9] IMPLICIT ElectronicSerialNumber OPTIONAL,
	-- O 6.5.2.63 d
	emergencyServicesRoutingDigits			[239] IMPLICIT EmergencyServicesRoutingDigits OPTIONAL,
	-- O 6.5.2.bs d, f
	imsi									[242] IMPLICIT IMSI OPTIONAL,
	-- O 6.5.2.bu d
	lcsBillingID							[367] IMPLICIT LCSBillingID OPTIONAL,
	-- O 6.5.2.gx k
	lirAuthorization						[368] IMPLICIT LIRAuthorization OPTIONAL,
	-- O 6.5.2.gy l
	lcs-Client-ID							[358] IMPLICIT LCS-Client-ID OPTIONAL,
	-- O 6.5.2.go d
	meid									[390] IMPLICIT MEID OPTIONAL,
	-- O 6.5.2.hv d
	mobileDirectoryNumber					[93] IMPLICIT MobileDirectoryNumber OPTIONAL,
	-- O 6.5.2.80 d
	mobileIdentificationNumber				[8] IMPLICIT MobileIdentificationNumber OPTIONAL,
	-- O 6.5.2.81 d
-- MobInfo_AMPS **Macro** O 6.5.2.fn b, p f expanded:
 	channelData								[5] IMPLICIT ChannelData OPTIONAL,
	-- (Serving) M 6.5.2.47
	dtxIndication							[329] IMPLICIT DTXIndication OPTIONAL,
	-- O 6.5.2.fg a
 	receivedSignalQuality					[72] IMPLICIT ReceivedSignalQuality OPTIONAL,
	-- O 6.5.2.106 a

-- Mobinfo_CDMA **Macro** O 6.5.2.fo a, p f
	cdmaChannelData							[63] IMPLICIT CDMAChannelData OPTIONAL,
	-- (Serving) O 6.5.2.30 c
	cdmaCodeChannel							[68] IMPLICIT CDMACodeChannel OPTIONAL,
	-- O 6.5.2.31 a
	cdmaMobileCapabilities					[330] IMPLICIT CDMAMobileCapabilities OPTIONAL,
	-- O 6.5.2.xx a
	cdmaPrivateLongCodeMask					[67] IMPLICIT CDMAPrivateLongCodeMask OPTIONAL,
	-- O 6.5.2.36 a
 	cdmaServingOneWayDelay2					[347] IMPLICIT	CDMAServingOneWayDelay2 OPTIONAL,
	-- O 6.5.2.gd a
	cdmaServiceOption						[175] IMPLICIT CDMAServiceOption OPTIONAL,
	-- O 6.5.2.f m
	cdmaTargetMAHOList						[136] IMPLICIT CDMATargetMAHOList OPTIONAL,
	-- O 6.5.2.43 g
	cdmaPSMMList							[346] IMPLICIT CDMAPSMMList OPTIONAL,
	-- O 6.5.2.gc a

-- Mobinfo_NAMPS **Macro** O 6.5.2.fp c, p f expanded:
-- 	channelData								[5] IMPLICIT ChannelData OPTIONAL,
	-- (Serving) M 6.5.2.47
	nampsChannelData							[76] IMPLICIT NAMPSChannelData OPTIONAL,
	-- (Serving) M 6.5.2.86
--	dtxIndication							[329] IMPLICIT DTXIndication OPTIONAL,
	-- O 6.5.2.fg a
-- 	receivedSignalQuality					[72] IMPLICIT ReceivedSignalQuality OPTIONAL,
	-- O 6.5.2.106 a
-- Mobinfo_TDMA **Macro** O 6.5.2.fq g, p f expanded:
	tdmaChannelData							[28] IMPLICIT TDMAChannelData,
	-- M 6.5.2.153
--	dtxIndication							[329] IMPLICIT DTXIndication OPTIONAL,
	-- O 6.5.2.fg a
--	receivedSignalQuality					[72] IMPLICIT ReceivedSignalQuality OPTIONAL,
	-- O 6.5.2.106 a
	targetMeasurementList					[157] IMPLICIT TargetMeasurementList OPTIONAL,
	-- O 6.5.2.150 a
	tdma-MAHO-CELLID						[359] IMPLICIT TDMA-MAHO-CELLID OPTIONAL,
	-- O 2.3.2.26 b
	tdma-MAHO-CHANNEL						[360] IMPLICIT TDMA-MAHO-CHANNEL OPTIONAL,
	-- O 2.3.2.27 c
	tdma-TimeAlignment						[362] IMPLICIT TDMA-TimeAlignment OPTIONAL,
	-- O 2.3.2.29 d
	tdmaVoiceMode							[223] IMPLICIT TDMAVoiceMode OPTIONAL,
	-- O ANSI-41-E a
	voicePrivacyMask							[48] IMPLICIT VoicePrivacyMask OPTIONAL,
	-- O 6.5.2.166 a

	mobilePositionCapability				[335] IMPLICIT MobilePositionCapability OPTIONAL,
	-- O 6.5.2.fm e, f
	mpcAddress								[370] IMPLICIT MPCAddress OPTIONAL,
	-- O 6.5.2.ha s, u
	mpcAddressList							[381] IMPLICIT MPCAddressList OPTIONAL,
	-- O 6.5.2.hm t, u
	mpcid									[371] IMPLICIT MPCID OPTIONAL,
	-- O 6.5.2.hb m
	mscid									[21] IMPLICIT MSCID OPTIONAL,
	-- (Serving) O 6.5.2.82 q f
	networkTMSI								[233] IMPLICIT NetworkTMSI OPTIONAL,
	-- O 6.5.2.bl d
	pc-ssn									[32] IMPLICIT PC-SSN OPTIONAL,
	-- (Serving MSC) O 6.5.2.93 r
--	PositionQualityOfService O 6.5.2.hc n MACRO expanded:
	pqos-HorizontalPosition					[372] IMPLICIT PQOS-HorizontalPosition OPTIONAL,
	-- O 6.5.2.hd a, b
	pqos-HorizontalVelocity					[373] IMPLICIT PQOS-HorizontalVelocity OPTIONAL,
	-- O 6.5.2.he c
	pqos-MaximumPositionAge					[374] IMPLICIT PQOS-MaximumPositionAge OPTIONAL,
	-- O 6.5.2.hf d
	pqos-PositionPriority					[375] IMPLICIT	PQOS-PositionPriority OPTIONAL,
	-- O 6.5.2.hg e
	pqos-ResponseTime						[376] IMPLICIT PQOS-ResponseTime OPTIONAL,
	-- O 6.5.2.hh f
	pqos-VerticalPosition					[377] IMPLICIT	PQOS-VerticalPosition OPTIONAL,
	-- O 6.5.2.hi g
	pqos-VerticalVelocity					[378] IMPLICIT PQOS-VerticalVelocity OPTIONAL,
	-- O 6.5.2.hj h
	servingCellID							[2] IMPLICIT ServingCellID OPTIONAL,
	-- O 6.5.2.117 p f
	tdma-MAHORequest						[364] IMPLICIT TDMA-MAHORequest OPTIONAL
	-- O 6.5.2.gu
}

-- InterSystemPositionRequest RETURN RESULT Parameters
InterSystemPositionRequestRes ::= [PRIVATE 18] SET {
	positionResult							[338] IMPLICIT PositionResult,
	-- M 6.5.2.ft
	lcsBillingID							[367] IMPLICIT LCSBillingID OPTIONAL,
	-- O 6.5.2.gx i
	mobilePositionCapability				[335] IMPLICIT MobilePositionCapability OPTIONAL,
	-- O 6.5.2.fm e
-- MobInfo_AMPS **Macro** O 6.5.2.fn c, e expanded:
 	channelData								[5] IMPLICIT ChannelData OPTIONAL,
	-- (Serving) M 6.5.2.47
	dtxIndication							[329] IMPLICIT DTXIndication OPTIONAL,
	-- O 6.5.2.fg a
 	receivedSignalQuality					[72] IMPLICIT ReceivedSignalQuality OPTIONAL,
	-- O 6.5.2.106 a
-- MobInfo_CDMA **Macro** O 6.5.2.fo b, e expanded:
	cdmaChannelData							[63] IMPLICIT CDMAChannelData OPTIONAL,
	-- (Serving) O 6.5.2.30 c
	cdmaCodeChannel							[68] IMPLICIT CDMACodeChannel OPTIONAL,
	-- O 6.5.2.31 a
	cdmaMobileCapabilities					[330] IMPLICIT CDMAMobileCapabilities OPTIONAL,
	-- O 6.5.2.xx a
	cdmaPrivateLongCodeMask					[67] IMPLICIT CDMAPrivateLongCodeMask OPTIONAL,
	-- O 6.5.2.36 a
 	cdmaServingOneWayDelay2					[347] IMPLICIT	CDMAServingOneWayDelay2 OPTIONAL,
	-- O 6.5.2.gd a
	cdmaServiceOption						[175] IMPLICIT CDMAServiceOption OPTIONAL,
	-- O 6.5.2.f m
	cdmaTargetMAHOList						[136] IMPLICIT CDMATargetMAHOList OPTIONAL,
	-- O 6.5.2.43 g
	cdmaPSMMList							[346] IMPLICIT CDMAPSMMList OPTIONAL,
	-- O 6.5.2.gc a

-- MobInfo_NAMPS **Macro** O 6.5.2.fp g, e expended:
-- 	channelData								[5] IMPLICIT ChannelData OPTIONAL,
	-- (Serving) M 6.5.2.47
	nampsChannelData						[76] IMPLICIT NAMPSChannelData OPTIONAL,
	-- (Serving) M 6.5.2.86
--	dtxIndication							[329] IMPLICIT DTXIndication OPTIONAL,
	-- O 6.5.2.fg a
--	receivedSignalQuality					[72] IMPLICIT ReceivedSignalQuality OPTIONAL,
	-- O 6.5.2.106 a

-- MobInfo_TDMA **Macro** O 6.5.2.fq a, e
	tdmaChannelData							[28] IMPLICIT TDMAChannelData,
	-- M 6.5.2.153
--	dtxIndication							[329] IMPLICIT DTXIndication OPTIONAL,
	-- O 6.5.2.fg a
--	receivedSignalQuality					[72] IMPLICIT ReceivedSignalQuality OPTIONAL,
	-- O 6.5.2.106 a
	targetMeasurementList					[157] IMPLICIT TargetMeasurementList OPTIONAL,
	-- O 6.5.2.150 a
	tdma-MAHO-CELLID						[359] IMPLICIT TDMA-MAHO-CELLID OPTIONAL,
	-- O 2.3.2.26 b
	tdma-MAHO-CHANNEL						[360] IMPLICIT TDMA-MAHO-CHANNEL OPTIONAL,
	-- O 2.3.2.27 c
	tdma-TimeAlignment						[362] IMPLICIT TDMA-TimeAlignment OPTIONAL,
	-- O 2.3.2.29 d
	tdmaVoiceMode							[223] IMPLICIT TDMAVoiceMode OPTIONAL,
	-- O ANSI-41-E a
	voicePrivacyMask						[48] IMPLICIT VoicePrivacyMask OPTIONAL,
	-- O 6.5.2.166 a

	mscid									[21] IMPLICIT MSCID OPTIONAL,
	-- (Serving) O 6.5.2.82 f
	positionInformation						[336] IMPLICIT PositionInformation OPTIONAL,
	-- O 6.5.2.fr h
	servingCellID							[2] IMPLICIT ServingCellID OPTIONAL
	-- O 6.5.2.117 d
}
-- 6.4.2.ao InterSystemPositionRequestForward
InterSystemPositionRequestForward ::= [PRIVATE 18] SET {
	electronicSerialNumber					[9] IMPLICIT ElectronicSerialNumber OPTIONAL,
	-- M 6.5.2.63
	interMSCCircuitID						[6] IMPLICIT	InterMSCCircuitID,
	-- M 6.5.2.72
	positionRequestType						[337] IMPLICIT PositionRequestType,
	--  M 6.5.2.fs
	imsi									[242] IMPLICIT IMSI OPTIONAL,
	-- O 6.5.2.bu a
	lcsBillingID							[367] IMPLICIT LCSBillingID OPTIONAL,
	-- O 6.5.2.gx d
	lcs-Client-ID							[358] IMPLICIT LCS-Client-ID OPTIONAL,
	-- O 6.5.2.go a
	meid									[390] IMPLICIT MEID OPTIONAL,
	-- O 6.5.2.hv a
	mobileIdentificationNumber				[8] IMPLICIT MobileIdentificationNumber OPTIONAL,
	-- O 6.5.2.81 a
	mobilePositionCapability				[335] IMPLICIT MobilePositionCapability OPTIONAL,
	-- O 6.5.2.fm b
	mpcid									[371] IMPLICIT MPCID OPTIONAL,
	-- O 6.5.2.hb d
--	PositionQualityOfService O 6.5.2.hc d MACRO expanded:
	pqos-HorizontalPosition					[372] IMPLICIT PQOS-HorizontalPosition OPTIONAL,
	-- O 6.5.2.hd a, b
	pqos-HorizontalVelocity					[373] IMPLICIT PQOS-HorizontalVelocity OPTIONAL,
	-- O 6.5.2.he c
	pqos-MaximumPositionAge					[374] IMPLICIT PQOS-MaximumPositionAge OPTIONAL,
	-- O 6.5.2.hf d
	pqos-PositionPriority					[375] IMPLICIT	PQOS-PositionPriority OPTIONAL,
	-- O 6.5.2.hg e
	pqos-ResponseTime						[376] IMPLICIT PQOS-ResponseTime OPTIONAL,
	-- O 6.5.2.hh f
	pqos-VerticalPosition					[377] IMPLICIT	PQOS-VerticalPosition OPTIONAL,
	-- O 6.5.2.hi g
	pqos-VerticalVelocity					[378] IMPLICIT PQOS-VerticalVelocity OPTIONAL,
	-- O 6.5.2.hj h
 	tdma-MAHORequest						[364] IMPLICIT TDMA-MAHORequest OPTIONAL
	-- O 6.5.2.gu c
}
--InterSystemPositionRequestForward RETURN RESULT Parameters
InterSystemPositionRequestForwardRes ::= [PRIVATE 18] SET {
	mscid									[21] IMPLICIT MSCID,
	-- (Serving) M 6.5.2.82
	positionResult							[338] IMPLICIT PositionResult,
	-- M 6.5.2.ft
	lcsBillingID							[367] IMPLICIT LCSBillingID OPTIONAL,
	-- O 6.5.2.gx b
	positionInformation						[336] IMPLICIT PositionInformation OPTIONAL,
	-- O 6.5.2.fr a
	servingCellID							[2] IMPLICIT ServingCellID OPTIONAL
	-- O 6.5.2.117
}

-- 6.4.2.ap ACGDirective
ACGDirective  ::= [PRIVATE 18] SET {
	controlType								[341] IMPLICIT ControlType,
	-- M 6.5.2.fw a
	destinationAddress						DestinationAddress OPTIONAL,
	--M 6.5.2.cc b
	gapDuration								[342] IMPLICIT GapDuration OPTIONAL,
	-- O 6.5.2.fx c, e
	gapInterval								GapInterval OPTIONAL
	-- O 6.5.2.fy d, e

}

-- 6.4.2.aq RoamerDatabaseVerificationRequest

RoamerDatabaseVerificationRequest ::= [PRIVATE 18] SET {
	invokingNEType							[353] IMPLICIT InvokingNEType OPTIONAL,
	-- O 6.5.2.gj g
	mobileDirectoryNumber					[93] IMPLICIT MobileDirectoryNumber OPTIONAL,
	-- O 6.5.2.80 e, f
	mscid									[21] IMPLICIT MSCID OPTIONAL,
	-- (HLR) O 6.5.2.82 a
	msid									MSID OPTIONAL,
	-- O 6.5.2.bv b, f
	range									[352] IMPLICIT Range OPTIONAL
	-- O 6.5.2.gj c, d
	}

-- RoamerDatabaseVerificationRequest RETURN RESULT Parameters
RoamerDatabaseVerificationRequestRes ::= [PRIVATE 18] SET {
	transactionCapability					[123] IMPLICIT TransactionCapability OPTIONAL
	-- O 6.5.2.160
	}

-- 6.4.2.au LCSParameterRequest
LCSParameterRequest ::=  [PRIVATE 18] SET {
	mobileDirectoryNumber					[93] IMPLICIT MobileDirectoryNumber OPTIONAL,
	-- O 6.5.2.80 a
	mpcid									[371] IMPLICIT MPCID OPTIONAL,
	-- O 6.5.2.hbb
	msid									MSID OPTIONAL
	-- O 6.5.2.bv a
}
-- LCSParameterRequest RETURN RESULT Parameters
LCSParameterRequestRes ::= [PRIVATE 18] SET {
	accessDeniedReason						[20] IMPLICIT AccessDeniedReason OPTIONAL,
	-- O 6.5.2.1 a
	electronicSerialNumber					[9] IMPLICIT ElectronicSerialNumber OPTIONAL,
	-- O 6.5.2.63 b
	imsi									[242] IMPLICIT IMSI OPTIONAL,
	-- O 6.5.2.bu b, c
	meid									[390] IMPLICIT MEID OPTIONAL,
	-- O 6.5.2.hv j
	mobileDirectoryNumber					[93] IMPLICIT MobileDirectoryNumber OPTIONAL,
	-- O 6.5.2.80 b, c
	mobileIdentificationNumber				[8] IMPLICIT MobileIdentificationNumber OPTIONAL,
	-- O 6.5.2.81 b, c
	mobilePositionCapability				[335] IMPLICIT MobilePositionCapability OPTIONAL,
	-- O 6.5.2.fm d
	mpcAddress								[370] IMPLICIT MPCAddress OPTIONAL,
	-- O 6.5.2.ha e, g
	mpcAddressList							[381] IMPLICIT MPCAddressList OPTIONAL,
	-- O 6.5.2.hm f, g
	mscid									[21] IMPLICIT MSCID OPTIONAL,
	-- (Serving) O 6.5.2.82 h
	pc-ssn									[32] IMPLICIT PC-SSN OPTIONAL
	-- (Serving MSC) O 6.5.2.93
}

-- 3.2.2.1 CheckMEID (new) X.S0002-0 v1.0

CheckMEID ::= [PRIVATE 18] SET {
	digits		 							[4] IMPLICIT Digits OPTIONAL,
	-- (Dialed) M 6.5.2.58 a
	interMSCCircuitID						[6] IMPLICIT	InterMSCCircuitID,
	-- M 6.5.2.72
	msid									MSID OPTIONAL,
	-- M 6.5.2.bv b
	confidentialityModes					[39] IMPLICIT ConfidentialityModes OPTIONAL,
	-- O 6.5.2.50 c
	electronicSerialNumber					[9] IMPLICIT ElectronicSerialNumber OPTIONAL,
	-- O 6.5.2.63
	emergencyServicesRoutingDigits			[239] IMPLICIT EmergencyServicesRoutingDigits OPTIONAL
	-- O 6.5.bs d
}

-- CheckMEID RETURN RESULTParameters
CheckMEIDRes ::= [PRIVATE 18] SET {
	meidStatus								[391] IMPLICIT MEIDStatus OPTIONAL
	-- M 3.3.2.97 a
}
-- 6.4.2.ar AddService N.S0029-0 v1.0

AddService ::= [PRIVATE 18] SET {
	cdmaConnectionReferenceList				[212] IMPLICIT CDMAConnectionReferenceList OPTIONAL,
	-- M 6.5.2.aq IS-737 a
	cdmaServiceOptionList					[176] IMPLICIT CDMAServiceOptionList OPTIONAL,
	-- O 6.5.2.g TSB76 b
	digits		 							[4] IMPLICIT Digits OPTIONAL,
	-- (Dialed) O 6.5.2.58 d, e
	interMSCCircuitID						[6] IMPLICIT	InterMSCCircuitID OPTIONAL,
	-- O 6.5.2.72 f
	imsi									[242] IMPLICIT IMSI OPTIONAL,
	-- O 6.5.2.bu IS-751 c
	mobileIdentificationNumber				[8] IMPLICIT MobileIdentificationNumber OPTIONAL
	-- O 6.5.2.81 c
	}
-- Table ar3 AddService RETURN RESULT Parameters

AddServiceRes ::= [PRIVATE 18] SET {
	cdmaConnectionReferenceList				[212] IMPLICIT CDMAConnectionReferenceList OPTIONAL,
	-- O 6.5.2.aq IS-737 a
	cdmaServiceOptionList					[176] IMPLICIT CDMAServiceOptionList OPTIONAL,
	--O 6.5.2.g TSB76 b
	qosPriority								[348] IMPLICIT QoSPriority OPTIONAL,
	-- O 6.5.2.ge c
	reasonList								[218] IMPLICIT ReasonList OPTIONAL
	-- O 6.5.2.aw IS-737 d
--	SpecialHandling O 6.5.2.bt J-STD-034 e
	}

-- 6.4.2.as DropService N.S0029-0 v1.0
DropService ::= [PRIVATE 18] SET {
	billingID								[1] IMPLICIT BillingID,
	-- O 6.5.2.16 a
	cdmaConnectionReferenceList				[212] IMPLICIT CDMAConnectionReferenceList OPTIONAL,
	-- O 6.5.2.aq IS-737 b
	interMSCCircuitID						[6] IMPLICIT	InterMSCCircuitID,
	-- O 6.5.2.72 c
	imsi									[242] IMPLICIT IMSI OPTIONAL,
	-- O 6.5.2.bu IS-751 d
	mobileIdentificationNumber				[8] IMPLICIT MobileIdentificationNumber OPTIONAL,
	-- O 6.5.2.81 d
	releaseReason							[10] IMPLICIT ReleaseReason OPTIONAL
	-- O 6.5.2.111 e
	}
-- Table as3 DropService RETURN RESULT Parameters
DropServiceRes ::= [PRIVATE 18] SET {
	billingID								[1] IMPLICIT BillingID OPTIONAL
	-- O 6.5.2.16 a
	}

-- 6.4.2.ay PositionEventNotification
PositionEventNotification ::= [PRIVATE 18] SET {
	positionResult							[338] IMPLICIT PositionResult,
	-- M 6.5.2.ft a
	imsi									[242] IMPLICIT IMSI OPTIONAL,
	-- O 6.5.2.bj c, d
	lcsBillingID							[367] IMPLICIT LCSBillingID OPTIONAL,
	-- O 6.5.2.gx b
	mobileIdentificationNumber				[8] IMPLICIT MobileIdentificationNumber OPTIONAL
	-- O 6.5.2.81 c, d
}
-- PositionEventNotification RETURN RESULT Parameters
-- zero octets

-- 6.4.2.CC OTASPRequest
OTASPRequest ::= [PRIVATE 18] SET {
	actionCode								[128] IMPLICIT ActionCode OPTIONAL,
	-- O 6.5.2.2 a
	aKeyProtocolVersion						[181] IMPLICIT AKeyProtocolVersion OPTIONAL,
	-- O 6.5.2.lB b
	authenticationData						[161] IMPLICIT AuthenticationData OPTIONAL,
	-- O 6.5.2.9 c
	authenticationResponse					[35] IMPLICIT AuthenticationResponse OPTIONAL,
	-- O 6.5.2.10 c
	callHistoryCount						[38] IMPLICIT CallHistoryCount OPTIONAL,
	-- O 6.5.2.18 c
	electronicSerialNumber					[9] IMPLICIT ElectronicSerialNumber OPTIONAL,
	-- O 6.5.2.63 d
	msid									MSID OPTIONAL,
	-- O 6.5.2.81 e, d
	mobileStationMSID						MobileStationMSID OPTIONAL,
	-- O 6.5.2.oC f
	mobileStationPartialKey					[185] IMPLICIT MobileStationPartialKey OPTIONAL,
	-- O 6.5.2.pB g
	mscid									[21] IMPLICIT MSCID OPTIONAL,
	-- O 6.5.2.64 h
	newlyAssignedMSID						NewlyAssignedMSID OPTIONAL,
	--O 6.5.2.rB i
	randomVariable							[40] IMPLICIT RandomVariable OPTIONAL,
	-- O 6.5.2.101 c
	randomVariableBaseStation				[41] IMPLICIT RandomVariableBaseStation,
	-- O 6.5.2.102 m
	serviceIndicator						[193] IMPLICIT ServiceIndicator OPTIONAL,
	-- O 6.5.2.wB j
	systemCapabilities						[49] IMPLICIT SystemCapabilities OPTIONAL,
	-- O 6.5.2.146 k
	terminalType							[47] IMPLICIT TerminalType OPTIONAL,
	-- O 6.5.2.154
	meid									[390] IMPLICIT MEID OPTIONAL
	-- O
		}
-- Table 6.4.2.CCy OTASPRequest RETURN RESULT Parameters
OTASPRequestRes ::= [PRIVATE 18] SET {
	aKeyProtocolVersion						[181] IMPLICIT AKeyProtocolVersion OPTIONAL,
	-- O 6.5.2.lB a
	authenticationResponseBaseStation		[36] IMPLICIT AuthenticationResponseBaseStation OPTIONAL,
	-- O 6.5.2.11 g
	baseStationPartialKey					[183] IMPLICIT BaseStationPartialKey OPTIONAL,
	-- O 6.5.2.nB b
	denyAccess								[50] IMPLICIT DenyAccess OPTIONAL,
	-- O 6.5.2.54 c
	modulusValue							[186] IMPLICIT ModulusValue OPTIONAL,
	-- O 6.5.2.qB b
	otasp-ResultCode						[189] IMPLICIT OTASP-ResultCode OPTIONAL,
	-- O 6.5.2.sB d
	primitiveValue							[190] IMPLICIT PrimitiveValue OPTIONAL,
	-- O 6.5.2.tB b
	signalingMessageEncryptionReport		[194] IMPLICIT SignalingMessageEncryptionReport OPTIONAL,
	-- O 6.5.2.xB e
	ssdUpdateReport							[156] IMPLICIT SSDUpdateReport OPTIONAL,
	-- O 6.5.2.142 f
	uniqueChallengeReport					[124] IMPLICIT UniqueChallengeReport OPTIONAL,
	-- O 6.5.2.162 f
	voicePrivacyReport						[196] IMPLICIT VoicePrivacyReport OPTIONAL
	-- O 6.5.2.zB e
	}
	
-- 3.2.2.2 StatusRequest (new) X.S0008-0 v1.0
StatusRequest ::= [PRIVATE 18] SET {
	msid									MSID,
	-- M 2.153 a
	record-Type								[392] IMPLICIT Record-Type
	-- M 3.3.2.2 b
}

-- StatusRequest RETURN RESULT Parameters
StatusRequestRes ::= [PRIVATE 18] SET {
	information-Record						[389] IMPLICIT Information-Record OPTIONAL
	-- O 3.3.2.2
}

-- 2.35 InterSystemSMSDeliveryPointToPoint
InterSystemSMSDeliveryPointToPoint ::= [PRIVATE 18] SET {
	sms-BearerData							[105] IMPLICIT SMS-BearerData,
	-- M 2.233
	sms-TeleserviceIdentifier				[116] IMPLICIT SMS-TeleserviceIdentifier,
	-- M 2.246
	imsi									[242] IMPLICIT IMSI OPTIONAL,
	-- O 2.127 a
	mobileIdentificationNumber				[8] IMPLICIT MobileIdentificationNumber OPTIONAL,
	-- O 2.140 a
	signalingMessageEncryptionKey			[45] IMPLICIT SignalingMessageEncryptionKey OPTIONAL,
	-- O 2.228 b
	sms-MessageCount						[108] IMPLICIT SMS-MessageCount OPTIONAL,
	-- O 2.237 c
	sms-OriginalOriginatingAddress			[112] IMPLICIT SMS-OriginalOriginatingAddress OPTIONAL,
	-- O 2.242 d
	sms-OriginalOriginatingSubaddress		[113] IMPLICIT SMS-OriginalOriginatingSubaddress OPTIONAL
	-- O 2.243 e
}
InterSystemSMSDeliveryPointToPointRes ::= [PRIVATE 18] SET {
	sms-BearerData							[105] IMPLICIT SMS-BearerData OPTIONAL,
	-- O 2.233 a
	sms-CauseCode							[153] IMPLICIT SMS-CauseCode OPTIONAL
	-- O 2.234 b
}
-- 2.36 InterSystemSMSPage X.S0004-540-E v2.0
InterSystemSMSPage ::= [PRIVATE 18] SET {
	sms-BearerData							[105] IMPLICIT SMS-BearerData,
	-- M 2.236
	sms-TeleserviceIdentifier				[116] IMPLICIT SMS-TeleserviceIdentifier,
	-- M 2.249
	cdma2000MobileSupportedCapabilities		[321] IMPLICIT CDMA2000MobileSupportedCapabilities OPTIONAL,
	-- O 2.42 a
	cdmaSlotCycleIndex						[166] IMPLICIT CDMASlotCycleIndex OPTIONAL,
	-- O 2.71 b
	cdmaStationClassMark2					[177] IMPLICIT CDMAStationClassMark2 OPTIONAL,
	-- O 2.73 c, d
	electronicSerialNumber					[9] IMPLICIT ElectronicSerialNumber OPTIONAL,
	-- O 2.113 e
	imsi									[242] IMPLICIT IMSI OPTIONAL,
	-- O 2.130 f
	locationAreaID							[33] IMPLICIT LocationAreaID OPTIONAL,
	-- O 2.138 g
	mobileIdentificationNumber				[8] IMPLICIT MobileIdentificationNumber OPTIONAL,
	-- O 2.143 f
	networkTMSI								[233] IMPLICIT NetworkTMSI OPTIONAL,
	-- O 2.161 f
	pageIndicator							[71] IMPLICIT PageIndicator OPTIONAL,
	-- O 2.173 h
	pageResponseTime						[301] IMPLICIT PageResponseTime OPTIONAL,
	-- O 2.174 i
	sms-ChargeIndicator						[106] IMPLICIT SMS-ChargeIndicator OPTIONAL,
	-- O 2.238 j
	sms-DestinationAddress					[107] IMPLICIT SMS-DestinationAddress OPTIONAL,
	-- O 2.239 k
	sms-OriginalDestinationAddress			[110] IMPLICIT SMS-OriginalDestinationAddress OPTIONAL,
	-- O 2.243 l
	sms-OriginalDestinationSubaddress		[111] IMPLICIT SMS-OriginalDestinationSubaddress OPTIONAL,
	-- O 2.244 m
	sms-OriginalOriginatingAddress			[112] IMPLICIT SMS-OriginalOriginatingAddress OPTIONAL,
	-- O 2.245 n
	sms-OriginalOriginatingSubaddress		[113] IMPLICIT SMS-OriginalOriginatingSubaddress OPTIONAL,
	-- O 2.246 m
	sms-OriginatingAddress					[114] IMPLICIT SMS-OriginatingAddress OPTIONAL
	-- O 2.247 o
	}
-- 2.48 QualificationRequest2 X.S0004-540-E v2.0
QualificationRequest2 ::= [PRIVATE 18] SET {
	mscid									[21] IMPLICIT MSCID,
	-- (Serving MSC or Originating MSC) M 2.154
	qualificationInformationCode			[17] IMPLICIT QualificationInformationCode,
	-- M 2.190
	systemAccessType						[34] IMPLICIT SystemAccessType,
	-- M 2.261
	systemMyTypeCode						[22] IMPLICIT SystemMyTypeCode,
	-- (MSC or VLR) M 2.263
	transactionCapability					[123] IMPLICIT TransactionCapability,
	-- M 2.288 a
	cdmaNetworkIdentification				[232] IMPLICIT CDMANetworkIdentification OPTIONAL,
	-- (Serving) O 2.58 b
	controlChannelMode						[199] IMPLICIT ControlChannelMode OPTIONAL,
	-- O 2.88 c
	electronicSerialNumber					[9] IMPLICIT ElectronicSerialNumber OPTIONAL,
	-- O 2.113 d
	locationAreaID							[33] IMPLICIT LocationAreaID OPTIONAL,
	-- O 2.138 e
	mobileDirectoryNumber					[93] IMPLICIT MobileDirectoryNumber OPTIONAL,
	-- O 2.142 f
	mSCIdentificationNumber					[94] IMPLICIT MSCIdentificationNumber OPTIONAL,
	-- O 2.155 g
--	mscid									[21] IMPLICIT MSCID OPTIONAL,
	-- O 2.156 d, h
	nonPublicData							[200] IMPLICIT NonPublicData OPTIONAL,
	-- O 2.169
	serviceRedirectionCause					[237] IMPLICIT ServiceRedirectionCause OPTIONAL,
	-- O 2.225 i
	senderIdentificationNumber				[103] IMPLICIT SenderIdentificationNumber OPTIONAL,
	--  O 2.218 j
	terminalType							[47] IMPLICIT TerminalType OPTIONAL,
	-- O 2.281 k
	userGroup								[208] IMPLICIT UserGroup OPTIONAL,
	-- O 2.297 l
	userZoneData							[209] IMPLICIT UserZoneData OPTIONAL,
	-- O 2.298 m
	winCapability							[280] IMPLICIT WINCapability OPTIONAL
	-- O 2.303 n
}
QualificationRequest2Res ::= [PRIVATE 18] SET {
	systemMyTypeCode						[22] IMPLICIT SystemMyTypeCode,
	-- (VLR or HLR) M 2.263
	analogRedirectRecord					[225] IMPLICIT AnalogRedirectRecord OPTIONAL,
	-- O 2.8 a
	authorizationDenied						[13] IMPLICIT AuthorizationDenied OPTIONAL,
	-- O 2.19 b
	authorizationPeriod						[14] IMPLICIT AuthorizationPeriod OPTIONAL,
	-- O 2.20 c
	cdmaRedirectRecord						[229] IMPLICIT CDMARedirectRecord OPTIONAL,
	-- O 2.63 d
	controlChannelMode						[199] IMPLICIT ControlChannelMode OPTIONAL,
	-- O 2.88 e
	deniedAuthorizationPeriod				[167] IMPLICIT DeniedAuthorizationPeriod OPTIONAL,
	-- O 2.100 f
	digits		 							[4] IMPLICIT Digits OPTIONAL,
	-- (Carrier) O 2.106 g
--	digits		 							[4] IMPLICIT Digits OPTIONAL,
	-- (Destination) O 2.106 h, i
	electronicSerialNumber					[9] IMPLICIT ElectronicSerialNumber OPTIONAL,
	-- O 2.113 j
	imsi									[242] IMPLICIT IMSI OPTIONAL,
	-- O 2.130 k
	mobileIdentificationNumber				[8] IMPLICIT MobileIdentificationNumber OPTIONAL,
	-- O 2.143 k
	mscid									[21] IMPLICIT MSCID OPTIONAL,
	-- (HLR) O 2.154 l
--	Profile **Macro** O 2.185 m, n
	authenticationCapability				[78] IMPLICIT AuthenticationCapability OPTIONAL,
	-- O 6.5.2.8 a
	callingFeaturesIndicator				[25] IMPLICIT CallingFeaturesIndicator OPTIONAL,
	-- O 6.5.2.20 b
	carrierDigits							[86] IMPLICIT CarrierDigits OPTIONAL,
	-- O 6.5.2.28 c
	cdmaServiceOptionList					[176] IMPLICIT CDMAServiceOptionList OPTIONAL,
	-- O 6.5.2.g d
	controlNetworkID						[307] IMPLICIT ControlNetworkID OPTIONAL,
	-- O 6.5.2.ek u
	dmh-AccountCodeDigits					[140] IMPLICIT DMH-AccountCodeDigits OPTIONAL,
	-- O 6.5.2.59 d
	dmh-AlternateBillingDigits				[141] IMPLICIT DMH-AlternateBillingDigits OPTIONAL,
	-- O 6.5.2.60 d
	dmh-BillingDigits						[142] IMPLICIT DMH-BillingDigits OPTIONAL,
	-- O 6.5.2.61 d
	geographicAuthorization					[143] IMPLICIT GeographicAuthorization OPTIONAL,
	-- O 6.5.2.68 e
	meidValidated							[401] IMPLICIT MEIDValidated OPTIONAL,
	-- O 3.2.2.98
	messageWaitingNotificationCount			[92] IMPLICIT MessageWaitingNotificationCount OPTIONAL,
	-- O 6.5.2.78 f
	messageWaitingNotificationType			[145] IMPLICIT MessageWaitingNotificationType OPTIONAL,
	-- O 6.5.2.79 g
	mobileDirectoryNumber					[93] IMPLICIT MobileDirectoryNumber OPTIONAL,
	--  O 6.5.2.80 d
	mobilePositionCapability				[335] IMPLICIT MobilePositionCapability OPTIONAL,
	-- O 6.5.2.fm t TIA/EIA/J-STD-036-A
	originationIndicator					[23] IMPLICIT OriginationIndicator OPTIONAL,
	-- O 6.5.2.89 h
	originationTriggers						[98] IMPLICIT OriginationTriggers OPTIONAL,
	-- O 6.5.2.90 i
	pACAIndicator							[146] IMPLICIT PACAIndicator OPTIONAL,
	-- O 6.5.2.91 j
	preferredLanguageIndicator				[147] IMPLICIT PreferredLanguageIndicator OPTIONAL,
	-- O 6.5.2.96 k
	qosPriority								[348] IMPLICIT QoSPriority OPTIONAL,
	--6.5.2.ge z
	restrictionDigits						[227] IMPLICIT RestrictionDigits OPTIONAL,
	-- O 6.5.2.113 l
	routingDigits							[150] IMPLICIT RoutingDigits OPTIONAL,
	-- O 6.5.2.114 m
	pSID-RSIDList							[203] IMPLICIT PSID-RSIDList OPTIONAL,
	-- O 6 .5.2.ag u , w
	sms-OriginationRestrictions				[115] IMPLICIT SMS-OriginationRestrictions OPTIONAL,
	-- O 6.5.2.136 n
	sms-TerminationRestrictions				[117] IMPLICIT SMS-TerminationRestrictions OPTIONAL,
	-- O 6.5.2.138 o
	spinipin								[154] IMPLICIT SPINIPIN OPTIONAL,
	-- O 6.5.2.139 p
	spiniTriggers							[155] IMPLICIT SPINITriggers OPTIONAL,
	-- O 6.5.2.140 q
	tdmaDataFeaturesIndicator				[221] IMPLICIT TDMADataFeaturesIndicator OPTIONAL,
	-- O 6.5.2.az s
	terminationRestrictionCode				[24] IMPLICIT TerminationRestrictionCode OPTIONAL,
	-- O 6.5.2.157 r
	terminationTriggers						[122] IMPLICIT TerminationTriggers OPTIONAL,
	-- O 6.5.2.159 s
	triggerAddressList						[276] IMPLICIT TriggerAddressList OPTIONAL,
	-- O 6.5.2.de t
	userGroup								[208] IMPLICIT UserGroup OPTIONAL,
	-- O 6 .5.2.al p
	nonPublicData							[200] IMPLICIT NonPublicData OPTIONAL,
	-- O 6 .5.2.ad v
	userZoneData							[209] IMPLICIT UserZoneData OPTIONAL,
	-- O 6 .5.2.am v , w
	callingPartyCategory					[355] IMPLICIT CallingPartyCategory OPTIONAL,
	-- O 6.5.2.gl z
	lirMode									[369] IMPLICIT LIRMode OPTIONAL,
	-- O 6.5.2.gz z
-- END MACRO
	roamingIndication						[239] IMPLICIT RoamingIndication OPTIONAL,
	-- O 2.211 o
	serviceRedirectionInfo					[238] IMPLICIT ServiceRedirectionInfo OPTIONAL
	-- O 2.226 a, d
}
-- Parameters
-- 6.5.2.1
-- 1 0 0 1 0 1 0 0 (0x94)
AccessDeniedReason ::= ENUMERATED {
	not-used						( 0 ),
	unassigned-directory-number		( 1 ),
	inactive						( 2 ),
	busy							( 3 ),
	termination-denied				( 4 ),
	no-page-response				( 5 ),
	unavailable						( 6 ),
	service-Rejected-by-MS			( 7 ),
	services-Rejected-by-the-System	( 8 ),
	service-Type-Mismatch			( 9 ),
	service-Denied					( 10 ),
	position-Determination-Not-Supported (12)
	}
-- 6.5.2.2
-- 1 0 0 1 1 1 1 1 (0x9f)
-- 1 0 0 0 0 0 0 1 (0x81)
-- 0 0 0 0 0 0 0 0 (0x00) (128)
ActionCode ::= OCTET STRING

-- 6.5.2.3
-- 1 0 0 1 1 1 1 1 (0x9f)
-- 0 1 0 0 1 0 1 1 (0x4b) 75
AlertCode ::= OCTET STRING

-- 6.5.2.4
-- 1 0 0 1 1 1 1 1 (0x9f)
-- 1 0 0 0 0 0 0 1 (0x81)
-- 0 0 0 0 0 0 0 1 (0x01)(129)
AlertResult ::= OCTET STRING

-- 6.5.2.5
-- 1 0 0 1 1 1 1 1 (0x9f)
-- 0 1 0 0 1 1 0 0 (0x4c) 76
AnnouncementCode ::= OCTET STRING

-- 6.5.2.6
-- 1 0 1 1 1 1 1 1 (0x9f) (0xbf)(constructed encoding)
-- 1 0 0 0 0 0 0 1 (0x81)
-- 0 0 0 0 0 0 1 0 (0x02)(130)
AnnouncementList ::= SEQUENCE {
	announcementCode1	[ 76 ] IMPLICIT AnnouncementCode,
	announcementCode2	[ 76 ] IMPLICIT AnnouncementCode OPTIONAL
	}
	
-- 6.5.2.7
-- 1 0 0 1 1 1 1 1 (0x9f)
-- 0 1 0 0 1 1 0 1 (0x4d) (77)
AuthenticationAlgorithmVersion ::= OCTET STRING

-- 6.5.2.8
-- 1 0 0 1 1 1 1 1 (0x9f)
-- 0 1 0 0 1 1 1 0 (0x4e) 78
AuthenticationCapability ::= OCTET STRING

-- 6.5.2.9
-- 1 0 0 1 1 1 1 1 (0x9f)
-- 1 0 0 0 0 0 0 1 (0x81)
-- 0 0 1 0 0 0 0 1 (0x21)(161)
AuthenticationData ::= OCTET STRING

-- 6.5.2.10
-- 1 0 0 1 1 1 1 1 (0x9f)
-- 0 0 1 0 0 0 1 1 (0x23)(35)
AuthenticationResponse ::= OCTET STRING

-- 6.5.2.11
-- 1 0 0 1 1 1 1 1 (0x9f)
-- 0 0 1 0 0 1 0 0 (0x24)(36)
AuthenticationResponseBaseStation ::= OCTET STRING

-- 6.5.2.12
-- 1 0 0 1 1 1 1 1 (0x9f)
-- 0 0 1 0 0 1 0 1 (0x25)(37)
AuthenticationResponseUniqueChallenge ::= OCTET STRING

-- 6.5.2.13
-- 1 0 0 0 1 1 0 1 (0x8d)(13)
AuthorizationDenied ::= ENUMERATED {
	not-used								( 0 ),
	delinquent-account						( 1 ),
	invalid-serial-number					( 2 ),
	stolen-unit								( 3 ),
	duplicate-unit							( 4 ),
	unassigned-directory-number				( 5 ),
	unspecified								( 6 ),
	multiple-access							( 7 ),
	not-Authorized-for-the-MSC				( 8 ),
	missing-authentication-parameters		( 9 ),
	terminalType-mismatch					( 10 ),
	requested-Service-Code-Not-Supported	( 11 )
	 }

-- 6.5.2.14
-- 1 0 0 0 1 1 1 0 (0x8e)(14)
AuthorizationPeriod ::= OCTET STRING

-- 6.5.2.15
-- 1 0 0 1 1 1 1 1 (0x9f)
-- 0 1 0 1 1 0 1 0 (0x5a)(90)
AvailabilityType ::= OCTET STRING

-- 6.5.2.16 1 0 0 0 0 0 0 1 (0x81)(1)
BillingID ::= OCTET STRING

-- 6.5.2.17
-- 1 0 0 1 1 1 1 1 (0x9f)
-- 0 0 1 1 1 0 1 0 (0x3a)(58)
BorderCellAccess ::= ENUMERATED{
    not-used            ( 0 ),
    border-Cell-Access  ( 1 )
    }

-- 6.5.2.18
-- 1 0 0 1 1 1 1 1 (0x9f)
-- 0 0 1 0 0 1 1 0 (0x26)(38)
CallHistoryCount ::= INTEGER (0..63)

-- 6.5.2.19
-- 1 0 0 1 1 1 1 1 (0x9f)
-- 0 1 0 0 1 1 1 1 (0x4f)
CallHistoryCountExpected ::= INTEGER (0..63)

-- 6.5.2.20
-- 1 0 0 1 1 0 0 1 (0x99)(25)
CallingFeaturesIndicator ::= OCTET STRING

-- 6.5.2.21
-- 1 0 0 1 1 1 1 1 (0x9f)
-- 0 1 0 1 0 0 0 0 (0x50)(80)
CallingPartyNumberDigits1 ::= DigitsType

-- 6.5.2.22
-- 1 0 0 1 1 1 1 1 (0x9f)
-- 0 1 0 1 0 0 0 1
CallingPartyNumberDigits2 ::= DigitsType

-- 6.5.2.23
-- 1 0 0 1 1 1 1 1 (0x9f)
-- 0 1 0 1 0 0 1 0 (0x52)(82)
CallingPartyNumberString1 ::= DigitsType

-- 6.5.2.24
-- 1 0 0 1 1 1 1 1 (0x9f)
-- 0 1 0 1 0 0 1 1 (0x53)(83)
CallingPartyNumberString2 ::= DigitsType

-- 6.5.2.25
-- 1 0 0 1 1 1 1 1 (0x9f)
-- 0 1 0 1 0 1 0 0 (0x54)(84)
CallingPartySubaddress ::= Subaddress

-- 6.5.2.26
-- 1 0 0 1 1 1 1 1 (0x9f)
-- 0 0 1 1 1 0 0 1 (0x39)(57)
CancellationDenied ::= ENUMERATED {
	not-used					( 0 ),
	multipleAccess				( 1 ),
	busy						( 2 )
}

-- 6.5.2.27
-- 1 0 0 1 1 1 1 1 (0x9f)
-- 0 1 0 1 0 1 0 1 (0x55)(85)
CancellationType ::= OCTET STRING

-- 6.5.2.28
-- 1 0 0 1 1 1 1 1 (0x9f)
-- 0 1 0 1 0 1 1 0 (0x56)(86)
CarrierDigits ::= DigitsType

-- 6.5.2.29
-- 1 0 0 1 1 1 1 1 (0x9f)
-- 0 0 1 1 1 1 1 0 (0x3e)(62)
CDMACallMode ::= OCTET STRING

-- 6.5.2.30
-- 1 0 0 1 1 1 1 1 (0x9f)
-- 0 0 1 1 1 1 1 1 (0x3f)(63)
CDMAChannelData ::= OCTET STRING

-- 6.5.2.31
-- 1 0 0 1 1 1 1 1 (0x9f)
-- 0 1 0 0 0 1 0 0 (0x44)(68)
CDMACodeChannel ::= OCTET STRING

-- 6.5.2.32
-- 1 0 1 1 1 1 1 1 (0xbf)
-- 1 0 0 0 0 0 0 1 (0x81)
-- 0 0 0 0 0 0 1 1 (0x03)(131)
CDMACodeChannelInformation ::= SEQUENCE {
	targetCellID						[3] IMPLICIT TargetCellID,
	cdmaCodeChannel						[68] IMPLICIT CDMACodeChannel,
	cdmaPilotPN							[173] IMPLICIT CDMAPilotPN OPTIONAL,
	-- O 6.5.2.d a
	cdmaPowerCombinedIndicator			[228] IMPLICIT CDMAPowerCombinedIndicator OPTIONAL,
	-- O 6.5.2.bg b
...
}

-- 6.5.2.33
-- 1 0 1 1 1 1 1 1 (0x9f)
-- 1 0 0 0 0 0 0 1 (0x81)
-- 0 0 0 0 0 1 0 0 (0x04)(132)
CDMACodeChannelList ::= SEQUENCE OF [131] IMPLICIT CDMACodeChannelInformation
--
--	cdmaCodeChannelInformation	[9999] IMPLICIT CDMACodeChannelInformation,
--	cdmaCodeChannelInformation	[9999] IMPLICIT CDMACodeChannelInformation OPTIONAL
--	}

-- 6.5.2.34
-- 1 0 0 1 1 1 1 1 (0x9f)
-- 0 1 0 0 0 0 1 0 (0x42)(66)
CDMAMobileProtocolRevision ::= OCTET STRING

-- 6.5.2.35
-- 1 0 0 1 1 1 1 1 (0x9f)
-- 0 1 0 0 0 0 0 1 (0x41)(65)
CDMAPilotStrength ::=  OCTET STRING

-- 6.5.2.36
-- 1 0 0 1 1 1 1 1 (0x9f)
-- 0 1 0 0 0 0 1 1 (0x43)(67)
CDMAPrivateLongCodeMask ::= OCTET STRING

-- 6.5.2.37
-- 1 0 0 1 1 1 1 1 (0x9f)
-- 0 1 0 0 0 1 0 1 (0x45)(69)
CDMASearchWindow ::= OCTET STRING

-- 6.5.2.38
-- 1 0 0 1 1 1 1 1 (0x9f)
-- 0 0 1 1 1 1 0 0 (0x3c)(60)
CDMAServingOneWayDelay ::= OCTET STRING

-- 6.5.2.39
-- 1 0 0 1 1 1 1 1 (0x9f)
-- 0 1 0 0 0 0 0 0 (0x40) (64)
CDMASignalQuality ::= OCTET STRING

-- 6.5.2.40
-- 1 0 0 1 1 1 1 1 (0x9f)
-- 1 0 0 0 0 0 0 1 (0x81)
-- 0 0 1 0 0 1 1 0 (0x26)(166)
CDMASlotCycleIndex ::= OCTET STRING

-- 6.5.2.41 N.S0005-0 v 1.0
-- 1 0 0 1 1 1 1 1 (0x9f)
-- 0 0 1 1 1 0 1 1 (0x3b)(59)
CDMAStationClassMark ::= OCTET STRING

-- 6.5.2.42
-- 1 0 1 1 1 1 1 1 (0x9f)
-- 1 0 0 0 0 0 0 1 (0x81)
-- 0 0 0 0 0 1 1 1 (0x07)(135)
CDMATargetMAHOInformation ::= SEQUENCE {
	targetCellID			[3] IMPLICIT TargetCellID,
	cdmaPilotStrength		[65] IMPLICIT CDMAPilotStrength,
	cdmaTargetOneWayDelay	[61] IMPLICIT CDMATargetOneWayDelay
	}
	
-- 6.5.2.43
-- 1 0 1 1 1 1 1 1 (0x9f)
-- 1 0 0 0 0 0 0 1 (0x81)
-- 0 0 0 0 1 0 0 0 (0x08)(136)
CDMATargetMAHOList ::= SEQUENCE OF [135] IMPLICIT CDMATargetMAHOInformation
-- CDMATargetMAHOList ::= SEQUENCE OF CDMATargetMAHOInformation

--	cdmaTargetMAHOInformation	[9999] IMPLICIT CDMATargetMAHOInformation,
--	cdmaTargetMAHOInformation	[9999] IMPLICIT CDMATargetMAHOInformation OPTIONAL
--	}
	
-- 6.5.2.44
-- 1 0 1 1 1 1 1 1 (0x9f)
-- 1 0 0 0 0 0 0 1 (0x81)
-- 0 0 0 0 0 1 0 1 (0x05)(133)
CDMATargetMeasurementInformation ::= SEQUENCE {
	targetCellID			[3] IMPLICIT TargetCellID,
	cdmaSignalQuality		[64] IMPLICIT CDMASignalQuality,
	cdmaTargetOneWayDelay	[61] IMPLICIT CDMATargetOneWayDelay OPTIONAL
	}

-- 6.5.2.45
-- 1 0 1 1 1 1 1 1 (0x9f)
-- 1 0 0 0 0 0 0 1 (0x81)
-- 0 0 0 0 0 1 1 0 (0x06)(134)
CDMATargetMeasurementList ::= SEQUENCE OF [133] IMPLICIT CDMATargetMeasurementInformation
--{
--	cdmaTargetMeasurementInformation	[133] IMPLICIT CDMATargetMeasurementInformation,
--	cdmaTargetMeasurementInformation	[133] IMPLICIT CDMATargetMeasurementInformation OPTIONAL
--	}
	

-- 6.5.2.46
-- 1 0 0 1 1 1 1 1 (0x9f)
-- 0 0 1 1 1 1 0 1 (0x3d)(61)
CDMATargetOneWayDelay ::= OCTET STRING

-- 6.5.2.47
-- 1 0 0 0 0 1 0 1 (0x85)(0x5)
ChannelData ::= OCTET STRING

-- 6.5.2.48
-- 1 0 0 1 1 1 1 1 (0x9f)
-- 1 0 0 0 0 0 0 1 (0x81)
-- 0 0 1 0 0 0 1 0 (0x22)(162)
ConditionallyDeniedReason ::= ENUMERATED {
	not-used					( 0 ),
	waitable					( 1 ),
	...
}

-- 6.5.2.49
-- 1 0 0 1 1 1 1 1 (0x9f)
-- 1 0 0 0 0 0 0 1 (0x81)
-- 0 0 0 0 1 0 0 1 (0x09)(137)
ConferenceCallingIndicator ::= OCTET STRING

-- 6.5.2.50
-- 1 0 0 1 1 1 1 1 (0x9f)
-- 0 0 1 0 0 1 1 1 (0x27) (39)
ConfidentialityModes ::= OCTET STRING

-- 6.5.2.51
-- 1 0 0 1 1 1 1 1 (0x9f)
-- 0 0 1 1 0 1 1 1 (0x37)(55)
ControlChannelData ::= OCTET STRING

-- 6.5.2.52
-- 1 0 0 1 1 1 1 1 (0x9f)
-- 1 0 0 0 0 0 0 1 (0x81)
-- 0 0 0 0 1 0 1 0 (0x0a)(138)
CountUpdateReport ::= OCTET STRING

-- 6.5.2.53
-- 1 0 0 1 1 1 1 1 (0x9f)
-- 1 0 0 0 0 0 0 1 (0x81)
-- 0 0 1 0 0 1 1 1 (0x27)(167)
DeniedAuthorizationPeriod ::= OCTET STRING

-- 6.5.2.54
-- 1 0 0 1 1 1 1 1 (0x9f)
-- 0 0 1 1 0 0 1 0 (0x32)(50)
DenyAccess ::= ENUMERATED {
	not-used							( 0 ),
	unspecified							( 1 ),
	ssd-Update-failure					( 2 ),
	cOUNT-Update-failure				( 3 ),
	unique-Challenge-failure			( 4 ),
	aUTHR-mismatch						( 5 ),
	cOUNT-mismatch						( 6 ),
	process-collision					( 7 ),
	missing-authentication-parameters	( 8 ),
	terminalType-mismatch				( 9 ),
	mIN-IMSI-or-ESN-authorization-failure	( 10 ),
	...
}

--6.5.2.55
-- 1 0 0 1 1 1 1 1 (0x9f)
-- 0 1 0 0 1 0 0 1 (0x49)(73)
DeregistrationType ::= ENUMERATED {
	not-used								( 0 ),
	deregister-for-an-unspecified-reason	( 1 ),
	deregister-for-an-administrative-reason	( 2 ),
	deregister-due-to-MS-power-down			( 3 ),
	...
}

-- 6.5.2.56
-- 1 0 0 1 1 1 1 1 (0x9f)
-- 0 1 0 1 0 1 1 1 (0x57)(87)
DestinationDigits ::= DigitsType

-- 6.5.2.57
-- 1 0 0 1 1 1 1 1 (0x9f)
-- 1 0 0 0 0 0 0 1 (0x81)
-- 0 0 0 0 1 0 1 1 (0x0b)(139)
DigitCollectionControl ::= OCTET STRING

-- 6.5.2.58		
-- 1 0 0 0 0 1 0 0 (0x84)(0x4)
Digits ::= DigitsType

-- 6.5.2.59
-- 1 0 0 1 1 1 1 1 (0x9f)
-- 1 0 0 0 0 0 0 1 (0x81)
-- 0 0 0 0 1 1 0 0 (0x0c)(140)		
DMH-AccountCodeDigits ::=  DigitsType

-- 6.5.2.60
-- 1 0 0 1 1 1 1 1 (0x9f)
-- 1 0 0 0 0 0 0 1 (0x81)
-- 0 0 0 0 1 1 0 1 (0x0d)(141)
DMH-AlternateBillingDigits ::= DigitsType

-- 6.5.2.61
-- 1 0 0 1 1 1 1 1 (0x9f)
-- 1 0 0 0 0 0 0 1 (0x81)
-- 0 0 0 0 1 1 1 0 (0x0e)(142)
DMH-BillingDigits ::= DigitsType

-- 6.5.2.62
-- 1 0 0 1 1 1 1 1 (0x9f)
-- 0 1 0 1 1 0 0 0 (0x58)(88)

DMH-RedirectionIndicator ::= ENUMERATED {
	not-specified			(0),
	cfu						(1),
	cfb						(2),
	cfna					(3),
	cfo						(4),
	cd-Unspecified			(5),
	cd-PSTN					(6),
	cd-Private				(7),
	pstn-Tandem				(8),
	private					(9),
	busy					(10),
	inactive				(11),
	unassigned				(12),
	termination-denied		(13),
	cd-failure				(14),
	ect						(15),
	mah						(16),
	fa						(17),
	abandoned-call-leg		(18),
	pca-call-refused		(19),
	sca-call-refused		(20),
	dialogue				(21),
	cfd						(22),
	cd-local				(23),
	voice-mail-retrieval	(24)
}

-- 6.5.2.63		
-- 1 0 0 0 1 0 0 1 (0x89)(0x9)
ElectronicSerialNumber ::=  OCTET STRING

-- 6.5.2.64
-- 1 0 0 1 1 1 1 1 (0x9f)
-- 0 0 1 1 0 1 0 1 (0x35)(53)
ExtendedMSCID ::= OCTET STRING

-- 6.5.2.65
-- 1 0 0 1 1 1 1 1 (0x9f)
-- 0 0 1 1 0 1 1 0 (0x36)(54)
ExtendedSystemMyTypeCode ::= OCTET STRING

-- 6.5.2.66
-- FaultyParameter ::= OCTET STRING

-- 6.5.2.67
-- 1 0 0 1 0 0 1 0 (0x92)(18)
FeatureResult ::= ENUMERATED {
	not-used			( 0 ),
	unsuccessful		( 1 ),
	successful			( 2 ),
	...
}

-- 6.5.2.68
-- 1 0 0 1 1 1 1 1 (0x9f)
-- 1 0 0 0 0 0 0 1 (0x81)
-- 0 0 0 0 1 1 1 1 (0x0f)(143)
GeographicAuthorization ::= OCTET STRING

--6.5.2.69
-- 1 0 0 1 1 1 1 1 (0x9f)
-- 1 0 0 0 0 0 0 1 (0x81)
-- 0 0 1 0 0 0 1 1 (0x23)(163)
GroupInformation ::= OCTET STRING

-- 6.5.2.70
-- 1 0 0 1 1 1 1 0 (0x9e)(30)
HandoffReason ::= ENUMERATED {
	not-used			( 0 ),
	unspecified			( 1 ),
	weak-Signal			( 2 ),
	off-loading			( 3 ),
	anticipatory		( 4 )
}

-- 6.5.2.71
-- 1 0 0 1 1 1 1 1 (0x9f)
-- 1 0 0 0 0 0 0 1 (0x81)
-- 0 0 1 0 0 1 0 0 (0x24)(164)
HandoffState ::= OCTET STRING

-- 6.5.2.72		
-- 1 0 0 0 0 1 1 0 (0x86)(0x6)
InterMSCCircuitID  ::=  OCTET STRING

-- 6.5.2.73		
-- 1 0 0 0 0 1 1 1 (0x87)(0x7)
InterSwitchCount  ::=  INTEGER (0..255)

--6.5.2.74
-- 1 0 1 1 1 1 1 1 (0x9f)
-- 0 1 0 1 1 0 0 1 (0x59)(89)
IntersystemTermination ::= SEQUENCE {
	destinationDigits						[87] IMPLICIT	DestinationDigits,
	-- M 6.5.2.56
	mscid									[21] IMPLICIT MSCID,
	-- (serving) M 6.5.2.82
	accessDeniedReason						[20] IMPLICIT AccessDeniedReason OPTIONAL,
	-- O 6.5.2.1 a
	billingID								[1] IMPLICIT BillingID OPTIONAL,
	-- (terminating) O 6.5.2.16 b
	carrierDigits							[86] IMPLICIT CarrierDigits OPTIONAL,
	-- O 6.5.2.28 c, d
	electronicSerialNumber					[9] IMPLICIT ElectronicSerialNumber OPTIONAL,
	-- O 6.5.2.63 e
	imsi									[242] IMPLICIT IMSI OPTIONAL,
	-- 6.5.2.bu e, k
	legInformation							[144] IMPLICIT LegInformation OPTIONAL,
	-- O 6.5.2.75 f
	mobileDirectoryNumber					[93] IMPLICIT MobileDirectoryNumber OPTIONAL,
	-- O 6.5.2.80 d, e
	mobileIdentificationNumber				[8] IMPLICIT MobileIdentificationNumber OPTIONAL,
	-- O 6.5.2.81 e
	mSCIdentificationNumber					[94] IMPLICIT MSCIdentificationNumber OPTIONAL,
	-- O 6.5.2.83 g
	routingDigits							[150] IMPLICIT RoutingDigits OPTIONAL,
	-- O 6.5.2.114 d, h
	terminationTriggers						[122] IMPLICIT TerminationTriggers OPTIONAL,
	-- O 6.5.2.159 d, i
...
}

-- 6.5.2.75
-- 1 0 0 1 1 1 1 1 (0x9f)
-- 1 0 0 0 0 0 0 1 (0x81)
-- 0 0 0 1 0 0 0 0 (0x10)(144)
LegInformation ::= OCTET STRING

-- 6.5.2.76
-- 1 0 1 1 1 1 1 1 (0x9f)
-- 0 1 0 1 1 0 1 1 (0x5b)(91)
LocalTermination ::= SEQUENCE {
	electronicSerialNumber					[9] IMPLICIT ElectronicSerialNumber,
	-- M 6.5.2.63
	terminationTreatment					[121] IMPLICIT TerminationTreatment,
	-- M 6.5.2.158
	alertCode								[75] IMPLICIT AlertCode OPTIONAL,
	-- O 6.5.2.3 a, b
	carrierDigits							[86] IMPLICIT CarrierDigits OPTIONAL,
	-- O 6.5.2.28 b, c
	destinationDigits						[87] IMPLICIT	DestinationDigits OPTIONAL,
	-- O 6.5.2.56 d, e
	imsi									[242] IMPLICIT IMSI OPTIONAL,
	-- 6.5.2.bu e, k
	legInformation							[144] IMPLICIT LegInformation OPTIONAL,
	-- O 6.5.2.75 a
	mobileDirectoryNumber					[93] IMPLICIT MobileDirectoryNumber OPTIONAL,
	-- O 6.5.2.80 b, f
	mobileIdentificationNumber				[8] IMPLICIT MobileIdentificationNumber,
	-- M 6.5.2.81
	oneTimeFeatureIndicator					[97] IMPLICIT OneTimeFeatureIndicator OPTIONAL,
	-- O 6.5.2.88 b, g
	routingDigits							[150] IMPLICIT RoutingDigits OPTIONAL,
	-- O 6.5.2.114 b, h
	terminationTriggers						[122] IMPLICIT TerminationTriggers OPTIONAL,
	-- O 6.5.2.159 a, b
	voiceMailboxPIN							[159] IMPLICIT VoiceMailboxPIN OPTIONAL,
	-- O 6.5.2.165 i
	voiceMailboxNumber						[160] IMPLICIT VoiceMailboxNumber OPTIONAL,
	-- O 6.5.2.164 j
	...
	}

-- 6.5.2.77
-- 1 0 0 1 1 1 1 1 (0x9f)
-- 0 0 1 0 0 0 0 1 (0x21)(33)
LocationAreaID ::= OCTET STRING

-- 6.5.2.78
-- 1 0 0 1 1 1 1 1 (0x9f)
-- 0 1 0 1 1 1 0 0 (0x5c)(92)
MessageWaitingNotificationCount::= OCTET STRING

-- 6.5.2.79
-- 1 0 0 1 1 1 1 1 (0x9f)
-- 1 0 0 0 0 0 0 1 (0x81)
-- 0 0 0 1 0 0 0 1 (0x11)(145)
MessageWaitingNotificationType ::=  OCTET STRING

-- 1 0 0 1 1 1 1 1 (0x9f)
-- 0 1 0 1 1 1 0 1 (0x5d)(93)
-- 6.5.2.80
MobileDirectoryNumber ::= DigitsType

-- 6.5.2.81		
-- 1 0 0 0 1 0 0 0 (0x88)(0x8)
MobileIdentificationNumber ::= MINType
--N.S0011-0 v 1.0
-- b. Refer to the MINType parameter type (see 6.5.3.u1) for notes and field encoding.

-- 6.5.2.82
-- 1 0 0 1 0 1 0 1 (0x95)
MSCID ::= OCTET STRING

-- 6.5.2.83
-- 1 0 0 1 1 1 1 1 (0x9f)
-- 0 1 0 1 1 1 1 0 (0x5e)(94)
MSCIdentificationNumber ::= DigitsType

-- 6.5.2.84
-- 1 0 0 1 1 1 1 1 (0x9f)
-- 0 1 0 0 0 1 1 0 (0x46)(70)
MSLocation ::=  OCTET STRING

-- 6.5.2.85
-- 1 0 0 1 1 1 1 1 (0x9f)
-- 1 0 0 0 0 0 0 1 (0x81)
-- 0 0 1 0 0 1 0 1 (0x25)(165)
NAMPSCallMode ::= OCTET STRING

-- 6.5.2.86
-- 1 0 0 1 1 1 1 1 (0x9f)
-- 0 1 0 0 1 0 1 0 (0x4a)(76)
NAMPSChannelData ::= OCTET STRING

-- 6.5.2.87
-- 1 0 0 1 1 1 1 1 (0x9f)
-- 0 1 1 0 0 0 0 0 (0x60)(96)
NoAnswerTime ::= OCTET STRING

-- 6.5.2.88
-- 1 0 0 1 1 1 1 1 (0x9f)
-- 0 1 1 0 0 0 0 1 (0x61)(97)
OneTimeFeatureIndicator ::= OCTET STRING

-- 6.5.2.89
-- 1 0 0 1 0 1 1 1 (0x97)(23)
OriginationIndicator ::= ENUMERATED {
	not-used					( 0 ),
	prior-agreement				( 1 ),
	origination-denied			( 2 ),
	local-calls-only			( 3 ),
	selected-leading-digits-of-directorynumber-or-of-international-E164-number	( 4 ),
	selected-leading-digits-of-directorynumber-or-of-international-E164-number-and-local-calls-only		( 5 ),
	national-long-distance			( 6 ),
	international-calls			( 7 ),
	single-directory-number-or-international-E164-number		( 8 ),
	...
	}
-- 6.5.2.90
-- 1 0 0 1 1 1 1 1 (0x9f)
-- 0 1 1 0 0 0 1 0 (0x62)
OriginationTriggers ::= OCTET STRING

-- 6.5.2.91
-- 1 0 0 1 1 1 1 1 (0x9f)
-- 1 0 0 0 0 0 0 1 (0x81)
-- 0 0 0 1 0 0 1 0 (0x12)(146)
PACAIndicator ::= OCTET STRING

-- 6.5.2.92
-- 1 0 0 1 1 1 1 1 (0x9f)
-- 0 1 0 0 0 1 1 1 (0x47)(71)
PageIndicator ::= OCTET STRING

-- 6.5.2.93
-- 1 0 0 1 1 1 1 1 (0x9f)
-- 0 0 1 0 0 0 0 0 (0x20)
PC-SSN ::= OCTET STRING

-- 6.5.2.94
-- 1 0 0 1 1 1 1 1 (0x9f)
-- 1 0 0 0 0 0 0 1 (0x81)
-- 0 0 1 0 1 0 0 1 (0x29)(169)
PilotBillingID ::= OCTET STRING

-- 6.5.2.95
-- 1 0 0 1 1 1 1 1 (0x9f)
-- 1 0 0 0 0 0 0 1 (0x81)
-- 0 0 1 0 1 0 0 0 (0x28)(168)
PilotNumber ::= DigitsType

-- 6.5.2.96
-- 1 0 0 1 1 1 1 1 (0x9f)
-- 1 0 0 0 0 0 0 1 (0x81)
-- 0 0 0 1 0 0 1 1 (0x13)(147)
PreferredLanguageIndicator ::= OCTET STRING

-- 6.5.2.97 Profile MACRO ?
-- Profile ::= SET {
--	authenticationCapability				[78] IMPLICIT AuthenticationCapability OPTIONAL,
	-- O 6.5.2.8 a
--	callingFeaturesIndicator				[25] IMPLICIT CallingFeaturesIndicator OPTIONAL,
	-- O 6.5.2.20 b
--	carrierDigits							[86] IMPLICIT CarrierDigits OPTIONAL,
	-- O 6.5.2.28 c
--	cdmaServiceOptionList					[176] IMPLICIT CDMAServiceOptionList OPTIONAL,
	-- O 6.5.2.g d
--	controlNetworkID						[307] IMPLICIT ControlNetworkID OPTIONAL,
	-- O 6.5.2.ek u
--	dmh-AccountCodeDigits					[140] IMPLICIT DMH-AccountCodeDigits OPTIONAL,
	-- O 6.5.2.59 d
--	dmh-AlternateBillingDigits				[141] IMPLICIT DMH-AlternateBillingDigits OPTIONAL,
	-- O 6.5.2.60 d
--	dmh-BillingDigits						[142] IMPLICIT DMH-BillingDigits OPTIONAL,
	-- O 6.5.2.61 d
--	geographicAuthorization					[143] IMPLICIT GeographicAuthorization OPTIONAL,
	-- O 6.5.2.68 e
--	messageWaitingNotificationCount			[92] IMPLICIT MessageWaitingNotificationCount OPTIONAL,
	-- O 6.5.2.78 f
--	messageWaitingNotificationType			[145] IMPLICIT MessageWaitingNotificationType OPTIONAL,
	-- O 6.5.2.79 g
--	mobileDirectoryNumber					[93] IMPLICIT MobileDirectoryNumber OPTIONAL,
	--  O 6.5.2.80 d
--	mobilePositionCapability				[335] IMPLICIT MobilePositionCapability OPTIONAL,
	-- O 6.5.2.fm t TIA/EIA/J-STD-036-A
--	originationIndicator					[23] IMPLICIT OriginationIndicator OPTIONAL,
	-- O 6.5.2.89 h
--	originationTriggers						[98] IMPLICIT OriginationTriggers,
	-- O 6.5.2.90 i
--	pACAIndicator							[274] IMPLICIT PACAIndicator OPTIONAL,
	-- O 6.5.2.91 j
--	preferredLanguageIndicator				[147] IMPLICIT PreferredLanguageIndicator OPTIONAL,
	-- O 6.5.2.96 k
--	qosPriority								[348] IMPLICIT QoSPriority OPTIONAL,
	--6.5.2.ge z
--	restrictionDigits						[227] IMPLICIT RestrictionDigits OPTIONAL,
	-- O 6.5.2.113 l
--	routingDigits							[150] IMPLICIT RoutingDigits OPTIONAL,
	-- O 6.5.2.114 m
--	pSID-RSIDList							[203] IMPLICIT PSID-RSIDList OPTIONAL,
	-- O 6 .5.2.ag u , w
--	sms-OriginationRestrictions				[115] IMPLICIT SMS-OriginationRestrictions OPTIONAL,
	-- O 6.5.2.136 n
--	sms-TerminationRestrictions				[117] IMPLICIT SMS-TerminationRestrictions OPTIONAL,
	-- O 6.5.2.138 o
--	spinipin								[154] IMPLICIT SPINIPIN OPTIONAL,
	-- O 6.5.2.139 p
--	spiniTriggers							[155] IMPLICIT SPINITriggers OPTIONAL,
	-- O 6.5.2.140 q
--	tdmaDataFeaturesIndicator				[221] IMPLICIT TDMADataFeaturesIndicator OPTIONAL,
	-- O 6.5.2.az s
--	terminationRestrictionCode				[24] IMPLICIT TerminationRestrictionCode OPTIONAL,
	-- O 6.5.2.157 r
--	terminationTriggers						[122] IMPLICIT TerminationTriggers OPTIONAL,
	-- O 6.5.2.159 s
--	triggerAddressList						[276] IMPLICIT TriggerAddressList OPTIONAL,
	-- O 6.5.2.de t
--	userGroup								[208] IMPLICIT UserGroup OPTIONAL,
	-- O 6 .5.2.al p
--	nonPublicData							[200] IMPLICIT NonPublicData OPTIONAL,
	-- O 6 .5.2.ad v
--	userZoneData							[209] IMPLICIT UserZoneData OPTIONAL,
	-- O 6 .5.2.am v , w
--	callingPartyCategory					[355] IMPLICIT CallingPartyCategory OPTIONAL,
	-- O 6.5.2.gl z
--	...,
--	lirMode									[369] IMPLICIT LIRMode OPTIONAL
	-- O 6.5.2.gz z
--	}
-- END MACRO

--	authenticationCapability				[78] IMPLICIT AuthenticationCapability OPTIONAL O 6.5.2.8 a
--	callingFeaturesIndicator				[25] IMPLICIT CallingFeaturesIndicator OPTIONAL, O 6.5.2.20 b
--	carrierDigits							[86] IMPLICIT CarrierDigits OPTIONAL,  O 6.5.2.28 c
--	dmh-AccountCodeDigits					[140] IMPLICIT DMH-AccountCodeDigits OPTIONAL, O 6.5.2.59 d
--	dmh-AlternateBillingDigits				[141] IMPLICIT DMH-AlternateBillingDigits OPTIONAL, O 6.5.2.60 d
--	dmh-BillingDigits						[142] IMPLICIT DMH-BillingDigits OPTIONAL, O 6.5.2.61 d
--	geographicAuthorization					[143] IMPLICIT GeographicAuthorization OPTIONAL, O 6.5.2.68 e
--	messageWaitingNotificationCount			[92] IMPLICIT MessageWaitingNotificationCount OPTIONAL, O 6.5.2.78 f
--	messageWaitingNotificationType			[145] IMPLICIT MessageWaitingNotificationType OPTIONAL, O 6.5.2.79 g
--	mobileDirectoryNumber					[93] IMPLICIT MobileDirectoryNumber OPTIONAL,  O 6.5.2.80 d
--	originationIndicator					[23] IMPLICIT OriginationIndicator OPTIONAL, O 6.5.2.89 h
--	originationTriggers						[98] IMPLICIT OriginationTriggers,  O 6.5.2.90 i
--	pACAIndicator							[274] IMPLICIT PACAIndicator OPTIONAL, O 6.5.2.91 j
--	preferredLanguageIndicator				[147] IMPLICIT PreferredLanguageIndicator OPTIONAL, O 6.5.2.96 k
--	restrictionDigits						[227] IMPLICIT RestrictionDigits OPTIONAL, O 6.5.2.113 l
--	routingDigits							[150] IMPLICIT RoutingDigits OPTIONAL, O 6.5.2.114 m
--	sms-OriginationRestrictions				[115] IMPLICIT SMS-OriginationRestrictions OPTIONAL, O 6.5.2.136 n
--	sms-TerminationRestrictions				[117] IMPLICIT SMS-TerminationRestrictions OPTIONAL, O 6.5.2.138 o
--	spinipin								[154] IMPLICIT SPINIPIN OPTIONAL, O 6.5.2.139 p
--	spiniTriggers							[155] IMPLICIT SPINITriggers OPTIONAL, O 6.5.2.140 q
--	terminationRestrictionCode				[24] IMPLICIT TerminationRestrictionCode OPTIONAL, O 6.5.2.157 r
--	terminationTriggers						[122] IMPLICIT TerminationTriggers OPTIONAL, O 6.5.2.159 s
--	triggerAddressList						[276] IPMPLICIT TriggerAddressList OPTIONAL, O 6.5.2.de t

-- 6.5.2.98
-- 1 0 1 1 1 1 1 1 (0x9f)
-- 0 1 0 1 1 1 1 1 (0x5f)(95)
PSTNTermination ::= SEQUENCE {
	destinationDigits						[87] IMPLICIT	DestinationDigits,
	-- M 6.5.2.56
	carrierDigits							[86] IMPLICIT CarrierDigits OPTIONAL,
	-- O 6.5.2.28 a, b
	electronicSerialNumber					[9] IMPLICIT ElectronicSerialNumber,
	-- O 6.5.2.63 c
	imsi									[242] IMPLICIT IMSI,
	-- 6.5.2.bu
	legInformation							[144] IMPLICIT LegInformation OPTIONAL,
	-- O 6.5.2.75 d
	mobileIdentificationNumber				[8] IMPLICIT MobileIdentificationNumber OPTIONAL,
	-- O 6.5.2.81 c, e
	routingDigits							[150] IMPLICIT RoutingDigits OPTIONAL,
	-- O 6.5.2.114 b, e
	terminationTriggers						[122] IMPLICIT TerminationTriggers OPTIONAL,
	-- O 6.5.2.159 b, f
	...
	}

--  6.5.2.99
-- 1 0 0 1 0 0 0 1 (0x91)(17)
QualificationInformationCode ::= ENUMERATED {
	not-used					( 0 ),
	no-information				( 1 ),
	validation-only				( 2 ),
	validation-and-profile		( 3 ),
	profile-only				( 4 )
	}

-- 6.5.2.100
-- 1 0 0 1 1 1 1 1 (0x9f)
-- 0 1 1 0 0 0 1 1 (0x43)(67)
RANDC ::= OCTET STRING

-- 6.5.2.101
-- 1 0 0 1 1 1 1 1 (0x9f)
-- 0 0 1 0 1 0 0 0 (0x28)(40)
RandomVariable ::= OCTET STRING

-- 6.5.2.102
-- 1 0 0 1 1 1 1 1 (0x9f)
-- 0 0 1 0 1 0 0 1 (0x29)(41)
RandomVariableBaseStation ::= OCTET STRING

-- 6.5.2.103
-- 1 0 0 1 1 1 1 1 (0x9f)
-- 0 0 1 0 1 0 1 0 (0x2a)(42)
RandomVariableSSD ::= OCTET STRING

-- 6.5.2.104
-- 1 0 0 1 1 1 1 1 (0x9f)
-- 0 0 1 0 1 0 1 1 (0x2b)(43)
RandomVariableUniqueChallenge ::= OCTET STRING

-- 6.5.2.105
-- 1 0 0 1 1 1 1 1 (0x9f)
-- 1 0 0 0 0 0 0 1 (0x81)
-- 0 0 0 1 0 1 0 0 (0x14)(148)
RANDValidTime ::= OCTET STRING

-- 6.5.2.106
-- 1 0 0 1 1 1 1 1 (0x9f)
-- 0 1 0 0 1 0 0 0 (0x48)(72)
ReceivedSignalQuality ::= INTEGER (0..255)

-- 6.5.2.107
-- 1 0 0 1 1 1 1 1 (0x9f)
-- 0 1 1 0 0 1 0 0 (0x64)(100)
RedirectingNumberDigits ::= DigitsType

-- 6.5.2.108
-- 1 0 0 1 1 1 1 1 (0x9f)
-- 0 1 1 0 0 1 0 1 (0x65)(101)
RedirectingNumberString ::= DigitsType

-- 6.5.2.109
-- 1 0 0 1 1 1 1 1 (0x9f)
-- 0 1 1 0 0 1 1 0 (0x66)(102)
RedirectingSubaddress ::= Subaddress

-- 6.5.2.110 RedirectionReason updated N.S0021
-- 1 0 0 1 0 0 1 1 (0x93)(19)
RedirectionReason ::= ENUMERATED {
	not-used						(0),
	busy							(1),
	no-Answer						(2),
	unconditional					(3),
	no-Page-Response				(4),
	unavailable						(5),
	unroutable						(6),
	call-accepted					(7),
	call-refused					(8),
	uSCFvm-Divert-to-voice-mail		(9),
	uSCFms-Divert-to-an-MS-provided-DN	(10),
	uSCFnr-Divert-to-a-network-registered-DN (11),
	...
	}

-- 6.5.2.111 ReleaseReason  updated N.S0029-0 v1.0
-- 1 0 0 0 1 0 1 0 (0x8a)
ReleaseReason ::= ENUMERATED {
	unspecified					(0),
	callOverClearForward		(1),
	callOverClearBackward		(2),
	handoffSuccessful			(3),
	handoffAbort-call-over		(4),
	handoffAbort-not-received	(5),
	abnormalMobileTermination	(6),
	abnormalSwitchTermination	(7),
	specialFeatureRelease		(8),
	sessionOverClearForward		(9),
	sessionOverClearBackward	(10),
	clearAllServicesForward		(11),
	clearAllServicesBackward	(12),
	anchor-MSC-was-removed-from-the-packet-data-session	(13),
	keep-MS-on-traffic-channel	(14),
	...
	}

-- 6.5.2.112
-- 1 0 0 1 1 1 1 1 (0x9f)
-- 0 0 1 0 1 1 0 0 (0x2c)
ReportType ::= ENUMERATED {
	not-used							( 0 ),
	unspecified-security-violation		( 1 ),
	mSID-ESN-mismatch					( 2 ),
	rANDC-mismatch						( 3 ),
	reserved							( 4 ),
	sSD-update-failed					( 5 ),
	reserved							( 6 ),
	cOUNT-mismatch						( 7 ),
	reserved							( 8 ),
	unique-Challenge-failed				( 9 ),
	unsolicited-Base-Station-Challenge	( 10 ),
	sSD-Update-no-response				( 11 ),
	cOUNT-Update-no-response			( 12 ),
	unique-Challenge-no-response		( 13 ),
	aUTHR-mismatch						( 14 ),
	tERMTYP-mismatch					( 15 ),
	missing-authentication-parameters	( 16 ),
	...
	}


-- 6.5.2.113
-- 1 0 0 1 1 1 1 1 (0x9f)
-- 1 0 0 0 0 0 0 1 (0x81)
-- 0 0 0 1 0 1 0 1 (0x15)(227)
RestrictionDigits ::= DigitsType

-- 6.5.2.114
-- 1 0 0 1 1 1 1 1 (0x9f)
-- 1 0 0 0 0 0 0 1 (0x81)
-- 0 0 0 1 0 1 1 0 (0x16)(150)
RoutingDigits ::= DigitsType

-- 6.5.2.115
-- 1 0 0 0 1 1 1 1 (0x8f)
SeizureType  ::= ENUMERATED {
	unspecified					( 0 ),
	loop-back					( 1 ),
	...
	}

-- 6.5.2.116
-- 1 0 0 1 1 1 1 1 (0x9f)
-- 0 1 1 0 0 1 1 1
SenderIdentificationNumber ::= DigitsType

-- 6.5.2.117	
-- 1 0 0 0 0 0 1 0 (0x82)(0x2)
ServingCellID ::= OCTET STRING

-- 6.5.2.118
-- 1 0 0 1 1 1 1 1 (0x9f)
-- 1 0 0 0 0 0 0 1 (0x81)
-- 0 0 0 1 0 1 1 1 (0x17)(151)
SetupResult ::= OCTET STRING

-- 6.5.2.119
-- 1 0 0 1 1 1 1 1 (0x9f)
-- 0 0 1 0 1 1 1 0 (0x2e)(46)
SharedSecretData ::= OCTET STRING

-- 6.5.2.120
-- 1 0 0 1 1 1 1 1 (0x9f)
-- 0 0 1 0 1 1 0 1 (0x2d)(45)
SignalingMessageEncryptionKey ::= OCTET STRING

-- 6.5.2.121
-- 1 0 0 0 1 0 1 1 (0x8b)(11)
SignalQuality ::= INTEGER{
	not-a-usable-signal (0),
	treat-as-Not-a-usable-signal (1),
	treat-as-Not-a-usable-signal (2),
	treat-as-Not-a-usable-signal (3),
	treat-as-Not-a-usable-signal (4),
	treat-as-Not-a-usable-signal (5),
	treat-as-Not-a-usable-signal (6),
	treat-as-Not-a-usable-signal (7),
	treat-as-Not-a-usable-signal (8),
	usable-signal-range (9),
	usable-signal-range (245),
	treat-the-same-as-interference (246),
	treat-the-same-as-interference (247),
	treat-the-same-as-interference (248),
	treat-the-same-as-interference (249),
	treat-the-same-as-interference (250),
	treat-the-same-as-interference (251),
	treat-the-same-as-interference (252),
	treat-the-same-as-interference (253),
	treat-the-same-as-interference (254),
	interference (255)
} (0..255)

-- 6.5.2.122
-- 1 0 0 1 1 1 1 1 (0x9f)
-- 1 0 0 0 0 0 0 1 (0x81)
-- 0 0 0 1 1 0 0 0 (0x18)(152)
SMS-AccessDeniedReason ::= OCTET STRING

-- 6.5.2.123
-- 1 0 0 1 1 1 1 1 (0x9f)
-- 0 1 1 0 1 0 0 0 (0x68)(104)
SMS-Address ::= DigitsType

-- 6.5.2.124
-- 1 0 0 1 1 1 1 1 (0x9f)
-- 0 1 1 0 1 0 0 1 (0x69)(105)
SMS-BearerData ::= OCTET STRING

-- 6.5.2.125
-- 1 0 0 1 1 1 1 1 (0x9f)
-- 1 0 0 0 0 0 0 1 (0x81)
-- 0 0 0 1 1 0 0 1 (0x19)(153)
SMS-CauseCode ::= OCTET STRING

-- 6.5.2.126
-- 1 0 0 1 1 1 1 1 (0x9f)
-- 0 1 1 0 1 0 1 0 (0x6a)(106)
SMS-ChargeIndicator ::= OCTET STRING

-- 6.5.2.127
-- 1 0 0 1 1 1 1 1 (0x9f)
-- 0 1 1 0 1 0 1 1 (0x6b)(107)
SMS-DestinationAddress ::= DigitsType

-- 6.5.2.128
-- 1 0 0 1 1 1 1 1 (0x9f)
-- 0 1 1 0 1 1 0 0 (0x6c)(108)
SMS-MessageCount ::= OCTET STRING

-- 6.5.2.129
-- 1 0 0 1 1 1 1 1 (0x9f)
-- 0 1 1 1 0 1 1 0 (0x76)(118)
SMS-MessageWaitingIndicator ::= NULL

-- 6.5.2.130
-- 1 0 0 1 1 1 1 1 (0x9f)
-- 0 1 1 0 1 1 0 1 (0x6d)(109)
SMS-NotificationIndicator ::= OCTET STRING

-- 6.5.2.131
-- 1 0 0 1 1 1 1 1 (0x9f)
-- 0 1 1 0 1 1 1 0 (0x6e)(110)
SMS-OriginalDestinationAddress ::= DigitsType

-- 6.5.2.132
-- 1 0 0 1 1 1 1 1 (0x9f)
-- 0 1 1 0 1 1 1 1 (0x6f)(111)
SMS-OriginalDestinationSubaddress ::= Subaddress

-- 6.5.2.133
-- 1 0 0 1 1 1 1 1 (0x9f)
-- 0 1 1 1 0 0 0 0 (0x70)(112)
SMS-OriginalOriginatingAddress ::= DigitsType

-- 1 0 0 1 1 1 1 1 (0x9f)
-- 0 1 1 1 0 0 0 1 (0x71)(113)
-- 6.5.2.134
SMS-OriginalOriginatingSubaddress ::= Subaddress

-- 6.5.2.135
-- 1 0 0 1 1 1 1 1 (0x9f)
-- 0 1 1 1 0 0 1 0 (0x72)(114)
SMS-OriginatingAddress ::= DigitsType

-- 1 0 0 1 1 1 1 1 (0x9f)
-- 0 1 1 1 0 0 1 1 (0x73)(115)
-- 6.5.2.136
SMS-OriginationRestrictions ::= OCTET STRING

-- 6.5.2.137
-- N.S0005-0 v 1.0
-- 1 0 0 1 1 1 1 1 (0x9f)
-- 0 1 1 1 0 1 0 0 (0x74)(116)
SMS-TeleserviceIdentifier ::= OCTET STRING
-- SMS-TeleserviceIdentifier ::= INTEGER

-- 6.5.2.138
-- 1 0 0 1 1 1 1 1 (0x9f)
-- 0 1 1 1 0 1 0 1 (0x75)(117)
SMS-TerminationRestrictions ::= OCTET STRING

-- 6.5.2.139
-- 1 0 0 1 1 1 1 1 (0x9f)
-- 1 0 0 0 0 0 0 1 (0x81)
-- 0 0 0 1 1 0 1 0 (0x1a)(154)
SPINIPIN ::= DigitsType

-- 6.5.2.140
-- 1 0 0 1 1 1 1 1 (0x9f)
-- 1 0 0 0 0 0 0 1 (0x81)
-- 0 0 0 1 1 0 1 1 (0x1b)(155)
SPINITriggers ::= OCTET STRING

-- 6.5.2.141
-- 1 0 0 1 1 1 1 1 (0x9f)
-- 0 0 1 1 0 1 0 0 (0x34) (52)
SSDNotShared ::= ENUMERATED {
	not-used					( 0 ),
	discard-SSD					( 1 ),
	...
	}
-- 6.5.2.142
-- 1 0 0 1 1 1 1 1 (0x9f)
-- 1 0 0 0 0 0 0 1 (0x81)
-- 0 0 0 1 1 1 0 0 (0x1c)(156)
SSDUpdateReport ::= OCTET STRING

-- 6.5.2.143
-- 1 0 0 0 1 1 0 0 (0x8c)(18)
StationClassMark ::= OCTET STRING


-- 6.5.2.144
-- 1 0 0 1 1 1 1 1 (0x9f)
-- 0 0 1 1 1 0 0 0 (0x38)(56)
SystemAccessData ::= OCTET STRING

-- 6.5.2.145
-- 1 0 0 1 1 1 1 1 (0x9f) (0x9c)
-- 0 0 1 0 0 0 1 0 (0x22)(34)
SystemAccessType  ::= ENUMERATED {
	not-used					(0),
	unspecified					(1),
	flash-request				(2),
	autonomous-registration		(3),
	call-origination			(4),
	page-response				(5),
	no-access					(6),
	power-down-registration		(7),
	sms-page-response			(8),
	otasp						(9),
	...
	}

-- 6.5.2.146
-- 1 0 0 1 1 1 1 1 (0x9f) (0x9c)
-- 0 0 1 1 0 0 0 1 (0x31)(49)
SystemCapabilities ::= OCTET STRING

-- 6.5.2.147
--  1 0 0 1 0 1 1 0 (0x96)(22)
SystemMyTypeCode ::= ENUMERATED {
	not-used					( 0 ),
	eDS							( 1 ),
	astronet					( 2 ),
	lucent-Technologies			( 3 ),
	ericsson					( 4 ),
	gTE							( 5 ),
	motorola					( 6 ),
	nEC							( 7 ),
	nORTEL						( 8 ),
	novAtel						( 9 ),
	plexsys						( 10 ),
	digital-Equipment-Corp		( 11 ),
	iNET						( 12 ),
	bellcore					( 13 ),
	alcatel-SEL					( 14 ),
	compaq						( 15 ),
	qUALCOMM					( 16 ),
	aldiscon					( 17 ),
	celcore						( 18 ),
	tELOS						( 19 ),
	aDI-Limited					( 20 ),
	coral-Systems				( 21 ),
	synacom-Technology			( 22 ),
	dSC							( 23 ),
	mCI							( 24 ),
	newNet						( 25 ),
	sema-Group-Telecoms			( 26 ),
	lG-Information-and-Communications	( 27 ),
	cBIS						( 28 ),
	siemens						( 29 ),
	samsung-Electronics			( 30 ),
	readyCom-Inc				( 31 ),
	aG-Communication-Systems	( 32 ),
	hughes-Network-Systems		( 33 ),
	phoenix-Wireless-Group		( 34 )
	}


-- 6.5.2.148
-- 1 0 0 0 0 0 1 1  (0x83)(0x3)
TargetCellID ::= OCTET STRING

-- 6.5.2.149
-- 1 0 1 1 1 1 1 1 (0x9f)
-- 1 0 0 0 0 0 0 1 (0x81)
-- 0 0 0 1 1 1 0 1 (0x1d)(157)
TargetMeasurementInformation ::= SEQUENCE{
	 targetCellID		[3] IMPLICIT TargetCellID,
	 -- M 6.5.2.148
	signalQuality		[11] IMPLICIT SignalQuality,
	-- M 6.5.2.121
	...
	}
-- 6.5.2.150
-- 1 0 1 1 1 1 1 1 (0x9f)
-- 1 0 0 0 0 0 0 1 (0x81)
-- 0 0 0 1 1 1 1 0 (0x1e)(158)
TargetMeasurementList ::= SEQUENCE OF [157] IMPLICIT TargetMeasurementInformation

-- 6.5.2.151
-- 1 0 0 1 1 1 1 1 (0x9f)
-- 0 0 0 1 1 1 1 1 (0x1f)(31)
TDMABurstIndicator ::= OCTET STRING

-- 6.5.2.152
-- 1 0 0 1 1 1 0 1 (0x9d)(29)
TDMACallMode ::= OCTET STRING

-- 6.5.2.153
-- 1 0 0 1 1 1 0 0 (0x9c)(28)
TDMAChannelData ::= OCTET STRING

-- 6.5.2.154
-- 1 0 0 1 1 1 1 1 (0x9f)
-- 0 0 1 0 1 1 1 1 (0x2f)(47)
TerminalType ::= ENUMERATED {
	not-used					( 0 ),
	not-distinguished			( 1 ),
	iS-54-B						( 2 ),
	iS-136						( 3 ),
	j-STD-011					( 4 ),
	iS-136-A-or-TIA-EIA-136-Revision-0	( 5 ),
	tIA-EIA-136-A				( 6 ),
	iA-EIA-136-B				( 7 ),
	iS-95						( 32 ),
	iS-95B						( 33 ),
	j-STD-008					( 34 ),
	tIA-EIA-95-B				( 35 ),
	iS-2000						( 36 ),
	iS-88						( 64 ),
	iS-94						( 65 ),
	iS-91						( 66 ),
	j-STD-014					( 67 ),
	tIA-EIA-553-A				( 68 ),
	iS-91-A						( 69 ),
	...
	}

-- 6.5.2.155
-- 1 0 0 1 1 1 1 1 (0x9f)
-- 0 1 1 1 0 1 1 1 (0x77)(119)
TerminationAccessType ::= OCTET STRING

-- 6.5.2.156
-- 1 0 1 1 1 1 1 1 (0x9f)
-- 0 1 1 1 1 0 0 0 (0x78)(120)
TerminationList ::= SET OF CHOICE {
	intersystemTermination	[89] IMPLICIT IntersystemTermination,
	-- O 6.5.2.74 b, c, d
	localTermination		[91] IMPLICIT LocalTermination,
	-- O 6.5.2.76 b, c, e
	pstnTermination			[95] IMPLICIT PSTNTermination,
	-- O 6.5.2.98 b, c, f
	...
	}

-- 6.5.2.157
-- 1 0 0 1 1 0 0 0 (0x98)(24)
TerminationRestrictionCode ::= ENUMERATED {
	not-used					( 0 ),
	termination-denied			( 1 ),
	unrestricted				( 2 ),
	the-treatment-for-this-value-is-not-specified	( 3 ),
	...
	}

-- 6.5.2.158
-- 1 0 0 1 1 1 1 1 (0x9f)
-- 0 1 1 1 1 0 0 1 (0x79)(121)
TerminationTreatment ::= OCTET STRING

-- 1 0 0 1 1 1 1 1 (0x9f)
-- 0 1 1 1 1 0 1 0 (0x7a)(122)
-- 6.5.2.159
TerminationTriggers ::= OCTET STRING

-- 6.5.2.160
-- 1 0 0 1 1 1 1 1 (0x9f)
-- 0 1 1 1 1 0 1 1 (0x9b)(123)
TransactionCapability ::= OCTET STRING

-- 6.5.2.161
-- 1 0 0 1 0 0 0 0 (0x90)(16)
TrunkStatus ::= ENUMERATED {
	idle					( 0 ),
	blocked					( 1 ),
	...
	}

-- 6.5.2.162
-- 1 0 0 1 1 1 1 1 (0x9f)
-- 0 1 1 1 1 1 0 0 (0x7c)(124)
UniqueChallengeReport ::= OCTET STRING

-- 6.5.2.163
-- 1 0 0 1 1 1 1 1 (0x9f)
-- 0 0 1 1 0 0 1 1 (0x33) (51)
UpdateCount ::= ENUMERATED {
	not-used		( 0 ),
	update-COUNT	( 1 ),
	...
	}

-- 6.5.2.164
-- 1 0 0 1 1 1 1 1 (0x9f)
-- 1 0 0 0 0 0 0 1 (0x81)
-- 0 0 1 0 0 0 0 0 (0x20)(160)
VoiceMailboxNumber ::= DigitsType

-- 6.5.2.165
-- 1 0 0 1 1 1 1 1 (0x9f)
-- 1 0 0 0 0 0 0 1 (0x81)
-- 0 0 0 1 1 1 1 1 (0x1f)(159)
VoiceMailboxPIN ::= DigitsType


-- 6.5.2.166
-- 1 0 0 1 1 1 1 1 (0x9f)
-- 0 0 1 1 0 0 0 0 (0x30)(48)
VoicePrivacyMask ::= OCTET STRING


-- 6.5.2.a N.S0010-0 v 1.0
-- 1 0 0 1 1 1 1 1 (0x9f)
-- 1 0 0 0 0 0 0 1 (0x81)
-- 0 0 1 0 1 0 1 0 (0x2a)(170)
-- a. See CDMA [TSB76] for the definition of this parameter.
CDMABandClass ::= OCTET STRING

-- 6.5.2.b N.S0010-0 v 1.0 N.S0006
-- 1 0 1 1 1 1 1 1 (0x9f)
-- 1 0 0 0 0 0 0 1 (0x81)
-- 0 0 1 0 1 0 1 1 (0x2b)(171)
CDMABandClassInformation ::= SEQUENCE{
	cdmaBandClass							[170] IMPLICIT CDMABandClass,
	-- M 6.5.2.a a
	cdmaMobileProtocolRevision				[66] IMPLICIT CDMAMobileProtocolRevision OPTIONAL,
	-- O 6.5.2.34 b
	cdmaStationClassMark2					[177] IMPLICIT CDMAStationClassMark2 OPTIONAL,
	-- O 6.5.2.h b
	...
}	

-- 6.5.2.c N.S0010-0 v 1.0
-- 1 0 1 1 1 1 1 1 (0x9f)
-- 1 0 0 0 0 0 0 1 (0x81)
-- 0 0 1 0 1 1 0 0 (0x2c)(172)
CDMABandClassList ::= SEQUENCE OF [171] IMPLICIT CDMABandClassInformation

-- 6.5.2.d N.S0010-0 v 1.0 N.S0006
-- 1 0 0 1 1 1 1 1 (0x9f)
-- 1 0 0 0 0 0 0 1 (0x81)
-- 0 0 1 0 1 1 0 1 (0x2d)(173)
CDMAPilotPN ::= OCTET STRING

-- 6.5.2.e (TSB76) N.S0010-0 v 1.0
-- 1 0 0 1 1 1 1 1 (0x9f)
-- 1 0 0 0 0 0 0 1 (0x81)
-- 0 0 1 0 1 1 1 0 (0x2e)(174)
CDMAServiceConfigurationRecord ::= OCTET STRING
-- a.	This field carries the CDMA Service Configuration Record. The bit-layout is the
--		same as that of Service Configuration Record in TSB74, and J-STD-008.

-- 6.5.2.f (TSB76) CDMAServiceOption N.S0010-0 v 1.0
-- 1 0 0 1 1 1 1 1 (0x9f)
-- 1 0 0 0 0 0 0 1 (0x81)
-- 0 0 1 0 1 1 1 1 (0x2f)(175)
CDMAServiceOption ::=  OCTET STRING
--a.	This field carries the CDMA Service Option. The bit-layout is the same as that of
--		Service Option in TSB74 and J-STD-008.

-- 6.5.2.g N.S0010-0 v 1.0
-- 1 0 1 1 1 1 1 1 (0xbf)
-- 1 0 0 0 0 0 0 1 (0x81)
-- 0 0 1 1 0 0 0 0 (0x30)(176)
CDMAServiceOptionList ::= SEQUENCE OF [175] IMPLICIT CDMAServiceOption

-- 6.5.2.h N.S0010-0 v 1.0
-- 1 0 0 1 1 1 1 1 (0x9f)
-- 1 0 0 0 0 0 0 1 (0x81)
-- 0 0 1 1 0 0 0 1 (0x31)(177)
CDMAStationClassMark2 ::= OCTET STRING


-- 6 .5.2.i N.S0007-0 v 1.0 N.S0010-0 v 1.0
-- 1 0 0 1 1 1 1 1 (0x9f)
-- 1 0 0 0 0 0 0 1 (0x81)
-- 0 0 1 1 0 0 1 0 (0x32)(178)
TDMAServiceCode  ::= OCTET STRING


-- 6.5.2.j N.S0007-0 v 1.0 N.S0010-0 v 1.0
-- 1 0 0 1 1 1 1 1 (0x9f)
-- 1 0 0 0 0 0 0 1 (0x81)
-- 0 0 1 1 0 0 1 1 (0x33)(179)
TDMATerminalCapability ::= OCTET STRING

-- 6.5.2.k N.S0007-0 v 1.0 N.S0010-0 v 1.0
-- 1 0 0 1 1 1 1 1 (0x9f)
-- 1 0 0 0 0 0 0 1 (0x81)
-- 0 0 1 1 0 1 0 0 (0x34)(180)
-- last TSB76 assigned identifier)
TDMAVoiceCoder ::= OCTET STRING



-- 6.5.2.aa (N.S0007-0 v 1.0)
-- 1 0 0 1 1 1 1 1 (0x9f)
-- 1 0 0 0 0 0 0 1 (0x81)
-- 0 1 0 0 0 1 0 1 (0x45)(197)
BaseStationManufacturerCode ::= OCTET STRING

-- 6.5.2.ab (N.S0007-0 v 1.0)
-- 1 0 0 1 1 1 1 1 (0x9f)
-- 1 0 0 0 0 0 0 1 (0x81)
-- 0 1 0 0 0 1 1 0 (0x46)(198)
BSMCStatus ::= OCTET STRING

-- 6.5.2.ac (N.S0007-0 v 1.0) N.S0010-0 v 1.0
-- 1 0 0 1 1 1 1 1 (0x9f)
-- 1 0 0 0 0 0 0 1 (0x81)
-- 0 1 0 0 0 1 1 1 (0x49)(199)
ControlChannelMode ::= OCTET STRING

-- 6 .5.2.ad (N.S0007-0 v 1.0)
-- 1 0 0 1 1 1 1 1 (0x9f)
-- 1 0 0 0 0 0 0 1 (0x81)
-- 0 1 0 0 1 0 0 0 (0x48)(200)
NonPublicData ::= OCTET STRING


-- 6.5.2.ae (N.S0007-0 v 1.0)
-- 1 0 0 1 1 1 1 1 (0x9f)
-- 1 0 0 0 0 0 0 1 (0x81)
-- 0 1 0 0 1 0 0 1 (0x49)(201)
PagingFrameClass ::= OCTET STRING


-- 6.5.2.af (N.S0007-0 v 1.0)
-- 1 0 0 1 1 1 1 1 (0x9f)
-- 1 0 0 0 0 0 0 1 (0x81)
-- 0 1 0 0 1 0 1 0 (0x4a)(202)
PSID-RSIDInformation ::= OCTET STRING

-- 6.5.2.ag (N.S0007-0 v 1.0)
-- 1 0 1 1 1 1 1 1 (0x9f)
-- 1 0 0 0 0 0 0 1 (0x81)
-- 0 1 0 0 1 0 1 1 (0x4b)(203)

PSID-RSIDList ::= SEQUENCE{
	pSID-RSIDInformation		[202] IMPLICIT PSID-RSIDInformation,
	 -- M 6.5.2.af
	pSID-RSIDInformation1		[202] IMPLICIT PSID-RSIDInformation OPTIONAL
	--O 6.5.2.af a
	}

-- 6.5.2.ah (N.S0007-0 v 1.0)
-- 1 0 0 1 1 1 1 1 (0x9f)
-- 1 0 0 0 0 0 0 1 (0x81)
-- 0 1 0 0 1 1 0 0 (0x4c)(204)
ServicesResult ::= OCTET STRING

-- 6.5.2.ai (N.S0007-0 v 1.0)
-- 1 0 0 1 1 1 1 1 (0x9f)
-- 1 0 0 0 0 0 0 1 (0x81)
-- 0 1 0 0 1 1 0 1 (0x4d)(205)
SOCStatus ::= OCTET STRING

-- 6.5.2.aj (N.S0007-0 v 1.0)
-- 1 0 0 1 1 1 1 1 (0x9f)
-- 1 0 0 0 0 0 0 1 (0x81)
-- 0 1 0 0 1 1 1 0 (0x4e)(206)
SystemOperatorCode ::= OCTET STRING


-- 6.5.2.aj
-- XXX Same code as ISLPinformation???
-- 1 0 0 1 1 1 1 1 (0x9f)
-- 1 0 0 0 0 0 0 1 (0x81)
-- 0 1 0 1 1 0 0 1 (0x59)()
-- SecondInterMSCCircuitID N.S0008-0 v 1.0

-- 6.5.2.ak (N.S0007-0 v 1.0)
-- 1 0 1 1 1 1 1 1 (0x9f)
-- 1 0 0 0 0 0 0 1 (0x81)
-- 0 1 0 0 1 1 1 1 (0x4f)(207)
TargetCellIDList ::= SEQUENCE {
	targetCellID							[3] IMPLICIT TargetCellID,
	-- M 6.5.2.148
	targetCellID1							[3] IMPLICIT TargetCellID OPTIONAL
	-- O 6.5.2.148
	}


-- 6.5.2.al (N.S0007-0 v 1.0)
-- 1 0 0 1 1 1 1 1 (0x9f)
-- 1 0 0 0 0 0 0 1 (0x81)
-- 0 1 0 1 0 0 0 0 (0x50)(208)
UserGroup ::= OCTET STRING


-- 6.5.2.am (N.S0007-0 v 1.0)
-- 1 0 0 1 1 1 1 1 (0x9f)
-- 1 0 0 0 0 0 0 1 (0x81)
-- 0 1 0 1 0 0 0 1 (0x51)(209)
UserZoneData ::= OCTET STRING

-- 6.5.2.ap (IS-737)
-- 1 0 1 1 1 1 1 1 (0x9f)
-- 1 0 0 0 0 0 0 1 (0x81)
-- 0 1 0 1 0 0 1 1 (0x53)(211)
CDMAConnectionReferenceInformation ::= SEQUENCE {
	cdmaConnectionReference					[208] IMPLICIT CDMAConnectionReference,
	-- M 6.5.2.bb d
	cdmaServiceOption						[175] IMPLICIT CDMAServiceOption,
	-- M 6.5.2.f
	cdmaState								[213] IMPLICIT CDMAState OPTIONAL,
	-- O 6.5.2.ad a
	dataPrivacyParameters					[216] IMPLICIT DataPrivacyParameters OPTIONAL,
	-- O 6.5.2.au b
	cdmaServiceOptionConnectionIdentifier	[361] IMPLICIT CDMAServiceOptionConnectionIdentifier OPTIONAL,
	--O 6.5.2.gr e
	...
	}

-- 6.5.2.ad (IS-737)
-- 1 0 1 1 1 1 1 1 (0x9f)
-- 1 0 0 0 0 0 0 1 (0x81)
-- 0 1 0 1 0 1 0 0 (0x54)(212)
CDMAConnectionReferenceList ::= SEQUENCE OF SEQUENCE {
	cdmaConnectionReferenceInformation	[211] IMPLICIT CDMAConnectionReferenceInformation,
	-- M 6.5.2.ap
	cdmaConnectionReferenceInformation2	[211] IMPLICIT CDMAConnectionReferenceInformation OPTIONAL,
	-- O 6.5.2.ap a
	...
	}

--6.5.2.ar
-- 6.5.2.ad CDMAState N.S0008-0 v 1.0
-- 1 0 0 1 1 1 1 1 (0x9f)
-- 1 0 0 0 0 0 1 0 (0x82)
-- 0 1 0 1 0 1 0 1 (0x55)(213)
CDMAState ::= OCTET STRING

-- 6.5.2.as N.S0008-0 v 1.0
-- 1 0 0 1 1 1 1 1 (0x9f)
-- 1 0 0 0 0 0 0 1 (0x81)
-- 0 1 0 1 0 1 1 0 (0x56)(214)
ChangeServiceAttributes ::= OCTET STRING

-- 6.5.2.at
-- 1 0 0 1 1 1 1 1 (0x9f)
-- 1 0 0 0 0 0 0 1 (0x81)
-- 0 1 0 1 0 1 1 1 (0x57)(215)
DataKey ::= OCTET STRING

-- 6.5.2.au
-- 1 0 0 1 1 1 1 1 (0x9f)
-- 1 0 0 0 0 0 0 1 (0x81)
-- 0 1 0 1 1 0 0 0 (0x58)(216)
DataPrivacyParameters ::= OCTET STRING


-- 6.5.2.av
-- 1 0 0 1 1 1 1 1 (0x9f)
-- 1 0 0 0 0 0 0 1 (0x81)
-- 0 1 0 1 1 0 0 1 (0x59)(217)
ISLPInformation ::= OCTET STRING

-- 6.5.2.aw ReasonList N.S0008-0 v 1.0
-- 1 0 0 1 1 1 1 1 (0x9f)
-- 1 0 0 0 0 0 0 1 (0x81)
-- 0 1 0 1 1 0 1 0 (0x5a)(218)
ReasonList ::= ENUMERATED {
	unknown		(0),
	unable-to-configure-ISLP (1),
	iSLP-failure (2),
	service-allowed-but-facilities-not-available (3),
	service-not-allowed (4),
	no-Response-to-TMSI-assignment (5),
	required-parameters-unavailable (6)
	}

-- 6.5.2.ay N.S0008-0 v 1.0
-- 1 0 0 1 1 1 1 1 (0x9f)
-- 1 0 0 0 0 0 0 1 (0x81)
-- 0 1 0 1 1 1 0 0 (0x5c)(220)
TDMABandwidth ::= OCTET STRING


-- 6.5.2.az N.S0008-0 v 1.0
-- 1 0 0 1 1 1 1 1 (0x9f)
-- 1 0 0 0 0 0 0 1 (0x81)
-- 0 1 0 1 1 1 0 1 (0x5d)(221)
TDMADataFeaturesIndicator ::= OCTET STRING

-- 6.5.2.ba
-- 1 0 0 1 1 1 1 1 (0x9f)
-- 1 0 0 0 0 0 0 1 (0x81)
-- 0 1 0 1 1 1 1 0 (0x5e)(222)
TDMADataMode ::= OCTET STRING

-- 6.5.2.bb
-- 1 0 0 1 1 1 1 1 (0x9f)
-- 1 0 0 0 0 0 0 1 (0x81)
-- 0 1 0 1 1 1 1 1 (0x5f)(223)
TDMAVoiceMode ::= OCTET STRING

-- 6.5.2.bb
-- 1 0 0 1 1 1 1 1 (0x9f)
-- 1 0 0 0 0 0 0 1 (0x81)
-- 0 1 0 1 0 0 1 0 (0x52)(208)
CDMAConnectionReference ::= OCTET STRING
-- a.	This field carries the CDMA Service Option Connection Reference. The bitlayout
--		is the same as that of Service Option Connection Reference in TSB74 and
--		J-STD-008.

-- 6.5.2.bc N.S0010-0 v 1.0
-- 1 0 0 1 1 1 1 1 (0x9f)
-- 1 0 0 0 0 0 0 1 (0x81)
-- 0 1 1 0 0 0 0 0 (0x60)(224)
AnalogRedirectInfo ::= OCTET STRING

-- 6.5.2.bd N.S0010-0 v 1.0
-- 1 0 1 1 1 1 1 1 (0x9f)
-- 1 0 0 0 0 0 0 1 (0x81)
-- 0 1 1 0 0 0 0 1 (0x61)(225)
AnalogRedirectRecord ::= SEQUENCE {
	analogRedirectInfo		[224] IMPLICIT AnalogRedirectInfo,
	-- M 6.5.2.bc
	mscid					[21] IMPLICIT MSCID,
	-- M 6.5.2.82
	...
	}

-- 6.5.2.be N.S0010-0 v 1.0
-- 1 0 0 1 1 1 1 1 (0x9f)
-- 1 0 0 0 0 0 0 1 (0x81)
-- 0 1 1 0 0 0 1 0 (0x62)(226)
CDMAChannelNumber ::= OCTET STRING

-- 6.5.2.bf N.S0010-0 v 1.0
-- 1 0 1 1 1 1 1 1 (0x9f)
-- 1 0 0 0 0 0 0 1 (0x81)
-- 0 1 1 0 0 0 1 1 (0x63)(227)
CDMAChannelNumberList ::= SEQUENCE OF SEQUENCE{
	cdmaChannelNumber		[226] IMPLICIT CDMAChannelNumber,
	-- M 6.5.2.be
	cdmaChannelNumber2		[226] IMPLICIT CDMAChannelNumber,
	-- O 6.5.2.be a
	...
	}

-- 6.5.2.bg N.S0010-0 v 1.0
-- 1 0 0 1 1 1 1 1 (0x9f)
-- 1 0 0 0 0 0 0 1 (0x81)
-- 0 1 1 0 0 1 0 0 (0x64)(228)
CDMAPowerCombinedIndicator ::= OCTET STRING

-- 6.5.2.bh N.S0010-0 v 1.0
-- 1 0 0 1 1 1 1 1 (0x9f)
-- 1 0 0 0 0 0 0 1 (0x81)
-- 0 1 1 0 0 1 0 1 (0x65)(229)
CDMARedirectRecord ::= SEQUENCE {
	cdmaBandClass							[170] IMPLICIT CDMABandClass,
	-- M 6.5.2.a a
	cdmaChannelNumberList					[227] IMPLICIT CDMAChannelNumberList,
	-- M 6.5.2.bf
	mscid									[21] IMPLICIT MSCID,
	-- M 6.5.2.82
	cdmaNetworkIdentification				[232] IMPLICIT CDMANetworkIdentification,
	-- M 6.5.2.bk
	...
	}
	
-- 6.5.2.bi N.S0010-0 v 1.0
-- 1 0 0 1 1 1 1 1 (0x9f)
-- 1 0 0 0 0 0 0 1 (0x81)
-- 0 1 1 0 0 1 1 0 (0x66)(230)
CDMASearchParameters ::= OCTET STRING

-- 6.5.2.bj N.S0010-0 v 1.0
-- 1 0 0 1 1 1 1 1 (0x9f)
-- 1 0 0 0 0 0 0 1 (0x81)
-- 0 1 1 0 0 1 1 1 (0x67)(231)
-- Reserved

-- 6.5.2.bk N.S0010-0 v 1.0
-- 1 0 0 1 1 1 1 1 (0x9f)
-- 1 0 0 0 0 0 0 1 (0x81)
-- 0 1 1 0 1 0 0 0 (0x68)(232)
CDMANetworkIdentification ::= OCTET STRING

-- 6.5.2.bl N.S0010-0 v 1.0
-- 1 0 0 1 1 1 1 1 (0x9f)
-- 1 0 0 0 0 0 0 1 (0x81)
-- 0 1 1 0 1 0 0 1 (0x69)(233)
-- XXX Is this correct? see (N.S0005-0 v 1.0 Chapter 5, page 219)
-- Changed from DigitsType to Octetstring  J-STD-036-AD-1
NetworkTMSI ::= OCTET STRING

-- 6.5.2.bm N.S0010-0 v 1.0
-- 1 0 0 1 1 1 1 1 (0x9f)
-- 1 0 0 0 0 0 0 1 (0x81)
-- 0 1 1 0 1 0 1 0 (0x6a)(234)
NetworkTMSIExpirationTime ::= OCTET STRING

-- 6.5.2.bn N.S0010-0 v 1.0
-- 1 0 0 1 1 1 1 1 (0x9f)
-- 1 0 0 0 0 0 0 1 (0x81)
-- 0 1 1 0 1 0 1 1 (0x6b)(235)
NewNetworkTMSI ::= DigitsType

-- 6.5.2.bo N.S0010-0 v 1.0
-- 1 0 0 1 1 1 1 1 (0x9f)
-- 1 0 0 0 0 0 0 1 (0x81)
-- 0 1 1 0 1 1 0 0 (0x6c)(236)
RequiredParametersMask ::= OCTET STRING

-- 6.5.2.bp N.S0010-0 v 1.0
-- 1 0 0 1 1 1 1 1 (0x9f)
-- 1 0 0 0 0 0 0 1 (0x81)
-- 0 1 1 0 1 1 0 1 (0x6d)(237)
ServiceRedirectionCause ::= OCTET STRING

-- 6.5.2.bq N.S0010-0 v 1.0
-- 1 0 0 1 1 1 1 1 (0x9f)
-- 1 0 0 0 0 0 0 1 (0x81)
-- 0 1 1 0 1 1 1 0 (0x6e)(238)
ServiceRedirectionInfo ::= OCTET STRING

-- 6.5.2.br N.S0010-0 v 1.0
-- 1 0 0 1 1 1 1 1 (0x9f)
-- 1 0 0 0 0 0 0 1 (0x81)
-- 0 1 1 0 1 1 1 1 (0x6f)(239)
RoamingIndication ::= OCTET STRING

-- 6.5.2.bs
-- 1 0 0 1 1 1 1 1 (0x9f)
-- 1 0 0 0 0 0 0 1 (0x81)
-- 0 1 1 1 0 0 0 0 (0x6f)(239)
EmergencyServicesRoutingDigits ::= DigitsType

-- 6.5.2.bu
-- N.S0010-0 v 1.0
-- 1 0 0 1 1 1 1 1 (0x9f)
-- 1 0 0 0 0 0 0 1 (0x81)
-- 0 1 1 1 0 0 0 0 (0x70)(240)
-- MSID


-- 6.5.2.bv MSID

MSID ::= CHOICE {
	mobileIdentificationNumber				[8] IMPLICIT MobileIdentificationNumber,
	imsi									[242] IMPLICIT IMSI
	}

-- 6.5.2.bu (IS-751)
-- 1 0 0 1 1 1 1 1 (0x9f)
-- 1 0 0 0 0 0 0 1 (0x81)
-- 0 1 1 1 0 0 1 0 (0x72)(242)
-- Import from GSM MAP for convenience
-- IMSI ::= OCTET STRING

-- 6.5.2.bw N.S0012-0 v 1.0
-- 1 0 0 1 1 1 1 1 (0x9f)
-- 1 0 0 0 0 0 0 1 (0x81)
-- 0 1 1 1 0 0 1 1 (0x73)(243)
CallingPartyName ::= OCTET STRING


-- 6.5.2.bx N.S0012-0 v 1.0
-- 1 0 0 1 1 1 1 1 (0x9f)
-- 1 0 0 0 0 0 0 1 (0x81)
-- 0 1 1 1 0 1 0 0 (0x74)(244)
DisplayText ::= OCTET STRING

-- 6.5.2.by N.S0012-0 v 1.0
-- 1 0 0 1 1 1 1 1 (0x9f)
-- 1 0 0 0 0 0 0 1 (0x81)
-- 0 1 1 1 0 1 0 1 (0x75)(245)
RedirectingPartyName ::= OCTET STRING

-- 6.5.2.bz N.S0012-0 v 1.0
-- 1 0 0 1 1 1 1 1 (0x9f)
-- 1 0 0 0 0 0 0 1 (0x81)
-- 0 1 1 1 0 1 1 0 (0x76)(246)
ServiceID ::= OCTET STRING

--6.5.2.ca
-- Ref N.S0013-0_v1.0
-- 1 0 0 1 1 1 1 1 (0x9f)
-- 1 0 0 0 0 0 0 1 (0x81)
-- 0 1 1 1 0 1 1 1 (0x77) (247)
AllOrNone ::= ENUMERATED{
	notUsed							( 0 ),
	allChangesMustSucceedOrNoneShouldBeApplied (1),
	treatEachChangeIndependently (2)
	}

-- 6.5.2.cb N.S0013-0 v 1.0
-- 1 0 0 1 1 1 1 1 (0x9f)
-- 1 0 0 0 0 0 0 1 (0x81)
-- 0 1 1 1 1 0 0 0 (0x78)(248)
Change  ::= ENUMERATED {
	setDataItemToDefaultValue (1),
	addDataItem (2),
	deleteDataItem (3),
	replaceDataItemWithAssociatedDataValue (4),
...}

-- 6.5.2.cc N.S0013-0 v 1.0
-- 1 0 1 1 1 1 1 1 (0xbf)
-- 1 0 0 0 0 0 0 1 (0x81)
-- 0 1 1 1 1 0 0 1 (0x79)(249)
DataAccessElement ::= SEQUENCE {
	dataID		[251] IMPLICIT DataID,
--	 M 6.5.2.ce
	change		[248] IMPLICIT Change OPTIONAL,
--	 O 6.5.2.cb a
	dataValue	[256]IMPLICIT DataValue OPTIONAL,
--	O 6.5.2.cj a
	...}

-- 6.5.2.cd N.S0013-0 v 1.0
-- 1 0 1 1 1 1 1 1 (0x9f)
-- 1 0 0 0 0 0 0 1 (0x81)
-- 0 1 1 1 1 0 1 0 (0x7a) (250)
DataAccessElementList ::= SEQUENCE OF SEQUENCE{
	dataAccessElement1	[249] IMPLICIT DataAccessElement,
	dataAccessElement2	[249] IMPLICIT DataAccessElement OPTIONAL
}

-- 6.5.2.ce N.S0013-0 v 1.0
-- 1 0 0 1 1 1 1 1 (0x9f)
-- 1 0 0 0 0 0 0 1 (0x81)
-- 0 1 1 1 1 0 1 1 (0x7b)(251)
DataID ::= OCTET STRING

-- 6.5.2.cf N.S0013-0 v 1.0
-- 1 0 0 1 1 1 1 1 (0x9f)
-- 1 0 0 0 0 0 0 1 (0x81)
-- 0 1 1 1 1 1 0 0 (0x7c)(252)
DatabaseKey ::= OCTET STRING

-- 6.5.2.cg N.S0013-0 v 1.0
-- 1 0 0 1 1 1 1 1 (0x9f)
-- 1 0 0 0 0 0 0 1 (0x81)
-- 0 1 1 1 1 1 0 1 (0x7d)(253)
DataResult ::= ENUMERATED {
	not-used										( 0 ),
	successful										( 1 ),
	unsuccessful-unspecified						( 2 ),
	unsuccessful-no-default-value-available			( 3 ),
	reserved							( 4 ) }


-- 6.5.2.ch N.S0013-0 v 1.0
-- 1 0 1 1 1 1 1 1 (0xbf)
-- 1 0 0 0 0 0 0 1 (0x81)
-- 0 1 1 1 1 1 1 0 (0x7e)(254)
DataUpdateResult ::= SEQUENCE {
	dataID		[251] IMPLICIT DataID,
--	M 6.5.2.ce
	dataResult	[253] IMPLICIT DataResult
--	 M 6.5.2.cg
}

-- 6.5.2.ci N.S0013-0 v 1.0
-- 1 0 1 1 1 1 1 1 (0x9f)
-- 1 0 0 0 0 0 0 1 (0x81)
-- 0 1 1 1 1 1 1 1 (0x7f)(255)
DataUpdateResultList ::= SEQUENCE OF DataUpdateResult
--DataUpdateResultList ::= SEQUENCE OF SEQUENCE{
--	dataUpdateResult	[254] IMPLICIT DataUpdateResult,
	--	M 6.5.2.ch
--	dataUpdateResultopt	[254] IMPLICIT DataUpdateResult OPTIONAL
	--	O 6.5.2.ch	
--}

-- 6.5.2.cj N.S0013-0 v 1.0
-- 1 0 0 1 1 1 1 1 (0x9f)
-- 1 0 0 0 0 0 1 0 (0x82)
-- 0 0 0 0 0 0 0 0 (0x00)(256)
DataValue ::= OCTET STRING


-- 6.5.2.ck DestinationAddress N.S0013-0 v 1.0
DestinationAddress ::= CHOICE {
	globalTitle	[261] IMPLICIT GlobalTitle,
	pC-SSN		[32] IMPLICIT PC-SSN
	}

DetectionPointType ::= ENUMERATED {
	tDP-R (1),
	tDP-N (2),
	eDP-R (3),
	eDP-N (4)
}

-- 6.5.2.cl N.S0013-0 v 1.0
-- 1 0 1 1 1 1 1 1 (0x9f)
-- 1 0 0 0 0 0 1 0 (0x82)
-- 0 0 0 0 0 0 1 0 (0x02)(386)
ExecuteScript ::= SEQUENCE {
	scriptName		[268] IMPLICIT ScriptName,
--	M 6.5.2.cw a
	scriptArgument	[267] IMPLICIT ScriptArgument OPTIONAL
--	O 6.5.2.cv b
}

-- 6.5.2.cm N.S0013-0 v 1.0
-- 1 0 0 1 1 1 1 1 (0x9f)
-- 1 0 0 0 0 0 1 0 (0x82)
-- 0 0 0 0 0 0 1 1 (0x03)(387)
FailureCause ::= OCTET STRING
--encoding of this parameter is based on the encoding of
--the information elements in T1.113.3 section 2.3.9.

-- 6.5.2.cn N.S0013-0 v 1.0
-- 1 0 0 1 1 1 1 1 (0x9f)
-- 1 0 0 0 0 0 1 0 (0x82)
-- 0 0 0 0 0 1 0 0 (0x04)(260)

FailureType ::= ENUMERATED {
	callAbandoned (1),
	resourceDisconnect (2),
	failureAtMSC (3),
	sSFTExpiration (4)
}


-- 6.5.2.co N.S0013-0 v 1.0
-- 1 0 0 1 1 1 1 1 (0x9f)
-- 1 0 0 0 0 0 1 0 (0x82)
-- 0 0 0 0 0 1 0 1 (0x05)(261)
GlobalTitle ::= OCTET STRING
--parameter carries the SCCP Global Title as defined in
--Section 3 of ANSI T1.112.

-- 6.5.2.cp N.S0013-0 v 1.0
-- ModificationRequest
-- 1 0 1 1 1 1 1 1 (0x9f)
-- 1 0 0 0 0 0 1 0 (0x82)
-- 0 0 0 0 0 1 1 0 (0x06)(262)

ModificationRequest ::= SEQUENCE {
	serviceDataAccessElementList	[271] IMPLICIT ServiceDataAccessElementList OPTIONAL,
	allOrNone	[247] IMPLICIT AllOrNone
	}

-- 6.5.2.cq N.S0013-0 v 1.0
-- 1 0 1 1 1 1 1 1 (0x9f)
-- 1 0 0 0 0 0 1 0 (0x82)
-- 0 0 0 0 0 1 1 1 (0x07)(263)
ModificationRequestList ::= SEQUENCE OF [262] IMPLICIT ModificationRequest

-- 6.5.2.cr ModificationResult N.S0013-0 v 1.0
-- The ModificationResult CHOICE is not explicitly encoded with a parameter identifier and length
ModificationResult ::= CHOICE
	{dataResult				[253] IMPLICIT DataResult,
	serviceDataResultList	[273] IMPLICIT ServiceDataResultList
	}

-- 6.5.2.cs N.S0013-0 v 1.0
-- 1 0 1 1 1 1 1 1 (0x9f)
-- 1 0 0 0 0 0 1 0 (0x82)
-- 0 0 0 0 1 0 0 0 (0x08)(264)
ModificationResultList ::= SEQUENCE OF ModificationResult


-- 6.5.2.ct N.S0013-0 v 1.0
-- 1 0 0 1 1 1 1 1 (0x9f)
-- 1 0 0 0 0 0 1 0 (0x82)
-- 0 0 0 0 1 0 0 1 (0x09)(265)
PrivateSpecializedResource ::= OCTET STRING
--values are allocated by network operators for use
--within their networks

-- 6.5.2.cu N.S0013-0 v 1.0
-- 1 0 0 1 1 1 1 1 (0x9f)
-- 1 0 0 0 0 0 1 0 (0x82)
-- 0 0 0 0 1 0 1 0 (0x0a)(266)
ResumePIC ::= ENUMERATED {
	continue-Call-Processing (1),
	collect-Information-PIC (2),
	analyze-Information-PIC (3),
	select-Route-PIC (4),
	authorize-Origination-Attempt-PIC (5),
	authorize-Call-Setup-PIC (6),
	send-Call-PIC (7),
	o-Alerting-PIC (8),
	o-Active-PIC (9),
	o-Suspended-PIC (10),
	o-Null-PIC (11),
	select-Facility-PIC (32),
	present-Call-PIC (33),
	authorize-Termination-Attempt-PIC (34),
	t-Alerting-PIC (35),
	t-Active-PIC (36),
	t-Suspended-PIC (37),
	t-Null-PIC (38)
}

-- 6.5.2.cv
-- 1 0 0 1 1 1 1 1 (0x9f)
-- 1 0 0 0 0 0 1 0 (0x82)
-- 0 0 0 0 1 0 1 1 (0x0b)(267)
ScriptArgument ::= OCTET STRING

-- 6.5.2.cw
-- 1 0 0 1 1 1 1 1 (0x9f)
-- 1 0 0 0 0 0 1 0 (0x82)
-- 0 0 0 0 1 1 0 0 (0x0c)(268)
ScriptName ::= OCTET STRING

-- 6.5.2.cx
-- 1 0 0 1 1 1 1 1 (0x9f)
-- 1 0 0 0 0 0 1 0 (0x82)
-- 0 0 0 0 1 1 0 1 (0x0d)(269)
ScriptResult ::= OCTET STRING

-- 6.5.2.cy
-- 1 0 1 1 1 1 1 1 (0x9f)
-- 1 0 0 0 0 0 1 0 (0x82)
-- 0 0 0 0 1 1 1 0 (0x0e) (270)
ServiceDataAccessElement ::= SEQUENCE {
	dataAccessElementList	[250] IMPLICIT DataAccessElementList,
	serviceID				[246] IMPLICIT ServiceID OPTIONAL
	}

-- 6.5.2.cz
-- 1 0 1 1 1 1 1 1 (0x9f)
-- 1 0 0 0 0 0 1 0 (0x82)
-- 0 0 0 0 1 1 1 1 (0x0f)(271)
ServiceDataAccessElementList ::= SEQUENCE OF [270] IMPLICIT ServiceDataAccessElement

-- 6.5.2.da
-- 1 0 1 1 1 1 1 1 (0x9f)
-- 1 0 0 0 0 0 1 0 (0x82)
-- 0 0 0 1 0 0 0 0 (0x10)(272)
ServiceDataResult ::= SEQUENCE {
	dataUpdateResultList	[255] IMPLICIT DataUpdateResultList,
	serviceID				[246] IMPLICIT ServiceID OPTIONAL
	}

-- 6.5.2.db
-- 1 0 1 1 1 1 1 1 (0x9f)
-- 1 0 0 0 0 0 1 0 (0x82)
-- 0 0 0 1 0 0 0 1 (0x11)(273)
ServiceDataResultList ::= SEQUENCE OF [272] IMPLICIT  ServiceDataResult

-- 6.5.2.dc
-- 1 0 0 1 1 1 1 1 (0x9f)
-- 1 0 0 0 0 0 1 0 (0x82)
-- 0 0 0 1 0 0 1 0 (0x12)(274)
SpecializedResource ::= OCTET STRING

--SRFCapability ::= SET {
--	specializedResource			[274] IMPLICIT SpecializedResource OPTIONAL,
--	privateSpecializedResource	[265] IMPLICIT PrivateSpecializedResource OPTIONAL
--	}
--at least one must be present

-- 6.5.2.dd
-- 1 0 0 1 1 1 1 1 (0x9f)
-- 1 0 0 0 0 0 1 0 (0x82)
-- 0 0 0 1 0 0 1 1 (0x13)(275)
TimeDateOffset ::= OCTET STRING

-- 6.5.2.de
-- 1 0 1 1 1 1 1 1 (0xbf)
-- 1 0 0 0 0 0 1 0 (0x82)
-- 0 0 0 1 0 1 0 0 (0x14)(276)
TriggerAddressList ::= SET{
	triggerList			[278] IMPLICIT TriggerList,
--	M 6.5.2.dg
	triggerListOpt		[278] IMPLICIT TriggerList OPTIONAL
--	O 6.5.2.dg a
}

-- 6.5.2.df TIA/EIA/IS-848 N.S0004
-- 1 0 0 1 1 1 1 1 (0x9f)
-- 1 0 0 0 0 0 1 0 (0x82)
-- 0 0 0 1 0 1 0 1 (0x15)(277)
TriggerCapability ::= OCTET STRING
--see 6.5.2.gg for encoding

-- 6.5.2.dg
-- 1 0 1 1 1 1 1 1 (0xbf) (0xbf)
-- 1 0 0 0 0 0 1 0 (0x82)
-- 0 0 0 1 0 1 1 0 (0x16)(278)
-- 6.5.2.ck DestinationAddress N.S0013-0 v 1.0
--DestinationAddress ::= CHOICE {
--	globalTitle	[261] IMPLICIT GlobalTitle,
--	pC-SSN		[32] IMPLICIT PC-SSN
--	}

TriggerList ::= SET{
	destinationAddress		DestinationAddress,
	wIN-TriggerList			[283] IMPLICIT WIN-TriggerList
	--	M 6.5.2.dk
}

-- 6.5.2.dh
-- 1 0 0 1 1 1 1 1 (0x9f)
-- 1 0 0 0 0 0 1 0 (0x82)
-- 0 0 0 1 0 1 1 1 (0x17)(279)

TriggerType ::= ENUMERATED {
	all-Calls (1),
	double-Introducing-Star (2),
	single-Introducing-Star (3),
	reserved-for-Home-System-Feature-Code (4),
	double-Introducing-Pound (5),
	single-Introducing-Pound (6),
	revertive-Call (7),
	a0-Digit (8),
	a1-Digit (9),
	a2-Digit (10),
	a3-Digit (11),
	a4-Digit (12),
	a5-Digit (13),
	a6-Digit (14),
	a7-Digit (15),
	a8-Digit (16),
	a9-Digit (17),
	a10-Digit (18),
	a11-Digit (19),
	a12-Digit (20),
	a13-Digit (21),
	a14-Digit (22),
	a15-Digit (23),
	local-Call (24),
	intra-LATA-Toll-Call (25),
	inter-LATA-Toll-Call (26),
	world-Zone-Call (27),
	international-Call (28),
	unrecognized-Number (29),
	prior-Agreement (30),
	specific-Called-Party-Digit-String (31),
	mobile-Termination (32),
	advanced-Termination (33),
	location (34),
	locally-Allowed-Specific-Digit-String (35),
	origination-Attempt-Authorized (36),
	calling-Routing-Address-Available (37),
	initial-Termination (38),
	called-Routing-Address-Available (39),
	o-Answer (40),
	o-Disconnect (41),
	o-Called-Party-Busy (42),
	o-No-Answer (43),

	terminating-Resource-Available (64),
	t-Busy (65),
	t-No-Answer (66),
	t-No-Page-Response (67),
	t-Routable (68),
	t-Answer (69),
	t-Disconnect (70),

	reserved-for-TDP-R-DP-Type-value (220),
	reserved-for-TDP-N-DP-Type-value (221),
	reserved-for-EDP-R-DP-Type-value (222),
	reserved-for-EDP-N-DP-Type-value (223),
	...
	}
-- 1 0 1 1 1 1 1 1 (0x9f) (0xbf)
-- 1 0 0 0 0 0 1 0 (0x82)
-- 0 0 0 1 1 0 0 0 (0x18)(280)
-- 6.5.2.di
WINCapability ::= SET {
	triggerCapability			[277] IMPLICIT TriggerCapability OPTIONAL,
--	O 6.5.2.df a
	wINOperationsCapability		[281] IMPLICIT WINOperationsCapability OPTIONAL
--	 O 6.5.2.dj a
}

-- 6.5.2.dj
-- 1 0 0 1 1 1 1 1 (0x9f)
-- 1 0 0 0 0 0 1 0 (0x82)
-- 0 0 0 1 1 0 0 1 (0x19)(281)
WINOperationsCapability ::= OCTET STRING
--see 6.5.2.kk for encoding

--WIN-Trigger ::= SEQUENCE {
--	triggerType			[279] IMPLICIT TriggerType OPTIONAL,
--	detectionPointType	DetectionPointType
--	}

--6.5.2.dk N.S0013-0 v 1.0,X.S0004-550-E v1.0 2.301
-- 1 0 0 1 1 1 1 1 (0x9f)
-- 1 0 0 0 0 0 1 0 (0x82)
-- 0 0 0 1 1 0 1 1 (0x1b)(283)
-- WIN-TriggerList ::= SET OF WIN-Trigger
WIN-TriggerList ::= OCTET STRING

-- 6.5.2.do
-- 1 0 0 1 1 1 1 1 (0x9f)
-- 1 0 0 0 0 0 1 0 (0x82)
-- 0 0 0 1 1 1 0 1 (0x1d)(285)

SuspiciousAccess ::= ENUMERATED {
	not-used (0),
	anomalous-Digits (1),
	unspecified (2),
	...
	}
-- 6.5.2.dp 1e 286
-- 6.5.2.dq 1f 287
-- 6.5.2.dr 20 288
-- 6.5.2.ds 21 289
-- (ANSI-41 6.5.2.dt) 2.2.2.25 J-STD-036-AD-1
-- 1 0 0 1 1 1 1 1 (0x9f)
-- 1 0 0 0 0 0 1 0 (0x82)
-- 0 0 1 0 0 0 1 0 (0x22)(290)
Teleservice-Priority ::= OCTET STRING

-- 6.5.2.eb
-- 1 0 0 1 1 1 1 1
-- 1 0 0 0 0 0 1 0
-- 0 0 1 0 1 0 1 0
-- [298)
--CommandCode
--(IS-764 modification)

-- 6.5.2.ec
-- 1 0 0 1 1 1 1 1
-- 1 0 0 0 0 0 1 0
-- 0 0 1 0 1 0 1 1
-- (299)
DisplayText2 ::= OCTET STRING



-- 6.5.2.ed
-- 1 0 0 1 1 1 1 1
-- 1 0 0 0 0 0 1 0
-- 0 0 1 0 1 1 0 0
-- (300)
-- PageCount

PageCount ::= OCTET STRING

-- 6.5.2.ee
-- 1 0 0 1 1 1 1 1
-- 1 0 0 0 0 0 1 0
-- 0 0 1 0 1 1 0 1
-- (301)
-- PageResponseTime
PageResponseTime ::= OCTET STRING

-- 2.258 X.S0004-550-E v2.0
-- 1 0 0 1 1 1 1 1 (0x9f)
-- 1 0 0 0 0 0 1 0 (0x82)
-- 0 0 1 0 1 1 1 0 (0x2e)(302)
SMS-TransactionID ::= OCTET STRING

-- 6.5.2.eg
-- 1 0 1 1 1 1 1 1 (0x9f)
-- 1 0 0 0 0 0 1 0 (0x82)
-- 0 0 1 0 1 1 1 1 (0x2f)(303)
CallRecoveryID ::= SET{
	billingID		[1] IMPLICIT BillingID ,
	timeDateOffset	[275] IMPLICIT TimeDateOffset,
	timeOfDay		[309] IMPLICIT TimeOfDay,
	...}

-- 6.5.2.eh
-- 1 0 1 1 1 1 1 1 (0x9f)
-- 1 0 0 0 0 0 1 0 (0x82)
-- 0 0 1 1 0 0 0 0 (0x30)(304)
CallRecoveryIDList ::= SET OF [303] IMPLICIT CallRecoveryID

--	callRecoveryID		[303] IMPLICIT CallRecoveryID,
--	callRecoveryIDopt	[303] IMPLICIT CallRecoveryID OPTIONAL,
--	}

-- 6.5.2.ei TIA/EIA-41.5-D Modifications N.S0018Re ??
-- 1 0 0 1 1 1 1 1 (0x9f)
-- 1 0 0 0 0 0 1 0 (0x82)
-- 0 0 1 1 0 0 0 1 (0x31)(305)
DMH-ServiceID ::= OCTET STRING

-- 6.5.2.ej
-- 1 0 0 1 1 1 1 1 (0x9f)
-- 1 0 0 0 0 0 1 0 (0x82)
-- 0 0 1 1 0 0 1 0 (0x32)(306)
FeatureIndicator  ::= ENUMERATED {
	not-used (0),
	user-selective-call-forwarding (38),
	...
	}
-- See the DMH FeatureIndicator parameter for the values of this field.
-- Dummy define here

-- 6.5.2.ek
-- 1 0 0 1 1 1 1 1 (0x9f)
-- 1 0 0 0 0 0 1 0 (0x82)
-- 0 0 1 1 0 0 1 1 (0x33)(307)
ControlNetworkID  ::= OCTET STRING

-- 6.5.2.el
-- 1 0 0 1 1 1 1 1 (0x9f)
-- 1 0 0 0 0 0 1 0 (0x82)
-- 0 0 1 1 0 1 0 0 (0x34)(308)
ReleaseCause ::= ENUMERATED {
	unspecified (0),
	calling-Party (1),
	called-Party (2),
	commanded-Disconnect (3),
	...
	}

-- 6.5.2.em
-- 1 0 0 1 1 1 1 1 (0x9f)
-- 1 0 0 0 0 0 1 0 (0x82)
-- 0 0 1 1 0 1 0 1 (0x35) (309)
TimeOfDay ::= INTEGER

-- 6.5.2.en
-- 1 0 0 1 1 1 1 1 (0x9f)
-- 1 0 0 0 0 0 1 0 (0x82)
-- 0 0 1 1 0 1 1 0 (0x36) (310)
CallStatus ::= ENUMERATED {
	not-used (0),
	call-Setup-in-Progress (1),
	called-Party (2),
	locally-Allowed-Call-No-Action (3),
	...
	}

-- 6.5.2.eo
-- 1 0 0 1 1 1 1 1 (0x9f)
-- 1 0 0 0 0 0 1 0 (0x82)
-- 0 0 1 1 0 1 1 1 (0x37)(311)
DMH-ChargeInformation ::= OCTET STRING


-- 6.5.2.ep
-- 1 0 0 1 1 1 1 1 (0x9f)
-- 1 0 0 0 0 0 1 0 (0x82)
-- 0 0 1 1 1 0 0 0 (0x38)(312)
DMH-BillingIndicator ::= ENUMERATED {
	unspecified (0)
	}
-- b. See the DMH BillingIndicator parameter for the values of this field. (?? Huh?)	

-- 1 0 0 1 1 1 1 1 (0x9f)
-- 1 0 0 0 0 0 1 0 (0x82)
-- 0 0 1 1 1 0 0 1 (0x39)(313)
-- 6.5.2.eq
MSStatus ::= OCTET STRING

-- 6.5.2.er
-- 1 0 0 1 1 1 1 1 (0x9f)
-- 1 0 0 0 0 0 1 0 (0x82)
-- 0 0 1 1 1 0 1 1 (0x3b)(315)
PositionInformationCode::= OCTET STRING

-- 2.38 http://www.3gpp2.org/Public_html/specs/X.S0004-550-E_v1.0_040406.pdf
-- 1 0 0 1 1 1 1 1 (0x9f)
-- 1 0 0 0 0 0 1 0 (0x82)
-- 0 0 1 1 1 1 0 0 (0x3c)(316)
CaveKey  ::= OCTET STRING

-- 2.41 http://www.3gpp2.org/Public_html/specs/X.S0004-550-E_v1.0_040406.pdf
-- 1 0 0 1 1 1 1 1 (0x9f)
-- 1 0 0 0 0 0 1 0 (0x82)
-- 0 1 0 0 0 0 0 1 (0x41)(321)
CDMA2000MobileSupportedCapabilities ::= OCTET STRING

-- 2.114 http://www.3gpp2.org/Public_html/specs/X.S0004-550-E_v1.0_040406.pdf
-- 1 0 0 1 1 1 1 1 (0x9f)
-- 1 0 0 0 0 0 1 0 (0x82)
-- 0 1 0 0 0 1 0 1 (0x45)(325)
EnhancedPrivacyEncryptionReport ::= OCTET STRING

-- 6.5.2.fd
-- 1 0 0 1 1 1 1 1 (0x9f)
-- 1 0 0 0 0 0 1 0 (0x82)
-- 0 1 0 0 0 1 1 0 (0x46)(326)
InterMessageTime ::= OCTET STRING

-- 6.5.2.fe
-- 1 0 0 1 1 1 1 1 (0x9f)
-- 1 0 0 0 0 0 1 0 (0x82)
-- 0 1 0 0 0 1 1 1 (0x47)(327)
-- (3xx)
MSIDUsage ::= OCTET STRING

-- 6.5.2.ff
-- 1 0 0 1 1 1 1 1 (0x9f)
-- 1 0 0 0 0 0 1 0 (0x82)
-- 0 1 0 0 1 0 0 0 (0x48)(328)
-- (3xx)
NewMINExtension ::= MINType

-- (ANSI-41 6.5.2.fg) 2.2.2.7 J-STD-036-AD-1
-- 1 0 0 1 1 1 1 1 (0x9f)
-- 1 0 0 0 0 0 1 0 (0x82)
-- 0 1 0 0 1 0 0 1 (0x49)(329)
DTXIndication ::= OCTET STRING

-- (ANSI-4a1 6.5.2.fh) 2.2.2.5 J-STD-036-AD-1
-- 1 0 0 1 1 1 1 1 (0x9f)
-- 1 0 0 0 0 0 1 0 (0x82)
-- 0 1 0 0 1 0 1 0 (0x4a)(330)
CDMAMobileCapabilities ::= OCTET STRING
-- H G F E D C B A		octet Notes
-- Reserved      MIPLI	1		a ( Bit A)
--
-- 0 No MS-initiated position determination.
-- 1 MS-initiated position determination.

-- (ANSI-41 6.5.2.fi) 2.2.2.8  J-STD-036-AD-1
-- 1 0 0 1 1 1 1 1 (0x9f)
-- 1 0 0 0 0 0 1 0 (0x82)
-- 0 1 0 0 1 0 1 1 (0x4b)(331)
-- GeneralizedTime
-- Generalized Time is included by reference to Chapter 7. The definition from
-- X.680 that is referenced from Chapter 7 should be used, and not the definition
-- from TIA/EIA-41-D.

-- (ANSI-41 6.5.2.fj) 2.2.2.9 J-STD-036-AD-1
-- 1 0 0 1 1 1 1 1 (0x9f)
-- 1 0 0 0 0 0 1 0 (0x82)
-- 0 1 0 0 1 1 0 0 (0x4c)(332)
-- GenericDigits

-- (ANSI-41 6.5.2.fk) 2.2.2.10 J-STD-036-AD-1
-- 1 0 0 1 1 1 1 1 (0x9f)
-- 1 0 0 0 0 0 1 0 (0x82)
-- 0 1 0 0 1 1 0 1 (0x4d)(333)
GeographicPosition ::= OCTET STRING

-- 2.2.2.11 (ANSI-41 6.5.2.fl) J-STD-036-AD-1
-- 1 0 0 1 1 1 1 1 (0x9f)
-- 1 0 0 0 0 0 1 0 (0x82)
-- 0 1 0 0 1 1 1 0 (0x4e)(334)
-- MobileCallStatus ::= OCTET STRING

-- 2.2.2.12 (ANSI-41 6.5.2.fm) J-STD-036-AD-1
-- 1 0 0 1 1 1 1 1 (0x9f)
-- 1 0 0 0 0 0 1 0 (0x82)
-- 0 1 0 0 1 1 1 1 (0x4f)(335)
MobilePositionCapability ::= OCTET STRING

-- 2.3.2.14 MobInfo_AMPS
-- The MobInfo_AMPS (AMPS Analog Mobile Information) is a collection of information
-- needed to determine the position of an MS that is currently operating in the AMPS analog mode.
-- The MobInfo_AMPS macro has been defined solely for editorial convenience, and does not
-- affect the encoding in any way.

-- 	channelData								[5] IMPLICIT ChannelData OPTIONAL,
	-- (Serving) M 6.5.2.47
--	dtxIndication							[329] IMPLICIT DTXIndication OPTIONAL,
	-- O 6.5.2.fg a
-- 	receivedSignalQuality					[72] IMPLICIT ReceivedSignalQuality OPTIONAL,
	-- O 6.5.2.106 a

-- 2.3.2.15 MobInfo_CDMA
-- 6.5.2.fo MobInfo_CDMA
-- MobInfo_CDMA Macro
--	cdmaChannelData							[63] IMPLICIT CDMAChannelData OPTIONAL,
	-- (Serving) O 6.5.2.30 c
--	cdmaCodeChannel							[68] IMPLICIT CDMACodeChannel OPTIONAL,
	-- O 6.5.2.31 a
--	cdmaMobileCapabilities					[330] IMPLICIT CDMAMobileCapabilities OPTIONAL,
	-- O 6.5.2.xx a
--	cdmaPrivateLongCodeMask					[67] IMPLICIT CDMAPrivateLongCodeMask OPTIONAL,
	-- O 6.5.2.36 a
-- 	cdmaServingOneWayDelay2					[347] IMPLICIT	CDMAServingOneWayDelay2 OPTIONAL,
	-- O 6.5.2.gd a
--	cdmaServiceOption						[175] IMPLICIT CDMAServiceOption OPTIONAL,
	-- O 6.5.2.f m
--	cdmaTargetMAHOList						[136] IMPLICIT CDMATargetMAHOList OPTIONAL,
	-- O 6.5.2.43 g
--	cdmaPSMMList							[346] IMPLICIT CDMAPSMMList OPTIONAL,
	-- O 6.5.2.gc a

-- 2.3.2.16 MobInfo_NAMPS TIA/EIA/J-STD-036-A
-- 	channelData								[5] IMPLICIT ChannelData OPTIONAL,
	-- (Serving) M 6.5.2.47
-- nampsChannelData							[76] IMPLICIT NAMPSChannelData OPTIONAL,
	-- (Serving) M 6.5.2.86
--	dtxIndication							[329] IMPLICIT DTXIndication OPTIONAL,
	-- O 6.5.2.fg a
-- 	receivedSignalQuality					[72] IMPLICIT ReceivedSignalQuality OPTIONAL,
	-- O 6.5.2.106 a

-- 2.3.2.17 MobInfo_TDMA
-- (new for ANSI-41-D Chapter 5, page 5-306)
-- The MobInfo_TDMA (TDMA Mobile Information) is a collection of information needed to
-- determine the position of an MS that is currently operating in the TDMA mode. The
-- MobInfo_TDMA macro has been defined solely for editorial convenience, and does not affect
-- the encoding in any way.
-- 	tdmaChannelData							[28] IMPLICIT TDMAChannelData,
	-- M 6.5.2.153
--	dtxIndication							[329] IMPLICIT DTXIndication OPTIONAL,
	-- O 6.5.2.fg a
-- receivedSignalQuality					[72] IMPLICIT ReceivedSignalQuality OPTIONAL,
	-- O 6.5.2.106 a
-- 	targetMeasurementList					[157] IMPLICIT TargetMeasurementList OPTIONAL,
	-- O 6.5.2.150 a
--	tdma-MAHO-CELLID						[359] IMPLICIT TDMA-MAHO-CELLID OPTIONAL,
	-- O 2.3.2.26 b
-- tdma-MAHO-CHANNEL						[360] IMPLICIT TDMA-MAHO-CHANNEL OPTIONAL,
	-- O 2.3.2.27 c
-- tdma-TimeAlignment						[362] IMPLICIT TDMA-TimeAlignment OPTIONAL,
	-- O 2.3.2.29 d
-- tdmaVoiceMode							[223] IMPLICIT TDMAVoiceMode OPTIONAL,
	-- O ANSI-41-E a
-- voicePrivacyMask							[48] IMPLICIT VoicePrivacyMask OPTIONAL,
	-- O 6.5.2.166 a

-- 2.2.2.18 (ANSI-41 6.5.2.fr)  J-STD-036-AD-1
-- 1 0 1 1 1 1 1 1 (0x9f)
-- 1 0 0 0 0 0 1 0 (0x82)
-- 0 1 0 1 0 0 0 0 (0x50)(336)
PositionInformation ::= SET {
	generalizedTime			[331] IMPLICIT GeneralizedTime,
	-- M 6.5.2.fi
	geographicPosition		[333] IMPLICIT GeographicPosition,
	-- M 6.5.2.fk
	positionSource			[339] IMPLICIT PositionSource OPTIONAL,
	-- O 6.5.2.fu
	horizontal-Velocity		[379] IMPLICIT Horizontal-Velocity OPTIONAL,
	-- O 6.5.2.hk
	vertical-Velocity		[380] IMPLICIT Vertical-Velocity OPTIONAL,
	-- O 6.5.2.hl
	...
}

-- 2.2.2.19 (ANSI-41 6.5.2.fs) J-STD-036-AD-1
-- 1 0 0 1 1 1 1 1 (0x9f)
-- 1 0 0 0 0 0 1 0 (0x82)
-- 0 1 0 1 0 0 0 1 (0x51)(337)
PositionRequestType ::= OCTET STRING

-- 2.2.2.20 (ANSI-41 6.5.2.ft) J-STD-036-AD-1
-- 1 0 0 1 1 1 1 1 (0x9f)
-- 1 0 0 0 0 0 1 0 (0x82)
-- 0 1 0 1 0 0 1 0 (0x52)(338)
PositionResult ::= OCTET STRING

-- 2.2.2.21 (ANSI-41 6.5.2.fu) J-STD-036-AD-1
-- 1 0 0 1 1 1 1 1 (0x9f)
-- 1 0 0 0 0 0 1 0 (0x82)
-- 0 1 0 1 0 0 1 1 (0x53)(339)
PositionSource ::= OCTET STRING

-- 6.5.2.fv ACGEncountered N.S0023-0 v 1.0
-- 1 0 0 1 1 1 1 1 (0x9f)
-- 1 0 0 0 0 0 1 0 (0x82)
-- 0 1 0 1 0 1 0 0 (0x54)(340)
ACGEncountered ::= OCTET STRING

-- 6.5.2.fw N.S0023-0 v 1.0
-- 1 0 0 1 1 1 1 1 (0x9f)
-- 1 0 0 0 0 0 1 0 (0x82)
-- 0 1 0 1 0 1 0 1 (0x55)(341)
ControlType ::= OCTET STRING

-- 6.5.2.fx GapDuration N.S0023-0 v 1.0
-- 1 0 0 1 1 1 1 1 (0x9f)
-- 1 0 0 0 0 0 1 0 (0x82)
-- 0 1 0 1 0 1 1 0 (0x56)(342)
GapDuration ::= ENUMERATED{
	not-used (0)
	}

-- 6.5.2.fy GapInterval
-- The GapInterval (GAPINT) identifies the average minimum amount of time in seconds
-- that the NE must wait before sending another query of the type under control. The
-- GapInterval CHOICE is not explicitly encoded with a parameter identifier and length.
GapInterval ::= CHOICE {
	sCFOverloadGapInterval					[343] IMPLICIT SCFOverloadGapInterval,
	-- O 6.5.2.fz a
	serviceManagementSystemGapInterval		[344] IMPLICIT ServiceManagementSystemGapInterval
	-- O 6.5.2.ga b
}

-- 6.5.2.fz N.S0023-0 v 1.0
-- 1 0 0 1 1 1 1 1 (0x9f)
-- 1 0 0 0 0 0 1 0 (0x82)
-- 0 1 0 1 0 1 1 1 (0x57)(343)
SCFOverloadGapInterval ::= ENUMERATED {
	not-used (0)
	}


-- 6.5.2.ga N.S0023-0 v 1.0
-- 1 0 0 1 1 1 1 1 (0x9f)
-- 1 0 0 0 0 0 1 0 (0x82)
-- 0 1 0 1 1 0 0 0 (0x58)(344)
ServiceManagementSystemGapInterval ::= ENUMERATED{
	not-used (0)
	}

-- 2.2.2.3 (ANSI-41 6.5.2.gb) J-STD-036-AD-1
-- 1 0 0 1 1 1 1 1
-- 1 0 0 0 0 0 1 0
-- 0 1 0 1 1 0 0 1(0x59)(345)
CDMAPSMMCount ::= OCTET STRING

-- 2.2.2.4 (ANSI-41 6.5.2.gc) J-STD-036-AD-1
-- 1 0 1 1 1 1 1 1 (0x9f)
-- 1 0 0 0 0 0 1 0 (0x82)
-- 0 1 0 1 1 0 1 0 (0x5a)(346)
 CDMAPSMMList ::= SET OF SET{
	cdmaServingOneWayDelay2		[347] IMPLICIT CDMAServingOneWayDelay2,
	-- M 6.5.2.gd
	cdmaTargetMAHOList			[136] IMPLICIT CDMATargetMAHOList,
	-- M 6.5.2.43
	cdmaTargetMAHOList2			[136] IMPLICIT CDMATargetMAHOList OPTIONAL
	-- O 6.5.2.43 a
}

-- 2.2.2.5 (ANSI-41 6.5.2.gd) J-STD-036-AD-1
-- 1 0 0 1 1 1 1 1 (0x9f)
-- 1 0 0 0 0 0 1 0 (0x82)
-- 0 1 0 1 1 0 1 1 (0x5b)(347)
CDMAServingOneWayDelay2 ::= OCTET STRING

-- 6.5.2.ge (Misc. 10.9)
-- 1 0 0 1 1 1 1 1 (0x9f)
-- 1 0 0 0 0 0 1 0 (0x82)
-- 0 1 0 1 1 1 0 0 (0x5c)(348)
QoSPriority ::= OCTET STRING

-- 6.5.2.gf
-- 1 0 0 1 1 1 1 1 (0x9f)
-- 1 0 0 0 0 0 1 0 (0x82)
-- 0 1 0 1 1 1 0 1 (0x5d)(349)
PDSNAddress ::= OCTET STRING

-- 6.5.2.gg
-- 1 0 0 1 1 1 1 1 (0x9f)
-- 1 0 0 0 0 0 1 0 (0x82)
-- 0 1 0 1 1 1 1 0 (0x5e)(350)
PDSNProtocolType ::= OCTET STRING

-- 6.5.2.gh
-- 1 0 0 1 1 1 1 1 (0x9f)
-- 1 0 0 0 0 0 1 0 (0x82)
-- 0 1 0 1 1 1 1 1 (0x5f)(351)
CDMAMSMeasuredChannelIdentity ::= OCTET STRING

--  6.5.2.gj Range N.S0025-B v1.0
-- 1 0 0 1 1 1 1 1 (0x9f)
-- 1 0 0 0 0 0 1 0 (0x82)
-- 0 1 1 0 0 0 0 0 (0x60)(352)
Range ::= INTEGER

-- 6.5.2.gk InvokingNEType N.S0025-B v1.0
-- 1 0 0 1 1 1 1 1 (0x9f)
-- 1 0 0 0 0 0 1 0 (0x82)
-- 0 1 1 0 0 0 0 1 (0x61)(353)
InvokingNEType ::= INTEGER

-- 1 0 0 1 1 1 1 1 (0x9f)
-- 1 0 0 0 0 0 1 0 (0x82)
-- 0 1 1 0 0 0 1 0 (0x62)(354)

-- 6.5.2.gl
-- 1 0 0 1 1 1 1 1 (0x9f)
-- 1 0 0 0 0 0 1 0 (0x82)
-- 0 1 1 0 0 0 1 1 (0x63)(355)
CallingPartyCategory ::= OCTET STRING

--The CallingPartyCategory (CPC) parameter identifies the Calling Party's Category. This
--parameter is based on the Calling Party's Category parameter defined in Section 3.11 of
--ITU-T Q.763-1997 and includes the "reserved for national use" values.


-- 6.5.2.gm
-- 1 0 0 1 1 1 1 1 (0x9f)
-- 1 0 0 0 0 0 1 0 (0x82)
-- 0 1 1 0 0 1 0 0 (0x64)(356)
CDMA2000HandoffInvokeIOSData ::= OCTET STRING

-- 6.5.2.gn
-- 1 0 0 1 1 1 1 1 (0x9f)
-- 1 0 0 0 0 0 1 0 (0x82)
-- 0 1 1 0 0 1 0 1 (0x65)(357)
CDMA2000HandoffResponseIOSData ::= OCTET STRING

-- 6.5.2.go X.S0002-0 v2.0
-- 1 0 0 1 1 1 1 1 (0x9f)
-- 1 0 0 0 0 0 1 0 (0x82)
-- 0 1 1 0 0 1 1 0 (0x66)(358)
LCS-Client-ID ::= DigitsType

-- 2.3.2.26 TIA/EIA/J-STD-036-A
-- 1 0 0 1 1 1 1 1 (0x9f)
-- 1 0 0 0 0 0 1 0 (0x82)
-- 0 1 1 0 0 1 1 1 (0x67)(359)
TDMA-MAHO-CELLID ::= OCTET STRING

-- 2.3.2.27
-- 1 0 0 1 1 1 1 1 (0x9f)
-- 1 0 0 0 0 0 1 0 (0x82)
-- 0 1 1 0 1 0 0 0 (0x68)(360)
TDMA-MAHO-CHANNEL ::= OCTET STRING

-- 2.3.2.29
-- 1 0 0 1 1 1 1 1 (0x9f)
-- 1 0 0 0 0 0 1 0 (0x82)
-- 0 1 1 0 1 0 1 0 (0x6a)(362)
TDMA-TimeAlignment ::= OCTET STRING

-- 1 0 0 1 1 1 1 1 (0x9f)
-- 1 0 0 0 0 0 1 0 (0x82)
-- 0 1 1 0 1 1 0 0 (0x6c)(364)
-- 2.3.2.28
TDMA-MAHORequest ::= OCTET STRING

-- 6.5.2.gr
-- 1 0 0 1 1 1 1 1 (0x9f)
-- 1 0 0 0 0 0 1 0 (0x82)
-- 0 1 1 0 1 0 0 1 (0x69)(361)
CDMAServiceOptionConnectionIdentifier ::= OCTET STRING

-- (0x6a)(362)
-- (0x6b)(363)
-- (0x6c)(364)
-- (0x6d)(365)
-- (0x6e)(366)

-- 6.5.2.gx X.S0002-0 v2.0
-- 1 0 0 1 1 1 1 1 (0x9f)
-- 1 0 0 0 0 0 1 0 (0x82)
-- 0 1 1 0 1 1 1 1 (0x6f)(367)
LCSBillingID ::= OCTET STRING

-- 6.5.2.gy X.S0002-0 v2.0
-- 1 0 0 1 1 1 1 1 (0x9f)
-- 1 0 0 0 0 0 1 0 (0x82)
-- 0 1 1 1 0 0 0 0 (0x70)(368)
LIRAuthorization ::= ENUMERATED {
	not-used			(0),
	user-Authorized		(1)
	}

-- 6.5.2.gz X.S0002-0 v2.0
-- 1 0 0 1 1 1 1 1 (0x9f)
-- 1 0 0 0 0 0 1 0 (0x82)
-- 0 1 1 1 0 0 0 1 (0x71)(369)
LIRMode ::= ENUMERATED {
	not-used			(0),
	unconditionally-Restricted		(1),
	pre-Authorized-LCS-Clients-Only (2),
	pre-Authorized-LCS-Clients-and-User-Authorized-LCS-Clients (3),
	unrestricted (4)
	}

-- 6.5.2.ha X.S0002-0 v2.0
-- 1 0 0 1 1 1 1 1
-- 1 0 0 0 0 0 1 0
-- 0 1 1 1 0 0 1 0 (0x72)(370)
MPCAddress ::= DigitsType

-- 6.5.2.hb X.S0002-0 v2.0
-- 1 0 0 1 1 1 1 1
-- 1 0 0 0 0 0 1 0
-- 0 1 1 1 0 0 1 1 (0x73)(371)
MPCID ::= DigitsType

--6.5.2.hc PositionQualityOfService
--(New for MAP, Section 6.5.2)
--The PositionQualityOfService (PQOS) is a collection of the required levels for the
--independent positioning attributes that should be satisfied by the position estimate. The
--PositionQualityOfService macro has been defined solely for editorial convenience and
--does not affect the encoding in any way.
--	pqos-HorizontalPosition					[372] IMPLICIT PQOS-HorizontalPosition OPTIONAL,
	-- O 6.5.2.hd a, b
--	pqos-HorizontalVelocity					[373] IMPLICIT PQOS-HorizontalVelocity OPTIONAL,
	-- O 6.5.2.he c
--	pqos-MaximumPositionAge					[374] IMPLICIT PQOS-MaximumPositionAge OPTIONAL,
	-- O 6.5.2.hf d
--	pqos-PositionPriority					[375] IMPLICIT	PQOS-PositionPriority OPTIONAL,
	-- O 6.5.2.hg e
--	pqos-ResponseTime						[376] IMPLICIT PQOS-ResponseTime OPTIONAL,
	-- O 6.5.2.hh f
--	pqos-VerticalPosition					[377] IMPLICIT	PQOS-VerticalPosition OPTIONAL,
	-- O 6.5.2.hi g
--	pqos-VerticalVelocity					[378] IMPLICIT PQOS-VerticalVelocity OPTIONAL,
	-- O 6.5.2.hj h

-- 6.5.2.hd X.S0002-0 v2.0
-- 1 0 0 1 1 1 1 1
-- 1 0 0 0 0 0 1 0
-- 0 1 1 1 0 1 0 0 (0x74)(372)
PQOS-HorizontalPosition ::= OCTET STRING

-- 6.5.2.he X.S0002-0 v2.0
-- 1 0 0 1 1 1 1 1
-- 1 0 0 0 0 0 1 0
-- 0 1 1 1 0 1 0 1 (0x75)(373)
PQOS-HorizontalVelocity ::= OCTET STRING

--  6.5.2.hf X.S0002-0 v2.0
-- 1 0 0 1 1 1 1 1
-- 1 0 0 0 0 0 1 0
-- 0 1 1 1 0 1 1 0 (0x76)(374)
PQOS-MaximumPositionAge ::= OCTET STRING

--  6.5.2.hg X.S0002-0 v2.0
-- 1 0 0 1 1 1 1 1
-- 1 0 0 0 0 0 1 0
-- 0 1 1 1 0 1 1 1 (0x77)(375)
PQOS-PositionPriority ::= OCTET STRING

-- 6.5.2.hh X.S0002-0 v2.0
-- 1 0 0 1 1 1 1 1
-- 1 0 0 0 0 0 1 0
-- 0 1 1 1 1 0 0 0 (0x78)(376)
PQOS-ResponseTime  ::= ENUMERATED {
	not-used			(0),
	no-Delay			(1),
	low-Delay			(2),
	delay-Tolerant		(3)
	}

-- 6.5.2.hi X.S0002-0 v2.0
-- 1 0 0 1 1 1 1 1
-- 1 0 0 0 0 0 1 0
-- 0 1 1 1 1 0 0 1 (0x79)(377)
PQOS-VerticalPosition ::= OCTET STRING

-- 6.5.2.hj X.S0002-0 v2.0
-- 1 0 0 1 1 1 1 1
-- 1 0 0 0 0 0 1 0
-- 0 1 1 1 1 0 1 0 (0x7a)(378)
PQOS-VerticalVelocity ::= OCTET STRING

-- 6.5.2.hk X.S0002-0 v2.0
-- 1 0 0 1 1 1 1 1
-- 1 0 0 0 0 0 1 0
-- 0 1 1 1 1 0 1 1 (0x7b)(379)
Horizontal-Velocity ::= OCTET STRING

-- 6.5.2.hl X.S0002-0 v2.0
-- 1 0 0 1 1 1 1 1
-- 1 0 0 0 0 0 1 0
-- 0 1 1 1 1 1 0 0 (0x7c)(380)
Vertical-Velocity ::= OCTET STRING

-- 6.5.2.hm X.S0002-0 v2.0
-- 1 0 1 1 1 1 1 1 (0x9f)
-- 1 0 0 0 0 0 1 0 (0x82)
-- 0 1 1 1 1 1 0 1 (0x7d)(381)
MPCAddressList ::= SET{
	mpcAddress		[370] IMPLICIT MPCAddress,
	-- M 6.5.2.ha
	mpcAddress2		[370] IMPLICIT MPCAddress OPTIONAL,
	-- O 6.5.2.ha a
	...
}
-- (0x7e)(382)
-- (0x7f)(383)
-- (0x00)(384)
-- (0x01)(385)
-- (0x02)(386)
-- (0x03)(387)

-- 2.138 http://www.3gpp2.org/Public_html/specs/X.S0004-550-E_v1.0_040406.pdf
-- 1 0 0 1 1 1 1 1 (0x9f)
-- 1 0 0 0 0 0 1 1 (0x83)
-- 0 0 0 0 0 1 0 0 (0x04)(388)
MINExtension ::= OCTET STRING

-- 3.3.2.2 X.S0008-0 v1.0
-- 1 0 0 1 1 1 1 1 (0x9f)
-- 1 0 0 0 0 0 1 1 (0x83)
-- 0 0 0 0 0 1 0 1 (0x05)(389)
Information-Record ::= OCTET STRING

-- 3.3.2.3  X.S0008-0 v1.0
-- 1 0 0 1 1 1 1 1 (0x9f)
-- 1 0 0 0 0 0 1 1 (0x83)
-- 0 0 0 0 0 1 1 0 (0x06)(390)
MEID ::= OCTET STRING

-- 3.3.2.97  X.S0008-0 v1.0
-- 1 0 0 1 1 1 1 1 (0x9f)
-- 1 0 0 0 0 0 1 1 (0x83)
-- 0 0 0 0 0 1 1 1 (0x07)(391)
MEIDStatus ::= OCTET STRING

-- 3.3.2.98  X.S0008-0 v1.0
-- 1 0 0 1 1 1 1 1 (0x9f)
-- 1 0 0 0 0 0 1 1 (0x83)
-- 0 0 0 0 1 0 0 0 (0x08)(392)
Record-Type ::= OCTET STRING

-- 3.3.2.98  X.S0008-0 v1.0, X.S0004-550
-- 1 0 0 1 1 1 1 1 (0x9f)
-- 1 0 0 0 0 0 1 1 (0x83)
-- 0 0 0 1 0 0 0 1 (0x11)(401)
MEIDValidated ::= NULL

-- 6.5.2.lB N.S0011-0 v 1.0
-- 1 0 0 1 1 1 1 1 (0x9f)
-- 1 0 0 0 0 0 0 1 (0x81)
-- 0 0 1 1 0 1 0 1 (0x35)(181)
AKeyProtocolVersion ::= OCTET STRING


-- 6.5.2.mT N.S0011-0 v 1.0
-- 1 0 0 1 1 1 1 1 (0x9f)
-- 1 0 0 0 0 0 0 1 (0x81)
-- 0 0 1 1 0 1 1 0 (0x36)(182)
AuthenticationResponseReauthentication ::= OCTET STRING

-- 6.5.2.nB N.S0011-0 v 1.0
-- 1 0 0 1 1 1 1 1 (0x9f)
-- 1 0 0 0 0 0 0 1 (0x81)
-- 0 0 1 1 0 1 1 1 (0x37)(183)
BaseStationPartialKey ::= OCTET STRING

-- 6.5.2.oC N.S0011-0 v 1.0
-- 1 0 0 1 1 1 1 1 (0x9f)
-- 1 0 0 0 0 0 0 1 (0x81)
-- 0 0 1 1 1 0 0 0 (0x38)(184)
MobileStationMIN ::= MINType
-- b. Refer to the MINType parameter type (see 6.5.3.u1) for notes and field encoding.

-- 6.5.2.pB N.S0011-0 v 1.0
-- 1 0 0 1 1 1 1 1 (0x9f)
-- 1 0 0 0 0 0 0 1 (0x81)
-- 0 0 1 1 1 0 0 1 (0x39)(185)
MobileStationPartialKey ::= OCTET STRING

-- 6.5.2.qB N.S0011-0 v 1.0
-- 1 0 0 1 1 1 1 1 (0x9f)
-- 1 0 0 0 0 0 0 1 (0x81)
-- 0 0 1 1 1 0 1 0 (0x3a)(186)
ModulusValue ::= OCTET STRING

-- 6.5.2.rB N.S0011-0 v 1.0
-- 1 0 0 1 1 1 1 1 (0x9f)
-- 1 0 0 0 0 0 0 1 (0x81)
-- 0 0 1 1 1 0 1 1 (0x3b)(187)
NewlyAssignedMIN ::= MINType


-- 6.5.2.sB N.S0011-0 v 1.0
-- 1 0 0 1 1 1 1 1 (0x9f)
-- 1 0 0 0 0 0 0 1 (0x81)
-- 0 0 1 1 1 1 0 1 (0x3d)(189)
OTASP-ResultCode ::= OCTET STRING

-- 6.5.2.tB N.S0011-0 v 1.0
-- 1 0 0 1 1 1 1 1 (0x9f)
-- 1 0 0 0 0 0 0 1 (0x81)
-- 0 0 1 1 1 1 1 0 (0x3e)(190)
PrimitiveValue ::= OCTET STRING

-- 6.5.2.uT N.S0011-0 v 1.0
-- 1 0 0 1 1 1 1 1 (0x9f)
-- 1 0 0 0 0 0 0 1 (0x81)
-- 0 0 1 1 1 1 1 1 (0x3f)(191)
RandomVariableReauthentication ::= OCTET STRING

-- 6.5.2.vT N.S0011-0 v 1.0
-- 1 0 0 1 1 1 1 1 (0x9f)
-- 1 0 0 0 0 0 0 1 (0x81)
-- 0 1 0 0 0 0 0 0 (0x40)(192)
ReauthenticationReport ::= OCTET STRING

-- 6.5.2.wB N.S0011-0 v 1.0
-- 1 0 0 1 1 1 1 1 (0x9f)
-- 1 0 0 0 0 0 0 1 (0x81)
-- 0 1 0 0 0 0 0 1 (0x41)(193)
ServiceIndicator ::= OCTET STRING

-- 6.5.2.xB N.S0011-0 v 1.0
-- 1 0 0 1 1 1 1 1 (0x9f)
-- 1 0 0 0 0 0 0 1 (0x81)
-- 0 1 0 0 0 0 1 0 (0x42)(194)
SignalingMessageEncryptionReport ::= OCTET STRING


-- 6.5.2.yC N.S0011-0 v 1.0
-- 1 0 0 1 1 1 1 1 (0x9f)
-- 1 0 0 0 0 0 0 1 (0x81)
-- 0 1 0 0 0 0 1 1 (0x43)(195)
TemporaryReferenceNumber ::= MINType

-- 6.5.2.zB N.S0011-0 v 1.0
-- 1 0 0 1 1 1 1 1 (0x9f)
-- 1 0 0 0 0 0 0 1 (0x81)
-- 0 1 0 0 0 1 0 0 (0x44)(196)
VoicePrivacyReport::= OCTET STRING

-- 6.5.2.dnC N.S0011-0 v 1.0
-- 1 0 0 1 1 1 1 1 (0x9f)
-- 1 0 0 0 0 0 1 0 (0x82)
-- 0 0 0 1 1 1 0 0 (0x1c)(284)
MSC-Address::= DigitsType

-- 6.5.2.dpC N.S0011-0 v 1.0
-- 1 0 0 1 1 1 1 1 (0x9f)
-- 1 0 0 0 0 0 1 0 (0x82)
-- 0 0 0 1 1 1 1 0 (0x1e)(286)
MobileStationIMSI ::= IMSIType

-- 6.5.2.dqB N.S0011-0 v 1.0
-- 1 0 0 1 1 1 1 1 (0x9f)
-- 1 0 0 0 0 0 1 0 (0x82)
-- 0 0 0 1 1 1 1 1 (0x1f)(287)
NewlyAssignedIMSI ::= IMSIType

-- 6.5.2.adC MobileStationMSID N.S0011-0 v 1.0
--The MobileStationMSID (MS_MSID) identifies the MIN or the IMSI value stored in the
--MS's permanent memory at an OTASP call origination. The MS_MSID CHOICE is not
--explicitly encoded with a parameter ID and length.

MobileStationMSID ::= CHOICE {
	mobileStationMIN			[184] IMPLICIT MobileStationMIN,
	-- O 6.5.2.oC
	mobileStationIMSI			[286] IMPLICIT MobileStationIMSI
	-- O 6.5.2.dpC
	}
	
-- 6.5.2.aeB NewlyAssignedMSID
--The NewlyAssignedMSID (NEWMSID) identifies the MIN or the IMSI value that may be
--assigned following the successful completion of the OTASP process. The MS_MSID
--CHOICE is not explicitly encoded with a parameter ID and length.	

NewlyAssignedMSID ::= CHOICE {
	newlyAssignedMIN				[187] IMPLICIT NewlyAssignedMIN,
	-- O 6.5.2.rB
	newlyAssignedIMSI				[287] IMPLICIT NewlyAssignedIMSI
	-- O 6.5.2.dqB
	}

--Notes:
--a. Parameters with references ending with a "B" in them, such as "6.5.2.qB" are
--common to BOTH CDMA and TDMA OTASP.
--b. Parameters with references ending with a "C" in them, such as "6.5.2.oC" are
--unique to CDMA OTASP.
--c. Parameters with references ending with a "T" in them, such as "6.5.2.uT" are
--unique to TDMA OTASP.

-- 6.5.3 Parameter Type Definitions
-- 6.5.3.2
DigitsType ::= OCTET STRING

-- 6.5.3.13
Subaddress ::= OCTET STRING

-- 6.5.3.u1 MINType
MINType ::= OCTET STRING

-- 6.5.3.u2 IMSIType

IMSIType ::= OCTET STRING



-- Definition to support ASN2WRS generating hf_indices

InvokeData ::= SEQUENCE {
    handoffMeasurementRequest HandoffMeasurementRequest,
	facilitiesDirective FacilitiesDirective,
	handoffBack HandoffBack,
	facilitiesRelease FacilitiesRelease,
	qualificationRequest QualificationRequest,
	qualificationDirective QualificationDirective,
	blocking Blocking,
	unblocking Unblocking,
	resetCircuit ResetCircuit,
	trunkTest TrunkTest,
	trunkTestDisconnect TrunkTestDisconnect,
	registrationNotification RegistrationNotification,
	registrationCancellation RegistrationCancellation,
	locationRequest LocationRequest,
	routingRequest RoutingRequest,
	featureRequest FeatureRequest,
	unreliableRoamerDataDirective UnreliableRoamerDataDirective,
	mSInactive MSInactive,
	transferToNumberRequest TransferToNumberRequest,
	redirectionRequest RedirectionRequest,
	handoffToThird HandoffToThird,
	flashRequest FlashRequest,
	authenticationDirective AuthenticationDirective,
	authenticationRequest AuthenticationRequest,
	baseStationChallenge BaseStationChallenge,
	authenticationFailureReport AuthenticationFailureReport,
	countRequest CountRequest,
	interSystemPage InterSystemPage,
	unsolicitedResponse UnsolicitedResponse,
	bulkDeregistration BulkDeregistration,
	handoffMeasurementRequest2 HandoffMeasurementRequest2,
	facilitiesDirective2 FacilitiesDirective2,
	handoffBack2 HandoffBack2,
	handoffToThird2 HandoffToThird2,
	authenticationDirectiveForward AuthenticationDirectiveForward,
	authenticationStatusReport AuthenticationStatusReport,
	informationDirective InformationDirective,
	informationForward InformationForward,
	interSystemAnswer InterSystemAnswer,
	interSystemPage2 InterSystemPage2,
	interSystemSetup InterSystemSetup,
	originationRequest OriginationRequest,
	randomVariableRequest RandomVariableRequest,
	redirectionDirective RedirectionDirective,
	remoteUserInteractionDirective RemoteUserInteractionDirective,
	sMSDeliveryBackward SMSDeliveryBackward,
	sMSDeliveryForward SMSDeliveryForward,
	sMSDeliveryPointToPoint SMSDeliveryPointToPoint,
	sMSNotification SMSNotification,
	sMSRequest SMSRequest,
	oTASPRequest OTASPRequest,
	changeFacilities ChangeFacilities,
	changeService ChangeService,
	parameterRequest ParameterRequest,
	tMSIDirective TMSIDirective,
	numberPortabilityRequest NumberPortabilityRequest,
	serviceRequest ServiceRequest,
	analyzedInformation AnalyzedInformation,
	connectionFailureReport ConnectionFailureReport,
	connectResource ConnectResource,
	facilitySelectedAndAvailable FacilitySelectedAndAvailable,
	modify Modify,
	search Search,
	seizeResource SeizeResource,
	sRFDirective SRFDirective,
	tBusy TBusy,
	tNoAnswer TNoAnswer,
	smsDeliveryPointToPointAck SMSDeliveryPointToPointAck,
	messageDirective MessageDirective,
	bulkDisconnection BulkDisconnection,
	callControlDirective CallControlDirective,
	oAnswer OAnswer,
	oDisconnect ODisconnect,
	callRecoveryReport CallRecoveryReport,
	tAnswer TAnswer,
	tDisconnect TDisconnect,
	unreliableCallData UnreliableCallData,
	oCalledPartyBusy OCalledPartyBusy,
	oNoAnswer ONoAnswer,
	positionRequest PositionRequest,
	positionRequestForward PositionRequestForward,
	callTerminationReport CallTerminationReport,
	geoPositionRequest GeoPositionRequest,
	interSystemPositionRequest InterSystemPositionRequest,
	interSystemPositionRequestForward InterSystemPositionRequestForward,
	aCGDirective ACGDirective,
	roamerDatabaseVerificationRequest RoamerDatabaseVerificationRequest,
	addService AddService,
	dropService DropService,
	lcsParameterRequest LCSParameterRequest,
	checkMEID	CheckMEID,
	positionEventNotification PositionEventNotification,
	statusRequest StatusRequest,
	interSystemSMSDeliveryPointToPoint InterSystemSMSDeliveryPointToPoint,
	qualificationRequest2 QualificationRequest2
}

ReturnData ::= SEQUENCE {
	handoffMeasurementRequestRes HandoffMeasurementRequestRes,
	facilitiesDirectiveRes FacilitiesDirectiveRes,
	handoffBackRes HandoffBackRes,
	facilitiesReleaseRes FacilitiesReleaseRes,
	qualificationDirectiveRes QualificationDirectiveRes,
	qualificationRequestRes QualificationRequestRes,
	resetCircuitRes ResetCircuitRes,
	registrationNotificationRes RegistrationNotificationRes,
	registrationCancellationRes RegistrationCancellationRes,
	locationRequestRes LocationRequestRes,
	routingRequestRes RoutingRequestRes,
	featureRequestRes FeatureRequestRes,
	transferToNumberRequestRes TransferToNumberRequestRes,
	handoffToThirdRes HandoffToThirdRes,
	authenticationDirectiveRes AuthenticationDirectiveRes,
	authenticationRequestRes AuthenticationRequestRes,
	baseStationChallengeRes BaseStationChallengeRes,
	authenticationFailureReportRes AuthenticationFailureReportRes,
	countRequestRes CountRequestRes,
	interSystemPageRes InterSystemPageRes,
	unsolicitedResponseRes UnsolicitedResponseRes,
	handoffMeasurementRequest2Res HandoffMeasurementRequest2Res,
	facilitiesDirective2Res FacilitiesDirective2Res,
	handoffBack2Res HandoffBack2Res,
	handoffToThird2Res HandoffToThird2Res,
	authenticationDirectiveForwardRes AuthenticationDirectiveForwardRes,
	authenticationStatusReportRes AuthenticationStatusReportRes,
	informationDirectiveRes InformationDirectiveRes,
	informationForwardRes InformationForwardRes,
	interSystemPage2Res InterSystemPage2Res,
	interSystemSetupRes InterSystemSetupRes,
	originationRequestRes OriginationRequestRes,
	randomVariableRequestRes RandomVariableRequestRes,
	remoteUserInteractionDirectiveRes RemoteUserInteractionDirectiveRes,
	sMSDeliveryBackwardRes SMSDeliveryBackwardRes,
	sMSDeliveryForwardRes SMSDeliveryForwardRes,
	sMSDeliveryPointToPointRes SMSDeliveryPointToPointRes,
	sMSNotificationRes SMSNotificationRes,
	sMSRequestRes SMSRequestRes,
	oTASPRequestRes OTASPRequestRes,
	changeFacilitiesRes ChangeFacilitiesRes,
	changeServiceRes ChangeServiceRes,
	parameterRequestRes ParameterRequestRes,
	tMSIDirectiveRes TMSIDirectiveRes,
	numberPortabilityRequestRes NumberPortabilityRequestRes,
	serviceRequestRes ServiceRequestRes,
	analyzedInformationRes AnalyzedInformationRes,
	facilitySelectedAndAvailableRes FacilitySelectedAndAvailableRes,
	modifyRes ModifyRes,
	searchRes SearchRes,
	seizeResourceRes SeizeResourceRes,
	sRFDirectiveRes SRFDirectiveRes,
	tBusyRes TBusyRes,
	tNoAnswerRes TNoAnswerRes,
	callControlDirectiveRes CallControlDirectiveRes,
	oDisconnectRes ODisconnectRes,
	tDisconnectRes TDisconnectRes,
	oCalledPartyBusyRes OCalledPartyBusyRes,
	oNoAnswerRes ONoAnswerRes,
	positionRequestRes PositionRequestRes,
	positionRequestForwardRes PositionRequestForwardRes,
	interSystemPositionRequestRes InterSystemPositionRequestRes,
	interSystemPositionRequestForwardRes InterSystemPositionRequestForwardRes,
	roamerDatabaseVerificationRequestRes RoamerDatabaseVerificationRequestRes,
	addServiceRes AddServiceRes,
	dropServiceRes DropServiceRes,
	interSystemSMSPage InterSystemSMSPage,
	lcsParameterRequestRes LCSParameterRequestRes,
	checkMEIDRes	CheckMEIDRes,
	statusRequestRes StatusRequestRes,
	interSystemSMSDeliveryPointToPointRes InterSystemSMSDeliveryPointToPointRes,
	qualificationRequest2Res QualificationRequest2Res
}

END

-- ASN description of MPEG Packetized Elementary Stream (PES)
-- Written by Shaun Jackman <sjackman@gmail.com>
-- Copyright 2007 Shaun Jackman
--
-- This program is free software; you can redistribute it and/or
-- modify it under the terms of the GNU General Public License.

MPEG DEFINITIONS ::= BEGIN

PES ::= SEQUENCE {
	prefix OCTET STRING (SIZE (3)),
	stream INTEGER {
		picture (0),
		sequence-header (179),
		sequence-header-extension (181),
		group-of-pictures (184),
		program-end (185),
		pack-header (186),
		system-header (187),
		program-stream-map (188),
		private-stream-1 (189),
		padding-stream (190),
		private-stream-2 (191),
		audio-stream (192),
		audio-stream-1 (193),
		audio-stream-2 (194),
		audio-stream-3 (195),
		audio-stream-4 (196),
		audio-stream-5 (197),
		audio-stream-6 (198),
		audio-stream-7 (199),
		audio-stream-8 (200),
		audio-stream-9 (201),
		audio-stream-10 (202),
		audio-stream-11 (203),
		audio-stream-12 (204),
		audio-stream-13 (205),
		audio-stream-14 (206),
		audio-stream-15 (207),
		audio-stream-16 (208),
		audio-stream-17 (209),
		audio-stream-18 (210),
		audio-stream-19 (211),
		audio-stream-20 (212),
		audio-stream-21 (213),
		audio-stream-22 (214),
		audio-stream-23 (215),
		audio-stream-24 (216),
		audio-stream-25 (217),
		audio-stream-26 (218),
		audio-stream-27 (219),
		audio-stream-28 (220),
		audio-stream-29 (221),
		audio-stream-30 (222),
		audio-stream-31 (223),
		video-stream (224),
		video-stream-1 (225),
		video-stream-2 (226),
		video-stream-3 (227),
		video-stream-4 (228),
		video-stream-5 (229),
		video-stream-6 (230),
		video-stream-7 (231),
		video-stream-8 (232),
		video-stream-9 (233),
		video-stream-10 (234),
		video-stream-11 (235),
		video-stream-12 (236),
		video-stream-13 (237),
		video-stream-14 (238),
		video-stream-15 (239)
	} (0..255)
}

Stream ::= SEQUENCE {
	length INTEGER (0..65535),
	must-be-one BOOLEAN,
	must-be-zero BOOLEAN,
	scrambling-control INTEGER {
		not-scrambled (0)
	} (0..3),
	priority BOOLEAN,
	data-alignment BOOLEAN,
	copyright BOOLEAN,
	original BOOLEAN,
	pts-flag BOOLEAN,
	dts-flag BOOLEAN,
	escr-flag BOOLEAN,
	es-rate-flag BOOLEAN,
	dsm-trick-mode-flag BOOLEAN,
	additional-copy-info-flag BOOLEAN,
	crc-flag BOOLEAN,
	extension-flag BOOLEAN,
	header-data-length INTEGER (0..255)
}

Sequence-header ::= SEQUENCE {
	horizontal-size BIT STRING (SIZE (12)),
	vertical-size BIT STRING (SIZE (12)),
	aspect-ratio INTEGER {
		aspect-1to1 (1),
		aspect-4to3 (2),
		aspect-16to9 (3),
		aspect-2-21to1 (4)
	} (0..15),
	frame-rate ENUMERATED {
		reserved (0),
		fr (23976),
		fr (24000),
		fr (25000),
		fr (29970),
		fr (30000),
		fr (50000),
		fr (59940),
		fr (60000)
	},
	bit-rate BIT STRING (SIZE (18)),
	must-be-one BOOLEAN,
	vbv-buffer-size BIT STRING (SIZE (10)),
	constrained-parameters-flag BOOLEAN,
	load-intra-quantiser-matrix BOOLEAN,
	load-non-intra-quantiser-matrix BOOLEAN
}

Sequence-extension ::= SEQUENCE {
	must-be-0001 BIT STRING (SIZE (4)),
	profile-and-level INTEGER (0..255),
	progressive-sequence BOOLEAN,
	chroma-format INTEGER (0..3),
	horizontal-size-extension INTEGER (0..3),
	vertical-size-extension INTEGER (0..3),
	bit-rate-extension BIT STRING (SIZE (12)),
	must-be-one BOOLEAN,
	vbv-buffer-size-extension INTEGER (0..255),
	low-delay BOOLEAN,
	frame-rate-extension-n INTEGER (0..3),
	frame-rate-extension-d INTEGER (0..3)
}

Group-of-pictures ::= SEQUENCE {
	drop-frame-flag BOOLEAN,
	hour INTEGER (0..32),
	minute INTEGER (0..64),
	must-be-one BOOLEAN,
	second INTEGER (0..64),
	frame INTEGER (0..64),
	closed-gop BOOLEAN,
	broken-gop BOOLEAN,
	must-be-zero BIT STRING (SIZE (5))
}

Picture ::= SEQUENCE {
	temporal-sequence-number BIT STRING (SIZE (10)),
	frame-type INTEGER {
		i-frame (1),
		p-frame (2),
		b-frame (3),
		d-frame (4)
	} (0..7),
	vbv-delay BIT STRING (SIZE (16))
}

END

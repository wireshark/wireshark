-- RNSAP-CommonDataTypes.asn
--
-- Taken from 3GPP TS 25.423 V13.1.0 (2015-12)
-- http://www.3gpp.org/ftp/Specs/archive/25_series/25.423/25423-790.zip/25423-790.DOC
--
-- 9.3.5	Common Definitions
--

-- **************************************************************
--
-- Common definitions
--
-- **************************************************************


RNSAP-CommonDataTypes {
itu-t (0) identified-organization (4) etsi (0) mobileDomain (0) 
umts-Access (20) modules (3) rnsap (1) version1 (1) rnsap-CommonDataTypes (3) }

DEFINITIONS AUTOMATIC TAGS ::= 

BEGIN

-- **************************************************************
--
-- Extension constants
--
-- **************************************************************

maxPrivateIEs 									INTEGER ::= 65535
maxProtocolExtensions 							INTEGER ::= 65535
maxProtocolIEs									INTEGER ::= 65535

-- **************************************************************
--
-- Common Data Types
--
-- **************************************************************

Criticality ::= ENUMERATED { reject, ignore, notify }

Presence ::= ENUMERATED { optional, conditional, mandatory }

PrivateIE-ID ::= CHOICE {
	local				INTEGER (0.. maxPrivateIEs),
	global				OBJECT IDENTIFIER
}

ProcedureCode ::= INTEGER (0..255)

ProcedureID ::= SEQUENCE {
	procedureCode			ProcedureCode,
	ddMode				ENUMERATED { tdd, fdd, common, ... }
}

ProtocolIE-ID ::= INTEGER (0..maxProtocolIEs)

TransactionID ::= CHOICE {
	shortTransActionId	INTEGER (0..127),
	longTransActionId	INTEGER (0..32767)
}

TriggeringMessage ::= ENUMERATED { initiating-message, successful-outcome, unsuccessful-outcome, outcome }

END

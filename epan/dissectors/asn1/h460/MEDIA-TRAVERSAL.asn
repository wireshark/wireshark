-- MEDIA-TRAVERSAL.asn
--
-- Taken from ITU ASN.1 database
-- http://www.itu.int/ITU-T/asn1/database/itu-t/h/h460.19/2005/MEDIA-TRAVERSAL.asn
--

-- Module MEDIA-TRAVERSAL (H.460.19:09/2005)
MEDIA-TRAVERSAL {itu-t(0) recommendation(0) h(8) 460 19 version(0) 1}
DEFINITIONS AUTOMATIC TAGS ::=
BEGIN

IMPORTS
  TimeToLive
    FROM H323-MESSAGES
  TransportAddress
    FROM MULTIMEDIA-SYSTEM-CONTROL;

TraversalParameters ::= SEQUENCE {
  multiplexedMediaChannel         TransportAddress OPTIONAL,
  multiplexedMediaControlChannel  TransportAddress OPTIONAL,
  multiplexID                     INTEGER(0..4294967295) OPTIONAL,
  keepAliveChannel                TransportAddress OPTIONAL,
  keepAlivePayloadType            INTEGER(0..127) OPTIONAL,
  keepAliveInterval               TimeToLive OPTIONAL,
  ...
}

END

-- Generated by Asnp, the ASN.1 pretty-printer of France Telecom R&D

-- Network-Facility-Extension.asn
--
-- Taken from ITU ASN.1 database
-- http://www.itu.int/ITU-T/asn1/database/itu-t/q/q932/1998-Amd1/Network-Facility-Extension.asn
--

-- Module Network-Facility-Extension (Q.932:05/1998)
Network-Facility-Extension {iso(1) standard(0) pss1-generic-procedures(11582)
  network-facility-extension(2)} DEFINITIONS ::=
BEGIN

EXPORTS NetworkFacilityExtension;

IMPORTS
  PartyNumber
    FROM Addressing-Data-Elements {itu-t recommendation q 932
      addressing-data-elements(7)};

NetworkFacilityExtension ::= [10] IMPLICIT SEQUENCE {
  sourceEntity              [0] IMPLICIT EntityType,
  sourceEntityAddress       [1]  AddressInformation OPTIONAL,
  destinationEntity         [2] IMPLICIT EntityType,
  destinationEntityAddress  [3]  AddressInformation OPTIONAL
}

EntityType ::= ENUMERATED {endPINX(0), anyTypeOfPINX(1)}

AddressInformation ::= PartyNumber

END -- of Network Facility Extension

-- Generated by Asnp, the ASN.1 pretty-printer of France Telecom R&D

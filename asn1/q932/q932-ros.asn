-- Module Facility-Information-Element-Components (Q.932:05/1998)
Facility-Information-Element-Components {itu-t recommendation q 932
  facility-information-element-component(3)} DEFINITIONS IMPLICIT TAGS ::=
BEGIN

Code ::= CHOICE {
  local   INTEGER,
  global  OBJECT IDENTIFIER
}

RoseAPDU ::= CHOICE {
  invoke        [1]  Invoke,
  returnResult  [2]  ReturnResult,
  returnError   [3]  ReturnError,
  reject        [4]  Reject
}

Invoke ::= SEQUENCE {
  invokeId InvokeId,
  linkedId CHOICE {
    present  [0] IMPLICIT InvokeId,
    absent   [1] IMPLICIT NULL
  } OPTIONAL,
  opcode Code,
  argument ANY OPTIONAL
}

ReturnResult ::= SEQUENCE {
  invokeId InvokeId,
  result SEQUENCE {
    opcode Code,
    result ANY OPTIONAL
  }
}

ReturnError ::= SEQUENCE {
  invokeId InvokeId,
  errcode Code,
  parameter ANY OPTIONAL
}

Reject ::= SEQUENCE {
  invokeId  InvokeId,
  problem CHOICE {
    general       [0]  GeneralProblem,
    invoke        [1]  InvokeProblem,
    returnResult  [2]  ReturnResultProblem,
    returnError   [3]  ReturnErrorProblem
  }
}

GeneralProblem ::= INTEGER {
  unrecognizedComponent(0), 
  mistypedComponent(1),
  badlyStructuredComponent(2)
}

InvokeProblem ::= INTEGER {
  duplicateInvocation(0),
  unrecognizedOperation(1),
  mistypedArgument(2),
  resourceLimitation(3),
  releaseInProgress(4),
  unrecognizedLinkedId(5),
  linkedResponseUnexpected(6),
  unexpectedLinkedOperation(7)
}

ReturnResultProblem ::= INTEGER {
  unrecognizedInvocation(0),
  resultResponseUnexpected(1),
  mistypedResult(2)
}

ReturnErrorProblem ::= INTEGER {
  unrecognizedInvocation(0),
  errorResponseUnexpected(1),
  unrecognizedError(2),
  unexpectedError(3),
  mistypedParameter(4)
}

RejectProblem ::= INTEGER {
  general-unrecognizedPDU(0),
  general-mistypedPDU(1),
  general-badlyStructuredPDU(2),
  invoke-duplicateInvocation(10),
  invoke-unrecognizedOperation(11),
  invoke-mistypedArgument(12),
  invoke-resourceLimitation(13),
  invoke-releaseInProgress(14),
  invoke-unrecognizedLinkedId(15),
  invoke-linkedResponseUnexpected(16),
  invoke-unexpectedLinkedOperation(17),
  returnResult-unrecognizedInvocation(20),
  returnResult-resultResponseUnexpected(21),
  returnResult-mistypedResult(22),
  returnError-unrecognizedInvocation(30),
  returnError-errorResponseUnexpected(31),
  returnError-unrecognizedError(32),
  returnError-unexpectedError(33),
  returnError-mistypedParameter(34)
}

InvokeId ::= CHOICE {
  present  INTEGER,
  absent   NULL
}

END -- end of generic ROS PDU definitions

-- $Id$
-- **************************************************************
--
-- Elementary Procedure definitions
--
-- **************************************************************

RANAP-PDU-Descriptions  { 
itu-t (0) identified-organization (4) etsi (0) mobileDomain (0) 
umts-Access (20) modules (3) ranap (0) version1 (1) ranap-PDU-Descriptions (0)}

DEFINITIONS AUTOMATIC TAGS ::= 

BEGIN

-- **************************************************************
--
-- IE parameter types from other modules.
--
-- **************************************************************
-- Includet at the end
--IMPORTS
--	Criticality,
--	ProcedureCode
--FROM RANAP-CommonDataTypes

--	Iu-ReleaseCommand,
--	Iu-ReleaseComplete,
--	RelocationCommand,
--	RelocationPreparationFailure,
--	RelocationRequired,
--	RelocationRequest,
--	RelocationRequestAcknowledge,
--	RelocationFailure,
--	RelocationCancel,
--	RelocationCancelAcknowledge,
--	SRNS-ContextRequest,
--	SRNS-ContextResponse,
--	SecurityModeCommand,
--	SecurityModeComplete,
--	SecurityModeReject,
--	DataVolumeReportRequest,
--	DataVolumeReport,
--	Reset,
--	ResetAcknowledge,
--	RAB-ReleaseRequest,
--	Iu-ReleaseRequest,
--	RelocationDetect,
--	RelocationComplete,
--	Paging,
--	CommonID,
--	CN-InvokeTrace,
--	CN-DeactivateTrace,
--	LocationReportingControl,
--	LocationReport,
--	InitialUE-Message,
--	DirectTransfer,
--	Overload,
--	ErrorIndication,
--	SRNS-DataForwardCommand,
--	ForwardSRNS-Context,
--	RAB-AssignmentRequest,
--	RAB-AssignmentResponse, 
--	RAB-ModifyRequest,
--	PrivateMessage,
--	ResetResource,
--	ResetResourceAcknowledge,
--	RANAP-RelocationInformation,
--	LocationRelatedDataRequest,
--	LocationRelatedDataResponse,
--	LocationRelatedDataFailure,
--	InformationTransferIndication,
--	InformationTransferConfirmation,
--	InformationTransferFailure,
--	UESpecificInformationIndication,
--	DirectInformationTransfer,
--	UplinkInformationExchangeRequest,
--	UplinkInformationExchangeResponse,
--	UplinkInformationExchangeFailure,
--	MBMSSessionStart,
--	MBMSSessionStartResponse,
--	MBMSSessionStartFailure,
--	MBMSSessionUpdate,
--	MBMSSessionUpdateResponse,
--	MBMSSessionUpdateFailure,
--	MBMSSessionStop,
--	MBMSSessionStopResponse,
--	MBMSUELinkingRequest,
--	MBMSUELinkingResponse,
--	MBMSRegistrationRequest,
--	MBMSRegistrationResponse,
--	MBMSRegistrationFailure,
--	MBMSCNDe-RegistrationRequest,
--	MBMSCNDe-RegistrationResponse,
--	MBMSRABEstablishmentIndication,
--	MBMSRABReleaseRequest,
--	MBMSRABRelease,
--	MBMSRABReleaseFailure
--FROM RANAP-PDU-Contents

--	id-LocationRelatedData,
--	id-CN-DeactivateTrace,
--	id-CN-InvokeTrace,
--	id-CommonID,
--	id-DataVolumeReport,
--	id-DirectTransfer,
--	id-ErrorIndication,
--	id-ForwardSRNS-Context,
--	id-InformationTransfer,
--	id-InitialUE-Message,
--	id-Iu-Release,
--	id-Iu-ReleaseRequest,
--	id-LocationReport,
--	id-LocationReportingControl,
--	id-OverloadControl,
--	id-Paging,
--	id-privateMessage,
--	id-RAB-Assignment,
--	id-RAB-ReleaseRequest, 
--	id-RAB-ModifyRequest,
--	id-RANAP-Relocation,
--	id-RelocationCancel,
--	id-RelocationComplete,
--	id-RelocationDetect,
--	id-RelocationPreparation,
--	id-RelocationResourceAllocation,
--	id-Reset,
--	id-SRNS-ContextTransfer,
--	id-SRNS-DataForward,
--	id-SecurityModeControl,
--	id-ResetResource,
--	id-UESpecificInformation,
--	id-DirectInformationTransfer,
--	id-UplinkInformationExchange,
--	id-MBMSSessionStart,
--	id-MBMSSessionUpdate,
--	id-MBMSSessionStop,
--	id-MBMSUELinking,
--	id-MBMSRegistration,
--	id-MBMSCNDe-Registration-Procedure,
--	id-MBMSRABEstablishmentIndication,
--	id-MBMSRABRelease

--FROM RANAP-Constants;

-- **************************************************************
--
-- Interface Elementary Procedure Class
--
-- **************************************************************

--RANAP-ELEMENTARY-PROCEDURE ::= CLASS {
--	&InitiatingMessage				,
--	&SuccessfulOutcome				OPTIONAL,
--	&UnsuccessfulOutcome				OPTIONAL,
--	&Outcome					OPTIONAL,
--	&procedureCode			ProcedureCode 	UNIQUE,
--	&criticality			Criticality 	DEFAULT ignore
--}
--WITH SYNTAX {
--	INITIATING MESSAGE		&InitiatingMessage
--	[SUCCESSFUL OUTCOME		&SuccessfulOutcome]
--	[UNSUCCESSFUL OUTCOME		&UnsuccessfulOutcome]
--	[OUTCOME			&Outcome]
--	PROCEDURE CODE				&procedureCode
--	[CRITICALITY			&criticality]
--}

-- **************************************************************
--
-- Interface PDU Definition
--
-- **************************************************************

RANAP-PDU ::= CHOICE {
	initiatingMessage	InitiatingMessage,
	successfulOutcome	SuccessfulOutcome,
	unsuccessfulOutcome	UnsuccessfulOutcome,
	outcome				Outcome,
	...
	}

--InitiatingMessage ::= SEQUENCE {
--	procedureCode	RANAP-ELEMENTARY-PROCEDURE.&procedureCode	({RANAP-ELEMENTARY-PROCEDURES}),
--	criticality	RANAP-ELEMENTARY-PROCEDURE.&criticality		({RANAP-ELEMENTARY-PROCEDURES}{@procedureCode}),
--	value		RANAP-ELEMENTARY-PROCEDURE.&InitiatingMessage	({RANAP-ELEMENTARY-PROCEDURES}{@procedureCode})
--}

InitiatingMessage ::= SEQUENCE {
	procedureCode	ProcedureCode,
	criticality		Criticality,
	value			Value		
	}

--SuccessfulOutcome ::= SEQUENCE {
--	procedureCode	RANAP-ELEMENTARY-PROCEDURE.&procedureCode	({RANAP-ELEMENTARY-PROCEDURES}),
--	criticality	RANAP-ELEMENTARY-PROCEDURE.&criticality		({RANAP-ELEMENTARY-PROCEDURES}{@procedureCode}),
--	value		RANAP-ELEMENTARY-PROCEDURE.&SuccessfulOutcome	({RANAP-ELEMENTARY-PROCEDURES}{@procedureCode})
--}
SuccessfulOutcome ::= SEQUENCE {
	procedureCode	ProcedureCode,
	criticality		Criticality,
	value			Value		
	}
--UnsuccessfulOutcome ::= SEQUENCE {
--	procedureCode	RANAP-ELEMENTARY-PROCEDURE.&procedureCode	({RANAP-ELEMENTARY-PROCEDURES}),
--	criticality	RANAP-ELEMENTARY-PROCEDURE.&criticality		({RANAP-ELEMENTARY-PROCEDURES}{@procedureCode}),
--	value		RANAP-ELEMENTARY-PROCEDURE.&UnsuccessfulOutcome	({RANAP-ELEMENTARY-PROCEDURES}{@procedureCode})
--}
UnsuccessfulOutcome ::= SEQUENCE {
	procedureCode	ProcedureCode,
	criticality		Criticality,
	value			Value		
	}
--Outcome ::= SEQUENCE {
--	procedureCode	RANAP-ELEMENTARY-PROCEDURE.&procedureCode	({RANAP-ELEMENTARY-PROCEDURES}),
--	criticality	RANAP-ELEMENTARY-PROCEDURE.&criticality		({RANAP-ELEMENTARY-PROCEDURES}{@procedureCode}),
--	value		RANAP-ELEMENTARY-PROCEDURE.&Outcome		({RANAP-ELEMENTARY-PROCEDURES}{@procedureCode})
--}
Outcome ::= SEQUENCE {
	procedureCode	ProcedureCode,
	criticality		Criticality,
	value			Value		
	}

Value ::= ANY

-- **************************************************************
--
-- Interface Elementary Procedure List
--
-- **************************************************************

--RANAP-ELEMENTARY-PROCEDURES RANAP-ELEMENTARY-PROCEDURE ::= {
--	RANAP-ELEMENTARY-PROCEDURES-CLASS-1	|
--	RANAP-ELEMENTARY-PROCEDURES-CLASS-2	|
--	RANAP-ELEMENTARY-PROCEDURES-CLASS-3	,
--	...
--}


--RANAP-ELEMENTARY-PROCEDURES-CLASS-1 RANAP-ELEMENTARY-PROCEDURE ::= {
--	iu-Release			|
--	relocationPreparation		|
--	relocationResourceAllocation	|
--	relocationCancel		|
--	sRNS-ContextTransfer		|
--	securityModeControl		|
--	dataVolumeReport		|
--	reset		|
--	resetResource				,
--	...,
--	locationRelatedData		|
--	informationTransfer		|
--	uplinkInformationExchange	|
--	mBMSSessionStart			|
--	mBMSSessionUpdate			|
--	mBMSSessionStop				|
--	mBMSUELinking				|
--	mBMSRegistration			|
--	mBMSCNDe-Registration		|
--	mBMSRABRelease
--}
--
--RANAP-ELEMENTARY-PROCEDURES-CLASS-2 RANAP-ELEMENTARY-PROCEDURE ::= {
--	rAB-ReleaseRequest		|
--	iu-ReleaseRequest		|
--	relocationDetect		|
--	relocationComplete		|
--	paging					|
--	commonID				|
--	cN-InvokeTrace			|
--	cN-DeactivateTrace		|
--	locationReportingControl	|
--	locationReport			|
--	initialUE-Message		|
--	directTransfer			|
--	overloadControl			|
--	errorIndication			|
--	sRNS-DataForward		|
--	forwardSRNS-Context		|
--	privateMessage			|
--	rANAP-Relocation		,
--	...,
--	rAB-ModifyRequest		|
--	uESpecificInformation	|
--	directInformationTransfer	|
--	mBMSRABEstablishmentIndication
--}

--RANAP-ELEMENTARY-PROCEDURES-CLASS-3 RANAP-ELEMENTARY-PROCEDURE ::= {
--	rAB-Assignment			,
--	...
--}

-- **************************************************************
--
-- Interface Elementary Procedures
--
-- **************************************************************

--iu-Release RANAP-ELEMENTARY-PROCEDURE ::= {
--	INITIATING MESSAGE	Iu-ReleaseCommand
--	SUCCESSFUL OUTCOME	Iu-ReleaseComplete
--	PROCEDURE CODE		id-Iu-Release
--	CRITICALITY		reject
--}

--relocationPreparation RANAP-ELEMENTARY-PROCEDURE ::= {
--	INITIATING MESSAGE	RelocationRequired
--	SUCCESSFUL OUTCOME	RelocationCommand
--	UNSUCCESSFUL OUTCOME	RelocationPreparationFailure
--	PROCEDURE CODE			id-RelocationPreparation
-- Value: 2
--	CRITICALITY		reject
--}

--relocationResourceAllocation RANAP-ELEMENTARY-PROCEDURE ::= {
--	INITIATING MESSAGE	RelocationRequest
--	SUCCESSFUL OUTCOME	RelocationRequestAcknowledge
--	UNSUCCESSFUL OUTCOME	RelocationFailure
--	PROCEDURE CODE			id-RelocationResourceAllocation
--	CRITICALITY		reject
-- value: 3
--}

--relocationCancel RANAP-ELEMENTARY-PROCEDURE ::= {
--	INITIATING MESSAGE	RelocationCancel
--	SUCCESSFUL OUTCOME	RelocationCancelAcknowledge
--	PROCEDURE CODE		id-RelocationCancel
--	CRITICALITY		reject
--}
--Value: 4

--sRNS-ContextTransfer RANAP-ELEMENTARY-PROCEDURE ::= {
--	INITIATING MESSAGE	SRNS-ContextRequest
--	SUCCESSFUL OUTCOME	SRNS-ContextResponse
--	PROCEDURE CODE		id-SRNS-ContextTransfer
--	CRITICALITY		reject
--}

--securityModeControl RANAP-ELEMENTARY-PROCEDURE ::= {
--	INITIATING MESSAGE	SecurityModeCommand
--	SUCCESSFUL OUTCOME	SecurityModeComplete
--	UNSUCCESSFUL OUTCOME	SecurityModeReject
--	PROCEDURE CODE		id-SecurityModeControl
--	CRITICALITY		reject
--}

--dataVolumeReport RANAP-ELEMENTARY-PROCEDURE ::= {
--	INITIATING MESSAGE	DataVolumeReportRequest
--	SUCCESSFUL OUTCOME	DataVolumeReport
--	PROCEDURE CODE		id-DataVolumeReport
--	CRITICALITY		reject
--}
	

--reset RANAP-ELEMENTARY-PROCEDURE ::= {
--	INITIATING MESSAGE	Reset
--	SUCCESSFUL OUTCOME	ResetAcknowledge
--	PROCEDURE CODE		id-Reset
--	CRITICALITY		reject
--}

--rAB-ReleaseRequest RANAP-ELEMENTARY-PROCEDURE ::= {
--	INITIATING MESSAGE	RAB-ReleaseRequest
--	PROCEDURE CODE		id-RAB-ReleaseRequest
--	CRITICALITY		ignore
--}

--iu-ReleaseRequest RANAP-ELEMENTARY-PROCEDURE ::= {
--	INITIATING MESSAGE	Iu-ReleaseRequest
--	PROCEDURE CODE		id-Iu-ReleaseRequest
--	CRITICALITY		ignore
--}

--relocationDetect RANAP-ELEMENTARY-PROCEDURE ::= {
--	INITIATING MESSAGE	RelocationDetect
--	PROCEDURE CODE		id-RelocationDetect
--	CRITICALITY		ignore
--}

--relocationComplete RANAP-ELEMENTARY-PROCEDURE ::= {
--	INITIATING MESSAGE	RelocationComplete
--	PROCEDURE CODE		id-RelocationComplete
--	CRITICALITY		ignore
--}

--paging RANAP-ELEMENTARY-PROCEDURE ::= {
--	INITIATING MESSAGE	Paging
--	PROCEDURE CODE		id-Paging
--	CRITICALITY		ignore
--}

--commonID RANAP-ELEMENTARY-PROCEDURE ::= {
--	INITIATING MESSAGE	CommonID
--	PROCEDURE CODE		id-CommonID
--	CRITICALITY		ignore
--}

--cN-InvokeTrace RANAP-ELEMENTARY-PROCEDURE ::= {
--	INITIATING MESSAGE	CN-InvokeTrace
--	PROCEDURE CODE		id-CN-InvokeTrace
--	CRITICALITY		ignore
--}

--cN-DeactivateTrace RANAP-ELEMENTARY-PROCEDURE ::= {
--	INITIATING MESSAGE	CN-DeactivateTrace
--	PROCEDURE CODE			id-CN-DeactivateTrace
--	CRITICALITY		ignore
--}

--locationReportingControl RANAP-ELEMENTARY-PROCEDURE ::= {
--	INITIATING MESSAGE	LocationReportingControl
--	PROCEDURE CODE		id-LocationReportingControl
--	CRITICALITY		ignore
--}
--locationReport RANAP-ELEMENTARY-PROCEDURE ::= {
--	INITIATING MESSAGE	LocationReport
--	PROCEDURE CODE		id-LocationReport
--	CRITICALITY		ignore
--}

--initialUE-Message RANAP-ELEMENTARY-PROCEDURE ::= {
--	INITIATING MESSAGE	InitialUE-Message
--	PROCEDURE CODE		id-InitialUE-Message
--	CRITICALITY		ignore
--}

--directTransfer RANAP-ELEMENTARY-PROCEDURE ::= {
--	INITIATING MESSAGE	DirectTransfer
--	PROCEDURE CODE		id-DirectTransfer
--	CRITICALITY		ignore
--}
--overloadControl RANAP-ELEMENTARY-PROCEDURE ::= {
--	INITIATING MESSAGE	Overload
--	PROCEDURE CODE		id-OverloadControl
--	CRITICALITY		ignore
--}

--errorIndication RANAP-ELEMENTARY-PROCEDURE ::= {
--	INITIATING MESSAGE	ErrorIndication
--	PROCEDURE CODE		id-ErrorIndication
--	CRITICALITY		ignore
--}

--sRNS-DataForward RANAP-ELEMENTARY-PROCEDURE ::= {
--	INITIATING MESSAGE	SRNS-DataForwardCommand
--	PROCEDURE CODE		id-SRNS-DataForward
--	CRITICALITY		ignore
--}

--forwardSRNS-Context RANAP-ELEMENTARY-PROCEDURE ::= {
--	INITIATING MESSAGE	ForwardSRNS-Context
--	PROCEDURE CODE		id-ForwardSRNS-Context
--	CRITICALITY		ignore
--}

--rAB-Assignment RANAP-ELEMENTARY-PROCEDURE ::= {
--	INITIATING MESSAGE	RAB-AssignmentRequest
--	OUTCOME			RAB-AssignmentResponse
--	PROCEDURE CODE		id-RAB-Assignment
--	CRITICALITY		reject
--}

--privateMessage RANAP-ELEMENTARY-PROCEDURE ::= {
--	INITIATING MESSAGE	PrivateMessage
--
--	PROCEDURE CODE	id-privateMessage
--	CRITICALITY		ignore
--}

--resetResource RANAP-ELEMENTARY-PROCEDURE ::= {
--	INITIATING MESSAGE	ResetResource
--	SUCCESSFUL OUTCOME	ResetResourceAcknowledge
--	PROCEDURE CODE			id-ResetResource
--	CRITICALITY		reject
--}

--rANAP-Relocation RANAP-ELEMENTARY-PROCEDURE ::= {
--	INITIATING MESSAGE	RANAP-RelocationInformation
--	PROCEDURE CODE			id-RANAP-Relocation
--	CRITICALITY		ignore
--}

--rAB-ModifyRequest RANAP-ELEMENTARY-PROCEDURE ::= {
--	INITIATING MESSAGE	RAB-ModifyRequest
--	PROCEDURE CODE		id-RAB-ModifyRequest
--	CRITICALITY		ignore
--}
--locationRelatedData RANAP-ELEMENTARY-PROCEDURE ::= {
--	INITIATING MESSAGE		LocationRelatedDataRequest
--	SUCCESSFUL OUTCOME		LocationRelatedDataResponse
--	UNSUCCESSFUL OUTCOME	LocationRelatedDataFailure
--	PROCEDURE CODE			id-LocationRelatedData
--	CRITICALITY				reject
--}

--informationTransfer RANAP-ELEMENTARY-PROCEDURE ::= {
--	INITIATING MESSAGE		InformationTransferIndication
--	SUCCESSFUL OUTCOME		InformationTransferConfirmation
--	UNSUCCESSFUL OUTCOME	InformationTransferFailure
--	PROCEDURE CODE			id-InformationTransfer
--	CRITICALITY				reject
--}

--uESpecificInformation RANAP-ELEMENTARY-PROCEDURE ::= {
--	INITIATING MESSAGE	UESpecificInformationIndication
--	PROCEDURE CODE		id-UESpecificInformation
--	CRITICALITY		ignore
--}

--directInformationTransfer RANAP-ELEMENTARY-PROCEDURE ::= {
--	INITIATING MESSAGE		DirectInformationTransfer
--	PROCEDURE CODE			id-DirectInformationTransfer
--	CRITICALITY				ignore
--}

--uplinkInformationExchange RANAP-ELEMENTARY-PROCEDURE ::= {
--	INITIATING MESSAGE		UplinkInformationExchangeRequest
--	SUCCESSFUL OUTCOME		UplinkInformationExchangeResponse
--	UNSUCCESSFUL OUTCOME	UplinkInformationExchangeFailure
--	PROCEDURE CODE			id-UplinkInformationExchange
--	CRITICALITY				reject
--}

--mBMSSessionStart RANAP-ELEMENTARY-PROCEDURE ::= {
--	INITIATING MESSAGE		MBMSSessionStart
--	SUCCESSFUL OUTCOME		MBMSSessionStartResponse
--	UNSUCCESSFUL OUTCOME	MBMSSessionStartFailure
--	PROCEDURE CODE			id-MBMSSessionStart
--	CRITICALITY				reject
--}

--mBMSSessionUpdate RANAP-ELEMENTARY-PROCEDURE ::= {
--	INITIATING MESSAGE		MBMSSessionUpdate
--	SUCCESSFUL OUTCOME		MBMSSessionUpdateResponse
--	UNSUCCESSFUL OUTCOME	MBMSSessionUpdateFailure
--	PROCEDURE CODE			id-MBMSSessionUpdate
--	CRITICALITY				reject
--}

--mBMSSessionStop RANAP-ELEMENTARY-PROCEDURE ::= {
--	INITIATING MESSAGE		MBMSSessionStop
--	SUCCESSFUL OUTCOME		MBMSSessionStopResponse
--	PROCEDURE CODE			id-MBMSSessionStop
--	CRITICALITY				reject
--}

--mBMSUELinking RANAP-ELEMENTARY-PROCEDURE ::= {
--	INITIATING MESSAGE		MBMSUELinkingRequest
--	OUTCOME					MBMSUELinkingResponse
--	PROCEDURE CODE			id-MBMSUELinking
--	CRITICALITY				reject
--}

--mBMSRegistration RANAP-ELEMENTARY-PROCEDURE ::= {
--	INITIATING MESSAGE		MBMSRegistrationRequest
--	SUCCESSFUL OUTCOME		MBMSRegistrationResponse
--	UNSUCCESSFUL OUTCOME	MBMSRegistrationFailure
--	PROCEDURE CODE			id-MBMSRegistration
--	CRITICALITY				reject
--}

--mBMSCNDe-Registration RANAP-ELEMENTARY-PROCEDURE ::= {
--	INITIATING MESSAGE		MBMSCNDe-RegistrationRequest
--	SUCCESSFUL OUTCOME		MBMSCNDe-RegistrationResponse
--	PROCEDURE CODE			id-MBMSCNDe-Registration-Procedure
--	CRITICALITY				reject
--}

--mBMSRABEstablishmentIndication RANAP-ELEMENTARY-PROCEDURE ::= {
--	INITIATING MESSAGE	MBMSRABEstablishmentIndication
--	PROCEDURE CODE		id-MBMSRABEstablishmentIndication
--	CRITICALITY		ignore
--}

--mBMSRABRelease RANAP-ELEMENTARY-PROCEDURE ::= {
--	INITIATING MESSAGE	MBMSRABReleaseRequest
--	SUCCESSFUL OUTCOME		MBMSRABRelease
--	UNSUCCESSFUL OUTCOME	MBMSRABReleaseFailure
--	PROCEDURE CODE		id-MBMSRABRelease
--	CRITICALITY		reject
--}



Dummy-initiating-messages::= CHOICE {
iu-ReleaseCommand					Iu-ReleaseCommand,
relocationRequired					RelocationRequired,
relocationRequest					RelocationRequest,
relocationCancel					RelocationCancel,
sRNS-ContextRequest					SRNS-ContextRequest,
securityModeCommand					SecurityModeCommand,
dataVolumeReportRequest				DataVolumeReportRequest,
reset								Reset,
rAB-ReleaseRequest					RAB-ReleaseRequest,
iu-ReleaseRequest					Iu-ReleaseRequest,
relocationDetect					RelocationDetect,
relocationComplete					RelocationComplete,
paging								Paging,
commonID							CommonID,
cN-InvokeTrace						CN-InvokeTrace,
cN-DeactivateTrace					CN-DeactivateTrace,
locationReportingControl			LocationReportingControl,
locationReport						LocationReport,
initialUE-Message					InitialUE-Message,
directTransfer						DirectTransfer,
overload							Overload,
errorIndication						ErrorIndication,
sRNS-DataForwardCommand				SRNS-DataForwardCommand,
forwardSRNS-Context					ForwardSRNS-Context,
rAB-AssignmentRequest				RAB-AssignmentRequest,
privateMessage						PrivateMessage,
resetResource						ResetResource,
rANAP-RelocationInformation			RANAP-RelocationInformation,
rAB-ModifyRequest					RAB-ModifyRequest,
locationRelatedDataRequest			LocationRelatedDataRequest,
informationTransferIndication		InformationTransferIndication,
uESpecificInformationIndication		UESpecificInformationIndication,
directInformationTransfer			DirectInformationTransfer,
uplinkInformationExchangeRequest	UplinkInformationExchangeRequest,
mBMSSessionStart					MBMSSessionStart,
mBMSSessionUpdate					MBMSSessionUpdate,
mMBMSSessionStop					MBMSSessionStop,
mBMSUELinkingRequest				MBMSUELinkingRequest,
mBMSRegistrationRequest				MBMSRegistrationRequest,
mBMSCNDe-RegistrationRequest		MBMSCNDe-RegistrationRequest,
mBMSRABEstablishmentIndication		MBMSRABEstablishmentIndication,
mBMSRABReleaseRequest				MBMSRABReleaseRequest,
...
}

Dummy-SuccessfulOutcome-messages::= CHOICE {
iu-ReleaseComplete					Iu-ReleaseComplete,
relocationCommand					RelocationCommand,
relocationRequestAcknowledge		RelocationRequestAcknowledge,
relocationCancelAcknowledge			RelocationCancelAcknowledge,
sRNS-ContextResponse				SRNS-ContextResponse,
securityModeComplete				SecurityModeComplete,
dataVolumeReport					DataVolumeReport,
resetAcknowledge					ResetAcknowledge,
resetResourceAcknowledge			ResetResourceAcknowledge,
locationRelatedDataResponse			LocationRelatedDataResponse,
informationTransferConfirmation		InformationTransferConfirmation,
uplinkInformationExchangeResponse	UplinkInformationExchangeResponse,
mBMSSessionStartResponse			MBMSSessionStartResponse,
mBMSSessionUpdateResponse			MBMSSessionUpdateResponse,
mBMSSessionStopResponse				MBMSSessionStopResponse,
mBMSRegistrationResponse			MBMSRegistrationResponse,
mBMSCNDeRegistrationResponse		MBMSCNDe-RegistrationResponse,
mBMSRABRelease						MBMSRABRelease,
...
}

Dummy-UnsuccessfulOutcome-messages::= CHOICE {
relocationPreparationFailure		RelocationPreparationFailure,
relocationFailure					RelocationFailure,
securityModeReject					SecurityModeReject,
locationRelatedDataFailure			LocationRelatedDataFailure,
informationTransferFailure			InformationTransferFailure,
uplinkInformationExchangeFailure	UplinkInformationExchangeFailure,
mBMSSessionStartFailure				MBMSSessionStartFailure,
mBMSSessionUpdateFailure			MBMSSessionUpdateFailure,
mBMSRegistrationFailure				MBMSRegistrationFailure,
mBMSRABReleaseFailure				MBMSRABReleaseFailure,
...
}

Dummy-Outcome-messages::= CHOICE {
iu-ReleaseCommand				Iu-ReleaseCommand,
rAB-AssignmentResponse			RAB-AssignmentResponse,
mBMSUELinkingResponse			MBMSUELinkingResponse,
...
}
--9.3.3	PDU Definitions
-- **************************************************************
--
-- PDU definitions for RANAP.
--
-- **************************************************************

--RANAP-PDU-Contents { 
--itu-t (0) identified-organization (4) etsi (0) mobileDomain (0) 
--umts-Access (20) modules (3) ranap (0) version1 (1) ranap-PDU-Contents (1) }

--DEFINITIONS AUTOMATIC TAGS ::= 

--BEGIN

-- **************************************************************
--
-- IE parameter types from other modules.
--
-- **************************************************************
--
--IMPORTS
--	AccuracyFulfilmentIndicator,
--	APN,
--	BroadcastAssistanceDataDecipheringKeys,
--	LocationRelatedDataRequestType,
--	LocationRelatedDataRequestTypeSpecificToGERANIuMode,
--	DataVolumeReference,
--	CellLoadInformation,
--	AreaIdentity,
--	CN-DomainIndicator,
--	Cause,
--	ClientType,
--	CriticalityDiagnostics,
--	ChosenEncryptionAlgorithm,
--	ChosenIntegrityProtectionAlgorithm,
--	ClassmarkInformation2,
--	ClassmarkInformation3,
--	DL-GTP-PDU-SequenceNumber,
--	DL-N-PDU-SequenceNumber,
--	DataVolumeReportingIndication,
--	DeltaRAListofIdleModeUEs,
--	DRX-CycleLengthCoefficient,
--	EncryptionInformation,
--	FrequenceLayerConvergenceFlag,
--	GERAN-BSC-Container,
--	GERAN-Classmark,
--	GlobalCN-ID,
--	GlobalRNC-ID,
--	InformationExchangeID,
--	InformationExchangeType,
--	InformationRequested,
--	InformationRequestType,
--	InformationTransferID,
--	InformationTransferType,
--	InterSystemInformationTransferType,
--	IntegrityProtectionInformation,
--	InterSystemInformation-TransparentContainer,
--	IPMulticastAddress,
--	IuSignallingConnectionIdentifier,
--	IuTransportAssociation,
--	KeyStatus,
--	L3-Information,
--	LAI,
--	LastKnownServiceArea,
--	MBMS-PTP-RAB-ID,
--	MBMSBearerServiceType,
--	MBMSCNDe-Registration,
--	MBMSRegistrationRequestType,
--	MBMSServiceArea,
--	MBMSSessionDuration,
--	MBMSSessionIdentity,
--	MBMSSessionRepetitionNumber,
--	NAS-PDU,
--	NAS-SequenceNumber,
--	NAS-SynchronisationIndicator,
--	NewBSS-To-OldBSS-Information,
--	NonSearchingIndication,
--	NumberOfSteps,
--	OMC-ID,
--	OldBSS-ToNewBSS-Information,
--	PagingAreaID,
--	PagingCause,
--	PDP-TypeInformation,
--	PermanentNAS-UE-ID,
--	PLMNidentity,
--	PositionData,
--	PositionDataSpecificToGERANIuMode,
--	PositioningPriority,
--	ProvidedData,
--	RAB-ID,
--	RAB-Parameters,
--	RAC,
--	RAListofIdleModeUEs,
--	RedirectionCompleted,
--	RejectCauseValue,
--	RelocationType,
--	RequestType, 
--	Requested-RAB-Parameter-Values,
--	ResponseTime,
--	RRC-Container,
--	SAI,
--	SAPI,
--	Service-Handover,
--	SessionUpdateID,
--	SNA-Access-Information,
--	SourceID,
--	SourceRNC-ToTargetRNC-TransparentContainer,
--	TargetID,
--	TargetRNC-ToSourceRNC-TransparentContainer,
--	TemporaryUE-ID,
--	TMGI,
--	TracePropagationParameters,
--	TraceReference,
--	TraceType,
--	UnsuccessfullyTransmittedDataVolume,
--	TransportLayerAddress,
--	TriggerID,
--	UE-ID,
--	UESBI-Iu,
--	UL-GTP-PDU-SequenceNumber,
--	UL-N-PDU-SequenceNumber,
--	UP-ModeVersions,
--	UserPlaneMode,
--	VerticalAccuracyCode,
--	Alt-RAB-Parameters,
--	Ass-RAB-Parameters
--FROM RANAP-IEs


--	PrivateIE-Container{},
--	ProtocolExtensionContainer{},
--	ProtocolIE-ContainerList{},
--	ProtocolIE-ContainerPair{},
--	ProtocolIE-ContainerPairList{},
--	ProtocolIE-Container{},
--	RANAP-PRIVATE-IES,
--	RANAP-PROTOCOL-EXTENSION,
--	RANAP-PROTOCOL-IES,
--	RANAP-PROTOCOL-IES-PAIR
-- FROM RANAP-Containers

--	maxNrOfDTs,
--	maxNrOfErrors,
--	maxNrOfIuSigConIds,
--	maxNrOfRABs,
--	maxNrOfVol,
--	maxnoofMulticastServicesPerUE,
--
--	id-AccuracyFulfilmentIndicator,
--	id-APN,
--	id-AreaIdentity, 
--	id-Alt-RAB-Parameters,
--	id-Ass-RAB-Parameters,
--	id-BroadcastAssistanceDataDecipheringKeys,
--	id-LocationRelatedDataRequestType,
--	id-CN-DomainIndicator,
--	id-Cause,
--	id-ChosenEncryptionAlgorithm,
--	id-ChosenIntegrityProtectionAlgorithm,
--	id-ClassmarkInformation2,
--	id-ClassmarkInformation3,
--	id-ClientType,
--	id-CNMBMSLinkingInformation,
--	id-CriticalityDiagnostics,
--	id-DeltaRAListofIdleModeUEs,
--	id-DRX-CycleLengthCoefficient,
--	id-DirectTransferInformationItem-RANAP-RelocInf,
--	id-DirectTransferInformationList-RANAP-RelocInf,
--	id-DL-GTP-PDU-SequenceNumber,
--	id-EncryptionInformation,
--	id-FrequenceLayerConvergenceFlag,
--	id-GERAN-BSC-Container,
--	id-GERAN-Classmark,
--	id-GERAN-Iumode-RAB-Failed-RABAssgntResponse-Item,
--	id-GERAN-Iumode-RAB-FailedList-RABAssgntResponse,
--	id-GlobalCN-ID,
--	id-GlobalRNC-ID,
--	id-InformationExchangeID,
--	id-InformationExchangeType,
--	id-InformationRequested,
--	id-InformationRequestType,
--	id-InformationTransferID,
--	id-InformationTransferType,
--	id-IntegrityProtectionInformation,
--	id-InterSystemInformationTransferType,
--	id-InterSystemInformation-TransparentContainer,
--	id-IPMulticastAddress,
--	id-IuSigConId,
--	id-IuSigConIdItem,
--	id-IuSigConIdList,
--	id-IuTransportAssociation,
--	id-JoinedMBMSBearerServicesList,
--	id-KeyStatus,
--	id-L3-Information,
--	id-LAI,
--	id-LastKnownServiceArea,
--	id-LeftMBMSBearerServicesList,
--	id-LocationRelatedDataRequestTypeSpecificToGERANIuMode,
--	id-MBMSBearerServiceType,
--	id-MBMSCNDe-Registration,
--	id-MBMSRegistrationRequestType,
--	id-MBMSServiceArea,
--	id-MBMSSessionDuration,
--	id-MBMSSessionIdentity,
--	id-MBMSSessionRepetitionNumber,
--	id-NAS-PDU,
--	id-NAS-SequenceNumber,
--	id-NewBSS-To-OldBSS-Information,
--	id-NonSearchingIndication,
--	id-NumberOfSteps,
--	id-OMC-ID,
--	id-OldBSS-ToNewBSS-Information,
--	id-PagingAreaID,
--	id-PagingCause, 
--	id-PDP-TypeInformation,
--	id-PermanentNAS-UE-ID,
--	id-PositionData,
--	id-PositionDataSpecificToGERANIuMode,
--	id-PositioningPriority,
--	id-ProvidedData,
--	id-RAB-ContextItem,
--	id-RAB-ContextList,
--	id-RAB-ContextFailedtoTransferItem,
--	id-RAB-ContextFailedtoTransferList,
--	id-RAB-ContextItem-RANAP-RelocInf,
--	id-RAB-ContextList-RANAP-RelocInf,
--	id-RAB-DataForwardingItem,
--	id-RAB-DataForwardingItem-SRNS-CtxReq,
--	id-RAB-DataForwardingList,
--	id-RAB-DataForwardingList-SRNS-CtxReq,
--	id-RAB-DataVolumeReportItem,
--	id-RAB-DataVolumeReportList,
--	id-RAB-DataVolumeReportRequestItem,
--	id-RAB-DataVolumeReportRequestList,
--	id-RAB-FailedItem,
--	id-RAB-FailedList,
--	id-RAB-FailedtoReportItem,
--	id-RAB-FailedtoReportList,
--	id-RAB-ID, 
--	id-RAB-ModifyList,
--	id-RAB-ModifyItem,
--	id-RAB-Parameters,
--	id-RAB-QueuedItem,
--	id-RAB-QueuedList,
--	id-RAB-ReleaseFailedList,
--	id-RAB-ReleaseItem,
--	id-RAB-ReleasedItem-IuRelComp,
--	id-RAB-ReleaseList,
--	id-RAB-ReleasedItem,
--	id-RAB-ReleasedList,
--	id-RAB-ReleasedList-IuRelComp,
--	id-RAB-RelocationReleaseItem,
--	id-RAB-RelocationReleaseList,
--	id-RAB-SetupItem-RelocReq,
--	id-RAB-SetupItem-RelocReqAck,
--	id-RAB-SetupList-RelocReq,
--	id-RAB-SetupList-RelocReqAck,
--	id-RAB-SetupOrModifiedItem,
--	id-RAB-SetupOrModifiedList,
--	id-RAB-SetupOrModifyItem,
--	id-RAB-SetupOrModifyList,
--	id-RAC,
--	id-RAListofIdleModeUEs,
--	id-RedirectionCompleted,
--	id-RedirectionIndication,
--	id-RejectCauseValue,
--	id-RelocationType,
--	id-RequestType,
--	id-ResponseTime,
--	id-SAI,
--	id-SAPI,
--	id-SelectedPLMN-ID,
--	id-SessionUpdateID,
--	id-SNA-Access-Information,
--	id-SourceID,
--	id-SourceRNC-ToTargetRNC-TransparentContainer,
--	id-SourceRNC-PDCP-context-info,
--	id-TargetID,
--	id-TargetRNC-ToSourceRNC-TransparentContainer,
--	id-TemporaryUE-ID,
--	id-TMGI,
--	id-TracePropagationParameters,
--	id-TraceReference,
--	id-TraceType,
--	id-TransportLayerAddress,
--	id-TransportLayerInformation,
--	id-TriggerID,
--	id-UE-ID,
--	id-UESBI-Iu,
--	id-UL-GTP-PDU-SequenceNumber,
--	id-UnsuccessfulLinkingList,
--	id-VerticalAccuracyCode
--FROM RANAP-Constants;
-- Dummy define to get hf def_s

Dymmy-ie-ids::= CHOICE {
	id-AccuracyFulfilmentIndicator						AccuracyFulfilmentIndicator,
	id-APN												APN,
	id-AreaIdentity										AreaIdentity, 
	id-Alt-RAB-Parameters								Alt-RAB-Parameters,
	id-Ass-RAB-Parameters								Ass-RAB-Parameters,
	id-BroadcastAssistanceDataDecipheringKeys			BroadcastAssistanceDataDecipheringKeys,
	id-LocationRelatedDataRequestType					LocationRelatedDataRequestType,
	id-CN-DomainIndicator								CN-DomainIndicator,
	id-Cause											Cause,
	id-ChosenEncryptionAlgorithm						ChosenEncryptionAlgorithm,
	id-ChosenIntegrityProtectionAlgorithm				ChosenIntegrityProtectionAlgorithm,
	id-ClassmarkInformation2							ClassmarkInformation2,
	id-ClassmarkInformation3							ClassmarkInformation3,
	id-ClientType										ClientType,
	id-CNMBMSLinkingInformation							CNMBMSLinkingInformation,
	id-CriticalityDiagnostics							CriticalityDiagnostics,
	id-DeltaRAListofIdleModeUEs							DeltaRAListofIdleModeUEs,
	id-DRX-CycleLengthCoefficient						DRX-CycleLengthCoefficient,
	id-DirectTransferInformationItem-RANAP-RelocInf		DirectTransferInformationItem-RANAP-RelocInf,
	id-DirectTransferInformationList-RANAP-RelocInf		DirectTransferInformationList-RANAP-RelocInf,
	id-DL-GTP-PDU-SequenceNumber						DL-GTP-PDU-SequenceNumber,
	id-EncryptionInformation							EncryptionInformation,
	id-FrequenceLayerConvergenceFlag					FrequenceLayerConvergenceFlag,
	id-GERAN-BSC-Container								GERAN-BSC-Container,
	id-GERAN-Classmark									GERAN-Classmark,
	id-GERAN-Iumode-RAB-Failed-RABAssgntResponse-Item	GERAN-Iumode-RAB-Failed-RABAssgntResponse-Item,
	id-GERAN-Iumode-RAB-FailedList-RABAssgntResponse	GERAN-Iumode-RAB-FailedList-RABAssgntResponse,
	id-GlobalCN-ID										GlobalCN-ID,
	id-GlobalRNC-ID										GlobalRNC-ID,
	id-InformationExchangeID							InformationExchangeID,
	id-InformationExchangeType							InformationExchangeType,
	id-InformationRequested								InformationRequested,
	id-InformationRequestType							InformationRequestType,
	id-InformationTransferID							InformationTransferID,
	id-InformationTransferType							InformationTransferType,
	id-TraceRecordingSessionInformation					TraceRecordingSessionInformation,
	id-IntegrityProtectionInformation					IntegrityProtectionInformation,
	id-InterSystemInformationTransferType				InterSystemInformationTransferType,
	id-InterSystemInformation-TransparentContainer		InterSystemInformation-TransparentContainer,
	id-IPMulticastAddress								IPMulticastAddress,
	id-IuSigConId										IuSignallingConnectionIdentifier,
	id-IuSigConIdItem									ResetResourceAckItem,
	id-IuSigConIdList									ResetResourceAckList,
	id-IuTransportAssociation							IuTransportAssociation,
	id-JoinedMBMSBearerServicesList						JoinedMBMSBearerService-IEs,
	id-KeyStatus										KeyStatus,
	id-L3-Information									L3-Information,
	id-LAI												LAI,
	id-LastKnownServiceArea								LastKnownServiceArea,
	id-SRB-TrCH-Mapping									SRB-TrCH-Mapping,
	id-LeftMBMSBearerServicesList						LeftMBMSBearerService-IEs,
	id-LocationRelatedDataRequestTypeSpecificToGERANIuMode	LocationRelatedDataRequestTypeSpecificToGERANIuMode,
	id-SignallingIndication								SignallingIndication,
	id-hS-DSCH-MAC-d-Flow-ID							HS-DSCH-MAC-d-Flow-ID,
	id-CellLoadInformationGroup							CellLoadInformationGroup,
	id-MBMSBearerServiceType							MBMSBearerServiceType,
	id-MBMSCNDe-Registration							MBMSCNDe-Registration,
	id-MBMSRegistrationRequestType						MBMSRegistrationRequestType,
	id-MBMSServiceArea									MBMSServiceArea,
	id-MBMSSessionDuration								MBMSSessionDuration,
	id-MBMSSessionIdentity								MBMSSessionIdentity,
	id-MBMSSessionRepetitionNumber						MBMSSessionRepetitionNumber,
	id-NAS-PDU											NAS-PDU,
	id-NAS-SequenceNumber								NAS-SequenceNumber,
	id-NewBSS-To-OldBSS-Information						NewBSS-To-OldBSS-Information,
	id-NonSearchingIndication							NonSearchingIndication,
	id-NumberOfSteps									NumberOfSteps,
	id-OMC-ID											OMC-ID,
	id-OldBSS-ToNewBSS-Information						OldBSS-ToNewBSS-Information,
	id-PagingAreaID										PagingAreaID,
	id-PagingCause										PagingCause, 
	id-PDP-TypeInformation								PDP-TypeInformation,
	id-PermanentNAS-UE-ID								PermanentNAS-UE-ID,
	id-PositionData										PositionData,
	id-PositionDataSpecificToGERANIuMode				PositionDataSpecificToGERANIuMode,
	id-PositioningPriority								PositioningPriority,
	id-ProvidedData										ProvidedData,
	id-RAB-ContextItem									RAB-ContextItem,
	id-RAB-ContextList									RAB-ContextList,
	id-RAB-ContextFailedtoTransferItem					RABs-ContextFailedtoTransferItem,
	id-RAB-ContextFailedtoTransferList					RAB-ContextFailedtoTransferList,
	id-RAB-ContextItem-RANAP-RelocInf					RAB-ContextItem-RANAP-RelocInf,
	id-RAB-ContextList-RANAP-RelocInf					RAB-ContextList-RANAP-RelocInf,
	id-RAB-DataForwardingItem							RAB-DataForwardingItem,
	id-RAB-DataForwardingItem-SRNS-CtxReq				RAB-DataForwardingItem-SRNS-CtxReq,
	id-RAB-DataForwardingList							RAB-DataForwardingList,
	id-RAB-DataForwardingList-SRNS-CtxReq				RAB-DataForwardingList-SRNS-CtxReq,
	id-RAB-DataVolumeReportItem							RAB-DataVolumeReportItem,
	id-RAB-DataVolumeReportList							RAB-DataVolumeReportList,
	id-RAB-DataVolumeReportRequestItem					RAB-DataVolumeReportRequestItem,
	id-RAB-DataVolumeReportRequestList					RAB-DataVolumeReportRequestList,
	id-RAB-FailedItem									RAB-FailedItem,
	id-RAB-FailedList									RAB-FailedList,
	id-RAB-FailedtoReportItem							RABs-failed-to-reportItem,
	id-RAB-FailedtoReportList							RAB-FailedtoReportList,
	id-RAB-ID											RAB-ID, 
	id-RAB-ModifyList									RAB-ModifyList,
	id-RAB-ModifyItem									RAB-ModifyItem,
	id-TypeOfError										TypeOfError,
	id-RAB-Parameters									RAB-Parameters,
	id-RAB-QueuedItem									RAB-QueuedItem,
	id-RAB-QueuedList									RAB-QueuedList,
	id-RAB-ReleaseFailedList							RAB-ReleaseFailedList,
	id-RAB-ReleaseItem									RAB-ReleaseItem,
	id-RAB-ReleasedItem-IuRelComp						RAB-ReleasedItem-IuRelComp,
	id-MessageStructure									MessageStructure,
	id-RAB-ReleaseList									RAB-ReleaseList,
	id-RAB-ReleasedItem									RAB-ReleasedItem,
	id-RAB-ReleasedList									RAB-ReleasedList,
	id-RAB-ReleasedList-IuRelComp						RAB-ReleasedList-IuRelComp,
	id-RAB-RelocationReleaseItem						RAB-RelocationReleaseItem,
	id-RAB-RelocationReleaseList						RAB-RelocationReleaseList,
	id-RAB-SetupItem-RelocReq							RAB-SetupItem-RelocReq,
	id-RAB-SetupItem-RelocReqAck						RAB-SetupItem-RelocReqAck,
	id-RAB-SetupList-RelocReq							RAB-SetupList-RelocReq,
	id-RAB-SetupList-RelocReqAck						RAB-SetupList-RelocReqAck,
	id-RAB-SetupOrModifiedItem							RAB-SetupOrModifiedItem,
	id-RAB-SetupOrModifiedList							RAB-SetupOrModifiedList,
--	id-RAB-SetupOrModifyItem							RAB-SetupOrModifyItem,
	id-RAB-SetupOrModifyList							RAB-SetupOrModifyList,
	id-RAC												RAC,
	id-RAListofIdleModeUEs								RAListofIdleModeUEs,
	id-RedirectionCompleted								RedirectionCompleted,
	id-RedirectionIndication							RedirectionIndication,
	id-RejectCauseValue									RejectCauseValue,
	id-RelocationType									RelocationType,
	id-RequestType										RequestType,
	id-ResponseTime										ResponseTime,
	id-SAI												SAI,
	id-SAPI												SAPI,
	id-SelectedPLMN-ID									PLMNidentity,
	id-SessionUpdateID									SessionUpdateID,
	id-SNA-Access-Information							SNA-Access-Information,
	id-SourceID											SourceID,
	id-SourceRNC-ToTargetRNC-TransparentContainer		SourceRNC-ToTargetRNC-TransparentContainer,
	id-SourceRNC-PDCP-context-info						RRC-Container,
	id-TargetID											TargetID,
	id-TargetRNC-ToSourceRNC-TransparentContainer		TargetRNC-ToSourceRNC-TransparentContainer,
	id-TemporaryUE-ID									TemporaryUE-ID,
	id-TMGI												TMGI,
	id-TracePropagationParameters						TracePropagationParameters,
	id-TraceReference									TraceReference,
	id-TraceType										TraceType,
	id-TransportLayerAddress							TransportLayerAddress,
	id-TransportLayerInformation						TransportLayerInformation,
	id-TriggerID										TriggerID,
	id-UE-ID											UE-ID,
	id-UESBI-Iu											UESBI-Iu,
	id-UL-GTP-PDU-SequenceNumber						UL-GTP-PDU-SequenceNumber,
	id-UnsuccessfulLinkingList							UnsuccessfulLinking-IEs,
	id-VerticalAccuracyCode								VerticalAccuracyCode,
	id-MBMSLinkingInformation							MBMSLinkingInformation,
	id-AlternativeRABConfiguration						RAB-Parameters,
	id-AlternativeRABConfigurationRequest				AlternativeRABConfigurationRequest,
	id-E-DCH-MAC-d-Flow-ID								E-DCH-MAC-d-Flow-ID
	}

Dymmy-firstvalue-ie-ids::= CHOICE {
	id-RAB-SetupOrModifyItem1						RAB-SetupOrModifyItemFirst,
	...
	}
	
Dymmy-secondvalue-ie-ids::= CHOICE {
	id-RAB-SetupOrModifyItem2						RAB-SetupOrModifyItemSecond,
	...
	}		
-- **************************************************************
--
-- Common Container Lists
--
-- **************************************************************

-- RAB-IE-ContainerList                  { RANAP-PROTOCOL-IES      : IEsSetParam }	::= ProtocolIE-ContainerList     { 1, maxNrOfRABs,   {IEsSetParam} }

RAB-IE-ContainerList ::= ProtocolIE-ContainerList256 

-- RAB-IE-ContainerPairList              { RANAP-PROTOCOL-IES-PAIR : IEsSetParam }	::= ProtocolIE-ContainerPairList { 1, maxNrOfRABs,   {IEsSetParam} }

RAB-IE-ContainerPairList ::= ProtocolIE-ContainerPairList256

-- ProtocolError-IE-ContainerList        { RANAP-PROTOCOL-IES      : IEsSetParam }	::= ProtocolIE-ContainerList     { 1, maxNrOfRABs,   {IEsSetParam} }

ProtocolError-IE-ContainerList ::= ProtocolIE-ContainerList256

-- IuSigConId-IE-ContainerList           { RANAP-PROTOCOL-IES      : IEsSetParam }	::= ProtocolIE-ContainerList     { 1, maxNrOfIuSigConIds,   {IEsSetParam} }

IuSigConId-IE-ContainerList ::= ProtocolIE-ContainerList250

-- DirectTransfer-IE-ContainerList   { RANAP-PROTOCOL-IES      : IEsSetParam }	::= ProtocolIE-ContainerList     { 1, maxNrOfDTs,    {IEsSetParam} }

DirectTransfer-IE-ContainerList ::= ProtocolIE-ContainerList15



-- **************************************************************
--
-- Iu RELEASE ELEMENTARY PROCEDURE
--
-- **************************************************************

-- **************************************************************
--
-- Iu Release Command
--
-- **************************************************************

-- Iu-ReleaseCommand ::= SEQUENCE {
--	protocolIEs			ProtocolIE-Container       { {Iu-ReleaseCommandIEs} },
--	protocolExtensions		ProtocolExtensionContainer { {Iu-ReleaseCommandExtensions} } 				OPTIONAL,
--	...
--}
Iu-ReleaseCommand ::= SEQUENCE {
	protocolIEs				ProtocolIE-Container,
	protocolExtensions		ProtocolExtensionContainer OPTIONAL,
	...
}


--Iu-ReleaseCommandIEs RANAP-PROTOCOL-IES ::= {
--	{ ID id-Cause					CRITICALITY ignore	TYPE Cause	 				PRESENCE mandatory	},
--	...
--}

--Iu-ReleaseCommandExtensions RANAP-PROTOCOL-EXTENSION ::= {
--	...
--}

-- **************************************************************
--
-- Iu Release Complete
--
-- **************************************************************

--Iu-ReleaseComplete ::= SEQUENCE {
--	protocolIEs			ProtocolIE-Container       { {Iu-ReleaseCompleteIEs} },
--	protocolExtensions		ProtocolExtensionContainer { {Iu-ReleaseCompleteExtensions} }				OPTIONAL,
--	...
--}

Iu-ReleaseComplete ::= SEQUENCE {
	protocolIEs				ProtocolIE-Container,
	protocolExtensions		ProtocolExtensionContainer OPTIONAL,
	...
}

--Iu-ReleaseCompleteIEs RANAP-PROTOCOL-IES ::= {
--	{ ID id-RAB-DataVolumeReportList		CRITICALITY ignore	TYPE RAB-DataVolumeReportList 			PRESENCE optional	} |
--	{ ID id-RAB-ReleasedList-IuRelComp		CRITICALITY ignore	TYPE RAB-ReleasedList-IuRelComp			PRESENCE optional	} |
--	{ ID id-CriticalityDiagnostics			CRITICALITY ignore	TYPE CriticalityDiagnostics  			PRESENCE optional 	},
--	...
--}

-- RAB-DataVolumeReportList 				::= RAB-IE-ContainerList { {RAB-DataVolumeReportItemIEs} }

RAB-DataVolumeReportList 				::= RAB-IE-ContainerList

--RAB-DataVolumeReportItemIEs RANAP-PROTOCOL-IES ::= {
--	{ ID id-RAB-DataVolumeReportItem		CRITICALITY ignore	TYPE RAB-DataVolumeReportItem			PRESENCE mandatory	},
--	...
--}

RAB-DataVolumeReportItem ::= SEQUENCE {
	rAB-ID						RAB-ID,
	dl-UnsuccessfullyTransmittedDataVolume		DataVolumeList		OPTIONAL
	-- This IE shall always be present although its presence is optional --,
	iE-Extensions					ProtocolExtensionContainer OPTIONAL,
	...
}

--RAB-DataVolumeReportItem-ExtIEs RANAP-PROTOCOL-EXTENSION ::= {
--	...
--}

-- RAB-ReleasedList-IuRelComp				::= RAB-IE-ContainerList { {RAB-ReleasedItem-IuRelComp-IEs} }

RAB-ReleasedList-IuRelComp				::= RAB-IE-ContainerList

--RAB-ReleasedItem-IuRelComp-IEs RANAP-PROTOCOL-IES ::= {
--	{ ID id-RAB-ReleasedItem-IuRelComp			CRITICALITY ignore	TYPE RAB-ReleasedItem-IuRelComp				PRESENCE mandatory	},
--	...
--}

RAB-ReleasedItem-IuRelComp	::= SEQUENCE {
		rAB-ID						RAB-ID,
		dL-GTP-PDU-SequenceNumber	DL-GTP-PDU-SequenceNumber 	OPTIONAL,
		uL-GTP-PDU-SequenceNumber	UL-GTP-PDU-SequenceNumber 	OPTIONAL,
--		iE-Extensions				ProtocolExtensionContainer { {RAB-ReleasedItem-IuRelComp-ExtIEs} }			OPTIONAL,
		iE-Extensions				ProtocolExtensionContainer OPTIONAL,
	...
}

--RAB-ReleasedItem-IuRelComp-ExtIEs RANAP-PROTOCOL-EXTENSION ::= {
--	...
--}


--Iu-ReleaseCompleteExtensions RANAP-PROTOCOL-EXTENSION ::= {
--	...
--}
-- **************************************************************
--
-- RELOCATION PREPARATION ELEMENTARY PROCEDURE
--
-- **************************************************************

-- **************************************************************
--
-- Relocation Required
--
-- **************************************************************
--RelocationRequired ::= SEQUENCE {
--	protocolIEs			ProtocolIE-Container       { {RelocationRequiredIEs} },
--	protocolExtensions		ProtocolExtensionContainer { {RelocationRequiredExtensions} }				OPTIONAL,
--        ...
--}

RelocationRequired ::= SEQUENCE {
	protocolIEs			ProtocolIE-Container,
	protocolExtensions		ProtocolExtensionContainer OPTIONAL,
        ...
}

--RelocationRequiredIEs RANAP-PROTOCOL-IES ::= {
--	{ ID id-RelocationType				CRITICALITY reject	TYPE RelocationType 				PRESENCE mandatory	} |
--	{ ID id-Cause					CRITICALITY ignore	TYPE Cause		 			PRESENCE mandatory	} |
--	{ ID id-SourceID				CRITICALITY ignore	TYPE SourceID	 				PRESENCE mandatory	} |
--	{ ID id-TargetID				CRITICALITY reject	TYPE TargetID	 				PRESENCE mandatory	} |
--	{ ID id-ClassmarkInformation2			CRITICALITY reject	TYPE ClassmarkInformation2			PRESENCE conditional
	-- This IE shall be present if the Target ID IE contains a CGI IE 								} |
--	{ ID id-ClassmarkInformation3			CRITICALITY ignore	TYPE ClassmarkInformation3			PRESENCE conditional
	-- This IE shall be present if the Target ID IE contains a CGI IE 								} |
--	{ ID id-SourceRNC-ToTargetRNC-TransparentContainer	
--							CRITICALITY reject	TYPE SourceRNC-ToTargetRNC-TransparentContainer PRESENCE conditional
	-- This IE shall be present if the Target ID IE contains a RNC-ID IE  												} |
--	{ ID id-OldBSS-ToNewBSS-Information		CRITICALITY ignore	TYPE OldBSS-ToNewBSS-Information		PRESENCE optional		} ,
--	...
--}

--RelocationRequiredExtensions RANAP-PROTOCOL-EXTENSION ::= {
-- Extension for Release 5 to enable GERAN support over Iu-cs --
--	{ ID id-GERAN-Classmark					CRITICALITY ignore	EXTENSION GERAN-Classmark			PRESENCE optional	} ,
--	...
--}


-- **************************************************************
--
-- Relocation Command
--
-- **************************************************************

--RelocationCommand ::= SEQUENCE {
--	protocolIEs			ProtocolIE-Container       { {RelocationCommandIEs} },
--	protocolExtensions		ProtocolExtensionContainer { {RelocationCommandExtensions} }				OPTIONAL,
--	...
--}

RelocationCommand ::= SEQUENCE {
	protocolIEs			ProtocolIE-Container,
	protocolExtensions		ProtocolExtensionContainer OPTIONAL,
	...
}

--RelocationCommandIEs RANAP-PROTOCOL-IES ::= {
--	{ ID id-TargetRNC-ToSourceRNC-TransparentContainer	
--							CRITICALITY reject	TYPE TargetRNC-ToSourceRNC-TransparentContainer PRESENCE optional	} |
--	{ ID id-L3-Information				CRITICALITY ignore	TYPE L3-Information				PRESENCE optional	} |
--	{ ID id-RAB-RelocationReleaseList		CRITICALITY ignore	TYPE RAB-RelocationReleaseList 			PRESENCE optional	} |
--	{ ID id-RAB-DataForwardingList			CRITICALITY ignore	TYPE RAB-DataForwardingList			PRESENCE optional	} |
--	{ ID id-CriticalityDiagnostics			CRITICALITY ignore	TYPE CriticalityDiagnostics 			PRESENCE optional	},
--	...
--}

--RAB-RelocationReleaseList 				::= RAB-IE-ContainerList { {RAB-RelocationReleaseItemIEs} }
RAB-RelocationReleaseList 				::= RAB-IE-ContainerList

--RAB-RelocationReleaseItemIEs RANAP-PROTOCOL-IES ::= {
--	{ ID id-RAB-RelocationReleaseItem		CRITICALITY ignore	TYPE RAB-RelocationReleaseItem			PRESENCE mandatory	},
--	...
--}

RAB-RelocationReleaseItem ::= SEQUENCE {
	rAB-ID						RAB-ID,
--	iE-Extensions					ProtocolExtensionContainer { {RAB-RelocationReleaseItem-ExtIEs} }			OPTIONAL,
	iE-Extensions					ProtocolExtensionContainer OPTIONAL,
	...
}

--RAB-RelocationReleaseItem-ExtIEs RANAP-PROTOCOL-EXTENSION ::= {
--	...
--}

--RAB-DataForwardingList 					::= RAB-IE-ContainerList { {RAB-DataForwardingItemIEs} }
RAB-DataForwardingList 					::= RAB-IE-ContainerList

--RAB-DataForwardingItemIEs RANAP-PROTOCOL-IES ::= {
--	{ ID id-RAB-DataForwardingItem			CRITICALITY ignore	TYPE RAB-DataForwardingItem			PRESENCE mandatory	},
--	...
--}

RAB-DataForwardingItem ::= SEQUENCE {
	rAB-ID						RAB-ID,
	transportLayerAddress				TransportLayerAddress,
	iuTransportAssociation				IuTransportAssociation,
--	iE-Extensions					ProtocolExtensionContainer { {RAB-DataForwardingItem-ExtIEs} }			OPTIONAL,
	iE-Extensions					ProtocolExtensionContainer	OPTIONAL,
	...
}

--RAB-DataForwardingItem-ExtIEs RANAP-PROTOCOL-EXTENSION ::= {
-- Extension for Release 5 to allow transfer of a second pair of TLA and association --
--	{ID id-TransportLayerAddress	CRITICALITY ignore	EXTENSION TransportLayerAddress	PRESENCE optional} |
--	{ID id-IuTransportAssociation	CRITICALITY ignore	EXTENSION IuTransportAssociation	PRESENCE optional},
--	...
--}

--RelocationCommandExtensions RANAP-PROTOCOL-EXTENSION ::= {
-- Extension for Release 5 to enable Inter RAN Load Information Exchange over Iu --
--	{ ID id-InterSystemInformation-TransparentContainer		CRITICALITY ignore	EXTENSION InterSystemInformation-TransparentContainer					PRESENCE optional	},
--	...
--}
-- **************************************************************
--
-- Relocation Preparation Failure
--
-- **************************************************************

--RelocationPreparationFailure ::= SEQUENCE {
--	protocolIEs			ProtocolIE-Container       { {RelocationPreparationFailureIEs} },
--	protocolExtensions		ProtocolExtensionContainer { {RelocationPreparationFailureExtensions} }			OPTIONAL,
--      ...
--}
RelocationPreparationFailure ::= SEQUENCE {
	protocolIEs			ProtocolIE-Container,
	protocolExtensions		ProtocolExtensionContainer	OPTIONAL,
      ...
}

--RelocationPreparationFailureIEs RANAP-PROTOCOL-IES ::= {
--	{ ID id-Cause					CRITICALITY ignore	TYPE Cause					PRESENCE mandatory	} |
--	{ ID id-CriticalityDiagnostics			CRITICALITY ignore	TYPE CriticalityDiagnostics 			PRESENCE optional	},
--	...
--}

--RelocationPreparationFailureExtensions RANAP-PROTOCOL-EXTENSION ::= {
-- Extension for Release 5 to enable Inter RAN Load Information Exchange over Iu 
--	{ ID id-InterSystemInformation-TransparentContainer		CRITICALITY ignore	EXTENSION InterSystemInformation-TransparentContainer				PRESENCE optional	},
--	...
--}

-- **************************************************************
--
-- RELOCATION RESOURCE ALLOCATION ELEMENTARY PROCEDURE
--
-- **************************************************************

-- **************************************************************
--
-- Relocation Request
--
-- **************************************************************

--RelocationRequest ::= SEQUENCE {
--	protocolIEs			ProtocolIE-Container       { {RelocationRequestIEs} },
--	protocolExtensions		ProtocolExtensionContainer { {RelocationRequestExtensions} }				OPTIONAL,
--	...
--}
RelocationRequest ::= SEQUENCE {
	protocolIEs			ProtocolIE-Container,
	protocolExtensions		ProtocolExtensionContainer OPTIONAL,
	...
}

--RelocationRequestIEs RANAP-PROTOCOL-IES ::= {
--	{ ID id-PermanentNAS-UE-ID			CRITICALITY ignore	TYPE PermanentNAS-UE-ID 			PRESENCE optional	} |
--	{ ID id-Cause					CRITICALITY ignore	TYPE Cause					PRESENCE mandatory	} |
--	{ ID id-CN-DomainIndicator			CRITICALITY reject	TYPE CN-DomainIndicator				PRESENCE mandatory	} |
--	{ ID id-SourceRNC-ToTargetRNC-TransparentContainer		
--							CRITICALITY reject	TYPE SourceRNC-ToTargetRNC-TransparentContainer	PRESENCE mandatory	} |
--	{ ID id-RAB-SetupList-RelocReq			CRITICALITY reject	TYPE RAB-SetupList-RelocReq			PRESENCE optional	} |
--	{ ID id-IntegrityProtectionInformation		CRITICALITY ignore	TYPE IntegrityProtectionInformation 		PRESENCE optional	} |
--	{ ID id-EncryptionInformation			CRITICALITY ignore	TYPE EncryptionInformation 			PRESENCE optional	} |
--	{ ID id-IuSigConId	CRITICALITY ignore TYPE IuSignallingConnectionIdentifier  PRESENCE mandatory },
--	...
--}

--RAB-SetupList-RelocReq 					::= RAB-IE-ContainerList { {RAB-SetupItem-RelocReq-IEs} }
RAB-SetupList-RelocReq 					::= RAB-IE-ContainerList

--RAB-SetupItem-RelocReq-IEs RANAP-PROTOCOL-IES ::= { 
--	{ ID id-RAB-SetupItem-RelocReq			CRITICALITY reject	TYPE RAB-SetupItem-RelocReq			PRESENCE mandatory 	},
--	...
--}

RAB-SetupItem-RelocReq ::= SEQUENCE {
	rAB-ID						RAB-ID,
	nAS-SynchronisationIndicator	NAS-SynchronisationIndicator	OPTIONAL,
	rAB-Parameters					RAB-Parameters,
	dataVolumeReportingIndication			DataVolumeReportingIndication 	OPTIONAL
	-- This IE shall be present if the CN domain indicator IE is set to "PS domain" --,
	pDP-TypeInformation				PDP-TypeInformation		OPTIONAL
  	-- This IE shall be present if the CN domain indicator IE is set to "PS domain" --,
	userPlaneInformation				UserPlaneInformation,
	transportLayerAddress				TransportLayerAddress,
	iuTransportAssociation				IuTransportAssociation,
	service-Handover				Service-Handover		OPTIONAL,
--	iE-Extensions					ProtocolExtensionContainer { {RAB-SetupItem-RelocReq-ExtIEs} }			OPTIONAL,
	iE-Extensions					ProtocolExtensionContainer OPTIONAL,
	...
}

--RAB-SetupItem-RelocReq-ExtIEs RANAP-PROTOCOL-EXTENSION ::= {
-- Extension for Release 4 to enable RAB Quality of Service negotiation over Iu 
--	{ID id-Alt-RAB-Parameters	CRITICALITY ignore		EXTENSION Alt-RAB-Parameters		PRESENCE optional} |
-- Extension for Release 5 to enable GERAN support over Iu-cs 
--	{ ID id-GERAN-BSC-Container					CRITICALITY ignore	EXTENSION GERAN-BSC-Container			PRESENCE optional	},
--	...
--}

UserPlaneInformation ::= SEQUENCE {
	userPlaneMode					UserPlaneMode,
	uP-ModeVersions					UP-ModeVersions,
--	iE-Extensions					ProtocolExtensionContainer { {UserPlaneInformation-ExtIEs} }			OPTIONAL,
	iE-Extensions					ProtocolExtensionContainer OPTIONAL,
	...
}

--UserPlaneInformation-ExtIEs RANAP-PROTOCOL-EXTENSION ::= {
--	...
--}

--RelocationRequestExtensions RANAP-PROTOCOL-EXTENSION ::= {
-- Extension for Release 4 
--	{ ID id-GlobalCN-ID				CRITICALITY reject		EXTENSION GlobalCN-ID				PRESENCE optional} |
-- Extension for Release 5 to enable shared networks in connected mode 
--	{ ID id-SNA-Access-Information	CRITICALITY ignore		EXTENSION SNA-Access-Information	PRESENCE optional} |
-- Extension for Release 5 to enable specific behaviour by the RNC in relation with early UE handling 
--	{ ID id-UESBI-Iu	CRITICALITY ignore		EXTENSION UESBI-Iu	PRESENCE optional}|
-- Extension for Release 6 to convey the selected PLMN id in network sharing mobility scenarios 
--	{ ID id-SelectedPLMN-ID	 	CRITICALITY ignore	EXTENSION PLMNidentity		PRESENCE optional 	}|
-- Extension for Release 6 to enable MBMS UE linking at relocation 
--	{ ID id-CNMBMSLinkingInformation	CRITICALITY ignore		EXTENSION CNMBMSLinkingInformation	PRESENCE optional},
--	...
--}

CNMBMSLinkingInformation ::= SEQUENCE {
	joinedMBMSBearerService-IEs		JoinedMBMSBearerService-IEs,
--	iE-Extensions					ProtocolExtensionContainer { {CNMBMSLinkingInformation-ExtIEs} }		OPTIONAL,
	iE-Extensions					ProtocolExtensionContainer OPTIONAL,
	...
}

--CNMBMSLinkingInformation-ExtIEs RANAP-PROTOCOL-EXTENSION ::= {
--	...
--}

JoinedMBMSBearerService-IEs ::= SEQUENCE (SIZE (1.. 128)) OF
	SEQUENCE {
		tMGI				TMGI,
		mBMS-PTP-RAB-ID		MBMS-PTP-RAB-ID,
--		iE-Extensions		ProtocolExtensionContainer { {JoinedMBMSBearerService-ExtIEs} } OPTIONAL,
		iE-Extensions		ProtocolExtensionContainer  OPTIONAL,
		...
	}

--JoinedMBMSBearerService-ExtIEs RANAP-PROTOCOL-EXTENSION ::= {
--	...
--}

-- **************************************************************
--
-- Relocation Request Acknowledge
--
-- **************************************************************

--RelocationRequestAcknowledge ::= SEQUENCE {
--	protocolIEs			ProtocolIE-Container       { {RelocationRequestAcknowledgeIEs} },
--	protocolExtensions		ProtocolExtensionContainer { {RelocationRequestAcknowledgeExtensions} }			OPTIONAL,
--	...
--}
RelocationRequestAcknowledge ::= SEQUENCE {
	protocolIEs			ProtocolIE-Container,
	protocolExtensions		ProtocolExtensionContainer 	OPTIONAL,
	...
}

--RelocationRequestAcknowledgeIEs RANAP-PROTOCOL-IES ::= {
--	{ ID id-TargetRNC-ToSourceRNC-TransparentContainer
--							CRITICALITY ignore	TYPE TargetRNC-ToSourceRNC-TransparentContainer PRESENCE optional	} |
--	{ ID id-RAB-SetupList-RelocReqAck		CRITICALITY ignore	TYPE RAB-SetupList-RelocReqAck			PRESENCE optional} |
--	{ ID id-RAB-FailedList				CRITICALITY ignore	TYPE RAB-FailedList				PRESENCE optional }|
--	{ ID id-ChosenIntegrityProtectionAlgorithm	CRITICALITY ignore	TYPE ChosenIntegrityProtectionAlgorithm		PRESENCE optional	} |
--	{ ID id-ChosenEncryptionAlgorithm		CRITICALITY ignore	TYPE ChosenEncryptionAlgorithm			PRESENCE optional	} |
--	{ ID id-CriticalityDiagnostics			CRITICALITY ignore	TYPE CriticalityDiagnostics 			PRESENCE optional	},
--	...
--}

--RAB-SetupList-RelocReqAck 				::= RAB-IE-ContainerList { {RAB-SetupItem-RelocReqAck-IEs} }
RAB-SetupList-RelocReqAck 				::= RAB-IE-ContainerList 

--RAB-SetupItem-RelocReqAck-IEs RANAP-PROTOCOL-IES ::= { 
--	{ ID id-RAB-SetupItem-RelocReqAck		CRITICALITY reject	TYPE RAB-SetupItem-RelocReqAck			PRESENCE mandatory 	},
--	...
--}

RAB-SetupItem-RelocReqAck ::= SEQUENCE {
	rAB-ID						RAB-ID,
	transportLayerAddress				TransportLayerAddress	OPTIONAL,
	iuTransportAssociation				IuTransportAssociation	OPTIONAL,
--	iE-Extensions					ProtocolExtensionContainer { {RAB-SetupItem-RelocReqAck-ExtIEs} }			OPTIONAL,
	iE-Extensions					ProtocolExtensionContainer OPTIONAL,
	...
}

--RAB-SetupItem-RelocReqAck-ExtIEs RANAP-PROTOCOL-EXTENSION ::= {
-- Extension for Release 4 to enable RAB Quality of Service negotiation over Iu 
--	{ID id-Ass-RAB-Parameters	CRITICALITY ignore		EXTENSION Ass-RAB-Parameters		PRESENCE optional	} |
-- Extension for Release 5 to allow transfer of a second pair of TLA and association 
--	{ID id-TransportLayerAddress	CRITICALITY ignore	EXTENSION TransportLayerAddress	PRESENCE optional} |
--	{ID id-IuTransportAssociation	CRITICALITY ignore	EXTENSION IuTransportAssociation	PRESENCE optional},
--	...
--}

--RAB-FailedList 						::= RAB-IE-ContainerList { {RAB-FailedItemIEs} }
RAB-FailedList 						::= RAB-IE-ContainerList

--RAB-FailedItemIEs RANAP-PROTOCOL-IES ::= {
--	{ ID id-RAB-FailedItem				CRITICALITY ignore	TYPE RAB-FailedItem				PRESENCE mandatory	},
--	...
--}

RAB-FailedItem ::= SEQUENCE {
	rAB-ID						RAB-ID,
	cause						Cause,
--	iE-Extensions					ProtocolExtensionContainer { {RAB-FailedItem-ExtIEs} }			OPTIONAL,
	iE-Extensions					ProtocolExtensionContainer 	OPTIONAL,
	...
}

--RAB-FailedItem-ExtIEs RANAP-PROTOCOL-EXTENSION ::= {
--	...
--}

--RelocationRequestAcknowledgeExtensions RANAP-PROTOCOL-EXTENSION ::= {
-- Extension for Release 5 to enable Inter RAN Load Information Exchange over Iu 
--	{ID id-NewBSS-To-OldBSS-Information		CRITICALITY ignore	EXTENSION NewBSS-To-OldBSS-Information		PRESENCE optional		},
--	...
--}

-- **************************************************************
--
-- Relocation Failure
--
-- **************************************************************

--RelocationFailure ::= SEQUENCE {
--	protocolIEs			ProtocolIE-Container       { {RelocationFailureIEs} },
--	protocolExtensions		ProtocolExtensionContainer { {RelocationFailureExtensions} }				OPTIONAL,
--	...
--}
RelocationFailure ::= SEQUENCE {
	protocolIEs			ProtocolIE-Container,
	protocolExtensions		ProtocolExtensionContainer OPTIONAL,
	...
}

--RelocationFailureIEs RANAP-PROTOCOL-IES ::= {
--	{ ID id-Cause					CRITICALITY ignore	TYPE Cause					PRESENCE mandatory	} |
--	{ ID id-CriticalityDiagnostics			CRITICALITY ignore	TYPE CriticalityDiagnostics 			PRESENCE optional	},
--	...
--}

--RelocationFailureExtensions RANAP-PROTOCOL-EXTENSION ::= {
-- Extension for Release 5 to enable Inter RAN Load Information Exchange over Iu 
--	{ ID id-NewBSS-To-OldBSS-Information		CRITICALITY ignore	EXTENSION NewBSS-To-OldBSS-Information		PRESENCE optional	} |
-- Extension for Release 5 to enable GERAN support over Iu-cs 
--	{ ID id-GERAN-Classmark					CRITICALITY ignore	EXTENSION GERAN-Classmark			PRESENCE optional	},
--	...
--}

-- **************************************************************
--
-- RELOCATION CANCEL ELEMENTARY PROCEDURE
--
-- **************************************************************

-- **************************************************************
--
-- RAB ASSIGNMENT ELEMENTARY PROCEDURE
--
-- **************************************************************

-- **************************************************************
--
-- RAB Assignment Request
--
-- **************************************************************

-- **************************************************************
--
-- Relocation Cancel
--
-- **************************************************************

--RelocationCancel ::= SEQUENCE {
--	protocolIEs			ProtocolIE-Container       { {RelocationCancelIEs} },
--	protocolExtensions		ProtocolExtensionContainer { {RelocationCancelExtensions} }				OPTIONAL,
--	...
--}
RelocationCancel ::= SEQUENCE {
	protocolIEs			ProtocolIE-Container,
	protocolExtensions		ProtocolExtensionContainer	OPTIONAL,
	...
}

--RelocationCancelIEs RANAP-PROTOCOL-IES ::= {
--	{ ID id-Cause					CRITICALITY ignore	TYPE Cause					PRESENCE mandatory	},
--	...
--}

--RelocationCancelExtensions RANAP-PROTOCOL-EXTENSION ::= {
--	...
--}

-- **************************************************************
--
-- Relocation Cancel Acknowledge
--
-- **************************************************************

--RelocationCancelAcknowledge ::= SEQUENCE {
--	protocolIEs			ProtocolIE-Container       { {RelocationCancelAcknowledgeIEs} },
--	protocolExtensions		ProtocolExtensionContainer { {RelocationCancelAcknowledgeExtensions} } 			OPTIONAL,
--	...
--}
RelocationCancelAcknowledge ::= SEQUENCE {
	protocolIEs			ProtocolIE-Container,
	protocolExtensions		ProtocolExtensionContainer OPTIONAL,
	...
}

--RelocationCancelAcknowledgeIEs RANAP-PROTOCOL-IES ::= {
--	{ ID id-CriticalityDiagnostics			CRITICALITY ignore	TYPE CriticalityDiagnostics			PRESENCE optional	},
--	...
--}

--RelocationCancelAcknowledgeExtensions RANAP-PROTOCOL-EXTENSION ::= {
--	...
--}

-- **************************************************************
--
-- SRNS CONTEXT TRANSFER OPEARATION
--
-- **************************************************************

-- **************************************************************
--
-- SRNS Context Request
--
-- **************************************************************

--SRNS-ContextRequest ::= SEQUENCE {
--	protocolIEs			ProtocolIE-Container       { {SRNS-ContextRequestIEs} },
--	protocolExtensions		ProtocolExtensionContainer { {SRNS-ContextRequestExtensions} }				OPTIONAL,
--	...
--}
SRNS-ContextRequest ::= SEQUENCE {
	protocolIEs			ProtocolIE-Container,
	protocolExtensions		ProtocolExtensionContainer 	OPTIONAL,
	...
}

--SRNS-ContextRequestIEs RANAP-PROTOCOL-IES ::= {
--	{ ID id-RAB-DataForwardingList-SRNS-CtxReq	CRITICALITY ignore	TYPE RAB-DataForwardingList-SRNS-CtxReq		PRESENCE mandatory	},
--	...
--}

--RAB-DataForwardingList-SRNS-CtxReq 			::= RAB-IE-ContainerList { {RAB-DataForwardingItem-SRNS-CtxReq-IEs} }
RAB-DataForwardingList-SRNS-CtxReq 			::= RAB-IE-ContainerList 

--RAB-DataForwardingItem-SRNS-CtxReq-IEs RANAP-PROTOCOL-IES ::= {
--	{ ID id-RAB-DataForwardingItem-SRNS-CtxReq	CRITICALITY reject	TYPE RAB-DataForwardingItem-SRNS-CtxReq		PRESENCE mandatory	},
--	...
--}

RAB-DataForwardingItem-SRNS-CtxReq ::= SEQUENCE {
	rAB-ID						RAB-ID,
--	iE-Extensions					ProtocolExtensionContainer { {RAB-DataForwardingItem-SRNS-CtxReq-ExtIEs} }			OPTIONAL,
	iE-Extensions					ProtocolExtensionContainer 	OPTIONAL,
	...
}

--RAB-DataForwardingItem-SRNS-CtxReq-ExtIEs RANAP-PROTOCOL-EXTENSION ::= {
--	...
--}

--SRNS-ContextRequestExtensions RANAP-PROTOCOL-EXTENSION ::= {
--	...
--}

-- **************************************************************
--
-- SRNS Context Response
--
-- **************************************************************

--SRNS-ContextResponse ::= SEQUENCE {
--	protocolIEs			ProtocolIE-Container       { {SRNS-ContextResponseIEs} },
--	protocolExtensions		ProtocolExtensionContainer { {SRNS-ContextResponseExtensions} }				OPTIONAL,
--	...
--}

SRNS-ContextResponse ::= SEQUENCE {
	protocolIEs			ProtocolIE-Container,
	protocolExtensions		ProtocolExtensionContainer OPTIONAL,
	...
}

--SRNS-ContextResponseIEs RANAP-PROTOCOL-IES ::= {
--	{ ID id-RAB-ContextList				CRITICALITY ignore	TYPE RAB-ContextList				PRESENCE optional	} |
--	{ ID id-RAB-ContextFailedtoTransferList		CRITICALITY ignore	TYPE RAB-ContextFailedtoTransferList		PRESENCE optional	}|
--	{ ID id-CriticalityDiagnostics			CRITICALITY ignore	TYPE CriticalityDiagnostics			PRESENCE optional	},
--	...
--}

--RAB-ContextList 					::= RAB-IE-ContainerList { {RAB-ContextItemIEs} }
RAB-ContextList 					::= RAB-IE-ContainerList 

--RAB-ContextItemIEs RANAP-PROTOCOL-IES ::= {
--	{ ID id-RAB-ContextItem				CRITICALITY ignore	TYPE RAB-ContextItem				PRESENCE mandatory	},
--	...
--}

RAB-ContextItem ::= SEQUENCE {
	rAB-ID						RAB-ID,
	dl-GTP-PDU-SequenceNumber			DL-GTP-PDU-SequenceNumber 	OPTIONAL,
	ul-GTP-PDU-SequenceNumber			UL-GTP-PDU-SequenceNumber 	OPTIONAL,
	dl-N-PDU-SequenceNumber				DL-N-PDU-SequenceNumber 	OPTIONAL,
	ul-N-PDU-SequenceNumber				UL-N-PDU-SequenceNumber 	OPTIONAL,
--	iE-Extensions					ProtocolExtensionContainer { {RAB-ContextItem-ExtIEs} }			OPTIONAL,
	iE-Extensions					ProtocolExtensionContainer OPTIONAL,
	...
}

--RAB-ContextItem-ExtIEs RANAP-PROTOCOL-EXTENSION ::= {
--	...
--}

--RAB-ContextFailedtoTransferList 				::= RAB-IE-ContainerList { {RABs-ContextFailedtoTransferItemIEs} }
RAB-ContextFailedtoTransferList 				::= RAB-IE-ContainerList

--RABs-ContextFailedtoTransferItemIEs RANAP-PROTOCOL-IES ::= {
--	{ ID id-RAB-ContextFailedtoTransferItem		CRITICALITY ignore	TYPE RABs-ContextFailedtoTransferItem			PRESENCE mandatory	},
--	...
--}

RABs-ContextFailedtoTransferItem::= SEQUENCE {
	rAB-ID						RAB-ID,
	cause						Cause,
--	iE-Extensions					ProtocolExtensionContainer { { RABs-ContextFailedtoTransferItem-ExtIEs} }			OPTIONAL,
	iE-Extensions					ProtocolExtensionContainer 	OPTIONAL,
	...
}


--RABs-ContextFailedtoTransferItem-ExtIEs RANAP-PROTOCOL-EXTENSION ::= {
--	...
--}

--SRNS-ContextResponseExtensions RANAP-PROTOCOL-EXTENSION ::= {
--	...
--}

-- **************************************************************
--
-- SECURITY MODE CONTROL ELEMENTARY PROCEDURE
--
-- **************************************************************

-- **************************************************************
--
-- Security Mode Command
--
-- **************************************************************

--SecurityModeCommand ::= SEQUENCE {
--	protocolIEs			ProtocolIE-Container       { {SecurityModeCommandIEs} },
--	protocolExtensions		ProtocolExtensionContainer { {SecurityModeCommandExtensions} }				OPTIONAL,
--	...
--}
SecurityModeCommand ::= SEQUENCE {
	protocolIEs			ProtocolIE-Container,
	protocolExtensions		ProtocolExtensionContainer OPTIONAL,
	...
}

--SecurityModeCommandIEs RANAP-PROTOCOL-IES ::= {
--	{ ID id-IntegrityProtectionInformation		CRITICALITY reject	TYPE IntegrityProtectionInformation		PRESENCE mandatory	} |
--	{ ID id-EncryptionInformation			CRITICALITY ignore	TYPE EncryptionInformation			PRESENCE optional	} |
--	{ ID id-KeyStatus						CRITICALITY reject	TYPE KeyStatus						PRESENCE mandatory},
--	...
--}

--SecurityModeCommandExtensions RANAP-PROTOCOL-EXTENSION ::= {
--	...
--}

-- **************************************************************
--
-- Security Mode Complete
--
-- **************************************************************

--SecurityModeComplete ::= SEQUENCE {
--	protocolIEs			ProtocolIE-Container       { {SecurityModeCompleteIEs} },
--	protocolExtensions		ProtocolExtensionContainer { {SecurityModeCompleteExtensions} }				OPTIONAL,
--	...
--}
SecurityModeComplete ::= SEQUENCE {
	protocolIEs			ProtocolIE-Container,
	protocolExtensions		ProtocolExtensionContainer OPTIONAL,
	...
}

--SecurityModeCompleteIEs RANAP-PROTOCOL-IES ::= {
--	{ ID id-ChosenIntegrityProtectionAlgorithm	CRITICALITY reject	TYPE ChosenIntegrityProtectionAlgorithm 	PRESENCE mandatory	} |
--	{ ID id-ChosenEncryptionAlgorithm		CRITICALITY ignore	TYPE ChosenEncryptionAlgorithm			PRESENCE optional	} |
--	{ ID id-CriticalityDiagnostics			CRITICALITY ignore	TYPE CriticalityDiagnostics			PRESENCE optional	},
--	...
--}

--SecurityModeCompleteExtensions RANAP-PROTOCOL-EXTENSION ::= {
--	...
--}

-- **************************************************************
--
-- Security Mode Reject
--
-- **************************************************************

--SecurityModeReject ::= SEQUENCE {
--	protocolIEs			ProtocolIE-Container       { {SecurityModeRejectIEs} },
--	protocolExtensions		ProtocolExtensionContainer { {SecurityModeRejectExtensions} }				OPTIONAL,
--	...
--}
SecurityModeReject ::= SEQUENCE {
	protocolIEs			ProtocolIE-Container,
	protocolExtensions		ProtocolExtensionContainer OPTIONAL,
	...
}

--SecurityModeRejectIEs RANAP-PROTOCOL-IES ::= {
--	{ ID id-Cause					CRITICALITY ignore	TYPE Cause					PRESENCE mandatory	} |
--	{ ID id-CriticalityDiagnostics			CRITICALITY ignore	TYPE CriticalityDiagnostics 			PRESENCE optional	},
--	...
--}

--SecurityModeRejectExtensions RANAP-PROTOCOL-EXTENSION ::= {
--	...
--}

-- **************************************************************
--
-- DATA VOLUME REPORT ELEMENTARY PROCEDURE
--
-- **************************************************************

-- **************************************************************
--
-- Data Volume Report Request
--
-- **************************************************************

--DataVolumeReportRequest ::= SEQUENCE {
--	protocolIEs			ProtocolIE-Container       { {DataVolumeReportRequestIEs} },
--	protocolExtensions		ProtocolExtensionContainer { {DataVolumeReportRequestExtensions} }			OPTIONAL,
--	...
--}
DataVolumeReportRequest ::= SEQUENCE {
	protocolIEs			ProtocolIE-Container,
	protocolExtensions		ProtocolExtensionContainer OPTIONAL,
	...
}

--DataVolumeReportRequestIEs RANAP-PROTOCOL-IES ::= {
--	{ ID id-RAB-DataVolumeReportRequestList		CRITICALITY ignore	TYPE RAB-DataVolumeReportRequestList		PRESENCE mandatory	},
--	...
--}

--RAB-DataVolumeReportRequestList 			::= RAB-IE-ContainerList { {RAB-DataVolumeReportRequestItemIEs} }
RAB-DataVolumeReportRequestList 			::= RAB-IE-ContainerList 

--RAB-DataVolumeReportRequestItemIEs RANAP-PROTOCOL-IES ::= {
--	{ ID id-RAB-DataVolumeReportRequestItem		CRITICALITY reject	TYPE RAB-DataVolumeReportRequestItem		PRESENCE mandatory	},
--	...
--}

RAB-DataVolumeReportRequestItem ::= SEQUENCE {
	rAB-ID						RAB-ID,
--	iE-Extensions					ProtocolExtensionContainer { {RAB-DataVolumeReportRequestItem-ExtIEs} }			OPTIONAL,
	iE-Extensions					ProtocolExtensionContainer OPTIONAL,
	...
}

--RAB-DataVolumeReportRequestItem-ExtIEs RANAP-PROTOCOL-EXTENSION ::= {
--	...
--}

--DataVolumeReportRequestExtensions RANAP-PROTOCOL-EXTENSION ::= {
--	...
--}

-- **************************************************************
--
-- Data Volume Report
--
-- **************************************************************

--DataVolumeReport ::= SEQUENCE {
--	protocolIEs			ProtocolIE-Container       { {DataVolumeReportIEs} },
--	protocolExtensions		ProtocolExtensionContainer { {DataVolumeReportExtensions} }				OPTIONAL,
--	...
--}

DataVolumeReport ::= SEQUENCE {
	protocolIEs			ProtocolIE-Container,
	protocolExtensions		ProtocolExtensionContainer OPTIONAL,
	...
}

--DataVolumeReportIEs RANAP-PROTOCOL-IES ::= {
--	{ ID id-RAB-DataVolumeReportList		CRITICALITY ignore	TYPE RAB-DataVolumeReportList			PRESENCE optional	} |
--	{ ID id-RAB-FailedtoReportList			CRITICALITY ignore	TYPE RAB-FailedtoReportList			PRESENCE optional	} |
--	{ ID id-CriticalityDiagnostics			CRITICALITY ignore	TYPE CriticalityDiagnostics			PRESENCE optional	},
--	...
--}

--DataVolumeReportExtensions RANAP-PROTOCOL-EXTENSION ::= {
--	...
--}

--RAB-FailedtoReportList 				::= RAB-IE-ContainerList { {RABs-failed-to-reportItemIEs} }
RAB-FailedtoReportList 				::= RAB-IE-ContainerList 

--RABs-failed-to-reportItemIEs RANAP-PROTOCOL-IES ::= {
--	{ ID id-RAB-FailedtoReportItem		CRITICALITY ignore	TYPE RABs-failed-to-reportItem			PRESENCE mandatory	},
--	...
--}

RABs-failed-to-reportItem::= SEQUENCE {
	rAB-ID						RAB-ID,
	cause						Cause,
--	iE-Extensions					ProtocolExtensionContainer { { RABs-failed-to-reportItem-ExtIEs} }			OPTIONAL,
	iE-Extensions					ProtocolExtensionContainer OPTIONAL,
	...
}


--RABs-failed-to-reportItem-ExtIEs RANAP-PROTOCOL-EXTENSION ::= {
--	...
--}


-- **************************************************************
--
-- RESET ELEMENTARY PROCEDURE
--
-- **************************************************************


--Reset ::= SEQUENCE {
--	protocolIEs			ProtocolIE-Container       { {ResetIEs} },
--	protocolExtensions		ProtocolExtensionContainer { {ResetExtensions} }					OPTIONAL,
--	...
--}

Reset ::= SEQUENCE {
	protocolIEs			ProtocolIE-Container,
	protocolExtensions		ProtocolExtensionContainer OPTIONAL,
	...
}

--ResetIEs RANAP-PROTOCOL-IES ::= {
--	{ ID id-Cause					CRITICALITY ignore	TYPE Cause					PRESENCE mandatory	} |
--	{ ID id-CN-DomainIndicator			CRITICALITY reject	TYPE CN-DomainIndicator				PRESENCE mandatory	} |
--	{ ID id-GlobalRNC-ID				CRITICALITY ignore	TYPE GlobalRNC-ID				PRESENCE optional	},
--	...
--}

--ResetExtensions RANAP-PROTOCOL-EXTENSION ::= {
-- Extension for Release 4 
--	{ ID id-GlobalCN-ID				CRITICALITY ignore		EXTENSION GlobalCN-ID				PRESENCE optional},
--	...
--}

-- **************************************************************
--
-- Reset Acknowledge
--
-- **************************************************************

--ResetAcknowledge ::= SEQUENCE {
--	protocolIEs			ProtocolIE-Container       { {ResetAcknowledgeIEs} },
--	protocolExtensions		ProtocolExtensionContainer { {ResetAcknowledgeExtensions} }				OPTIONAL,
--	...
--}

ResetAcknowledge ::= SEQUENCE {
	protocolIEs			ProtocolIE-Container,
	protocolExtensions		ProtocolExtensionContainer OPTIONAL,
	...
}

--ResetAcknowledgeIEs RANAP-PROTOCOL-IES ::= {
--	{ ID id-CN-DomainIndicator			CRITICALITY reject	TYPE CN-DomainIndicator				PRESENCE mandatory	} |
--	 { ID id-CriticalityDiagnostics			CRITICALITY ignore	TYPE CriticalityDiagnostics			PRESENCE optional	} |
--	{ ID id-GlobalRNC-ID				CRITICALITY ignore	TYPE GlobalRNC-ID				PRESENCE optional	},
--	...
--}

--ResetAcknowledgeExtensions RANAP-PROTOCOL-EXTENSION ::= {
-- Extension for Release 4 
--	{ ID id-GlobalCN-ID				CRITICALITY ignore		EXTENSION GlobalCN-ID				PRESENCE optional},
--	...
--}
-- **************************************************************
--
-- RESET RESOURCE ELEMENTARY PROCEDURE
--
-- **************************************************************


-- **************************************************************
--
-- Reset Resource
--
-- **************************************************************

--ResetResource ::= SEQUENCE {
--	protocolIEs			ProtocolIE-Container       { {ResetResourceIEs} },
--	protocolExtensions		ProtocolExtensionContainer { {ResetResourceExtensions} }					OPTIONAL,
--	...
--}

ResetResource ::= SEQUENCE {
	protocolIEs			ProtocolIE-Container,
	protocolExtensions		ProtocolExtensionContainer OPTIONAL,
	...
}

--ResetResourceIEs RANAP-PROTOCOL-IES ::= {
--	{ ID id-CN-DomainIndicator			CRITICALITY reject	TYPE CN-DomainIndicator				PRESENCE mandatory	} |
--	{ ID id-Cause					CRITICALITY ignore	TYPE Cause					PRESENCE mandatory	} |
--	{ ID id-IuSigConIdList				CRITICALITY ignore	TYPE ResetResourceList				PRESENCE mandatory	} |
--	{ ID id-GlobalRNC-ID				CRITICALITY ignore	TYPE GlobalRNC-ID				PRESENCE optional	},
--	...
--}

--ResetResourceList 	::=	IuSigConId-IE-ContainerList{ {ResetResourceItemIEs} }
ResetResourceList 	::=	IuSigConId-IE-ContainerList

--ResetResourceItemIEs RANAP-PROTOCOL-IES ::= {
--	{ ID id-IuSigConIdItem				CRITICALITY reject	TYPE	ResetResourceItem			PRESENCE mandatory	},
--	...
--}

ResetResourceItem ::= SEQUENCE {
	iuSigConId					IuSignallingConnectionIdentifier,
--	iE-Extensions				ProtocolExtensionContainer { { ResetResourceItem-ExtIEs} }			OPTIONAL,
	iE-Extensions				ProtocolExtensionContainer OPTIONAL,
	...
}

--ResetResourceItem-ExtIEs RANAP-PROTOCOL-EXTENSION ::= {
--	...
--}

--ResetResourceExtensions RANAP-PROTOCOL-EXTENSION ::= {
-- Extension for Release 4 
--	{ ID id-GlobalCN-ID				CRITICALITY ignore		EXTENSION GlobalCN-ID				PRESENCE optional},
--	...
--}

-- **************************************************************
--
-- Reset Resource Acknowledge
--
-- **************************************************************

--ResetResourceAcknowledge ::= SEQUENCE {
--	protocolIEs			ProtocolIE-Container       { {ResetResourceAcknowledgeIEs} },
--	protocolExtensions		ProtocolExtensionContainer { {ResetResourceAcknowledgeExtensions} }				OPTIONAL,
--	...
--}

ResetResourceAcknowledge ::= SEQUENCE {
	protocolIEs			ProtocolIE-Container,
	protocolExtensions		ProtocolExtensionContainer	OPTIONAL,
	...
}

--ResetResourceAcknowledgeIEs RANAP-PROTOCOL-IES ::= {
--	{ ID id-CN-DomainIndicator			CRITICALITY reject	TYPE CN-DomainIndicator				PRESENCE mandatory	} |
--	{ ID id-IuSigConIdList				CRITICALITY ignore	TYPE ResetResourceAckList			PRESENCE mandatory	} |
--	{ ID id-GlobalRNC-ID				CRITICALITY ignore	TYPE GlobalRNC-ID				PRESENCE optional	} |
--	{ ID id-CriticalityDiagnostics			CRITICALITY ignore	TYPE CriticalityDiagnostics			PRESENCE optional	},
--	...
--}
--ResetResourceAckList 	::=	IuSigConId-IE-ContainerList{ {ResetResourceAckItemIEs} }
ResetResourceAckList 	::=	IuSigConId-IE-ContainerList

--ResetResourceAckItemIEs RANAP-PROTOCOL-IES ::= {
--	{ ID id-IuSigConIdItem				CRITICALITY reject	TYPE	ResetResourceAckItem			PRESENCE mandatory	},
--	...
--}

ResetResourceAckItem ::= SEQUENCE {
	iuSigConId					IuSignallingConnectionIdentifier,
--	iE-Extensions				ProtocolExtensionContainer { { ResetResourceAckItem-ExtIEs} }			OPTIONAL,
	iE-Extensions				ProtocolExtensionContainer OPTIONAL,
	...
}

--ResetResourceAckItem-ExtIEs RANAP-PROTOCOL-EXTENSION ::= {
--	...
--}

--ResetResourceAcknowledgeExtensions RANAP-PROTOCOL-EXTENSION ::= {
-- Extension for Release 4 
--	{ ID id-GlobalCN-ID				CRITICALITY ignore		EXTENSION GlobalCN-ID				PRESENCE optional},
--	...
--}

-- **************************************************************
--
-- RAB RELEASE REQUEST ELEMENTARY PROCEDURE
--
-- **************************************************************

-- **************************************************************
--
-- RAB Release Request
--
-- **************************************************************

--RAB-ReleaseRequest ::= SEQUENCE {
--	protocolIEs			ProtocolIE-Container       { {RAB-ReleaseRequestIEs} },
--	protocolExtensions		ProtocolExtensionContainer { {RAB-ReleaseRequestExtensions} }				OPTIONAL,
--	...
--}
RAB-ReleaseRequest ::= SEQUENCE {
	protocolIEs			ProtocolIE-Container,
	protocolExtensions		ProtocolExtensionContainer OPTIONAL,
	...
}

--RAB-ReleaseRequestIEs RANAP-PROTOCOL-IES ::= {
--	{ ID id-RAB-ReleaseList				CRITICALITY ignore	TYPE RAB-ReleaseList				PRESENCE mandatory	},
--	...
--}

--RAB-ReleaseList 					::= RAB-IE-ContainerList { {RAB-ReleaseItemIEs} }
RAB-ReleaseList 					::= RAB-IE-ContainerList

--RAB-ReleaseItemIEs RANAP-PROTOCOL-IES ::= {
--	{ ID id-RAB-ReleaseItem				CRITICALITY ignore	TYPE RAB-ReleaseItem				PRESENCE mandatory	},
--	...
--}

RAB-ReleaseItem ::= SEQUENCE {
	rAB-ID						RAB-ID,
	cause						Cause,
--	iE-Extensions					ProtocolExtensionContainer { {RAB-ReleaseItem-ExtIEs} }			OPTIONAL,
	iE-Extensions					ProtocolExtensionContainer OPTIONAL,
	...
}

--RAB-ReleaseItem-ExtIEs RANAP-PROTOCOL-EXTENSION ::= {
--	...
--}

--RAB-ReleaseRequestExtensions RANAP-PROTOCOL-EXTENSION ::= {
--	...
--}

-- **************************************************************
--
-- Iu RELEASE REQUEST ELEMENTARY PROCEDURE
--
-- **************************************************************

-- **************************************************************
--
-- Iu Release Request
--
-- **************************************************************

--Iu-ReleaseRequest ::= SEQUENCE {
--	protocolIEs			ProtocolIE-Container       { {Iu-ReleaseRequestIEs} },
--	protocolExtensions		ProtocolExtensionContainer { {Iu-ReleaseRequestExtensions} }				OPTIONAL,
--	...
--}

Iu-ReleaseRequest ::= SEQUENCE {
	protocolIEs			ProtocolIE-Container,
	protocolExtensions		ProtocolExtensionContainer OPTIONAL,
	...
}

--Iu-ReleaseRequestIEs RANAP-PROTOCOL-IES ::= {
--	{ ID id-Cause					CRITICALITY ignore	TYPE Cause					PRESENCE mandatory	},
--	...
--}

--Iu-ReleaseRequestExtensions RANAP-PROTOCOL-EXTENSION ::= {
--	...
--}

-- **************************************************************
--
-- RELOCATION DETECT ELEMENTARY PROCEDURE
--
-- **************************************************************
-- **************************************************************
--
-- Relocation Detect
--
-- **************************************************************

--RelocationDetect ::= SEQUENCE {
--	protocolIEs			ProtocolIE-Container       { {RelocationDetectIEs} },
--	protocolExtensions		ProtocolExtensionContainer { {RelocationDetectExtensions} }				OPTIONAL,
--	...
--}
RelocationDetect ::= SEQUENCE {
	protocolIEs			ProtocolIE-Container,
	protocolExtensions		ProtocolExtensionContainer OPTIONAL,
	...
}

--RelocationDetectIEs RANAP-PROTOCOL-IES ::= {
--	...
--}

--RelocationDetectExtensions RANAP-PROTOCOL-EXTENSION ::= {
--	...
--}

-- **************************************************************
--
-- RELOCATION COMPLETE ELEMENTARY PROCEDURE
--
-- **************************************************************

-- **************************************************************
--
-- Relocation Complete
--
-- **************************************************************

--RelocationComplete ::= SEQUENCE {
--	protocolIEs			ProtocolIE-Container       { {RelocationCompleteIEs} },
--	protocolExtensions		ProtocolExtensionContainer { {RelocationCompleteExtensions} }				OPTIONAL,
--	...
--}
RelocationComplete ::= SEQUENCE {
	protocolIEs			ProtocolIE-Container,
	protocolExtensions		ProtocolExtensionContainer OPTIONAL,
	...
}

--RelocationCompleteIEs RANAP-PROTOCOL-IES ::= {
--	...
--}

--RelocationCompleteExtensions RANAP-PROTOCOL-EXTENSION ::= {
--	...
--}

-- **************************************************************
--
-- PAGING ELEMENTARY PROCEDURE
--
-- **************************************************************

-- **************************************************************
--
-- Paging
--
-- **************************************************************

--Paging ::= SEQUENCE {
--	protocolIEs			ProtocolIE-Container       { {PagingIEs} },
--	protocolExtensions		ProtocolExtensionContainer { {PagingExtensions} }					OPTIONAL,
--	...
--}
Paging ::= SEQUENCE {
	protocolIEs			ProtocolIE-Container,
	protocolExtensions		ProtocolExtensionContainer OPTIONAL,
	...
}

--PagingIEs RANAP-PROTOCOL-IES ::= {
--	{ ID id-CN-DomainIndicator			CRITICALITY ignore	TYPE CN-DomainIndicator				PRESENCE mandatory	} |
--	{ ID id-PermanentNAS-UE-ID 			CRITICALITY ignore	TYPE PermanentNAS-UE-ID				PRESENCE mandatory	} |
--	{ ID id-TemporaryUE-ID				CRITICALITY ignore	TYPE TemporaryUE-ID				PRESENCE optional	} |
--	{ ID id-PagingAreaID				CRITICALITY ignore	TYPE PagingAreaID				PRESENCE optional	} |
--	{ ID id-PagingCause				CRITICALITY ignore	TYPE PagingCause				PRESENCE optional	} |
--	{ ID id-NonSearchingIndication			CRITICALITY ignore	TYPE NonSearchingIndication			PRESENCE optional	} |
--	{ ID id-DRX-CycleLengthCoefficient				CRITICALITY ignore	TYPE DRX-CycleLengthCoefficient				PRESENCE optional	} ,
--	...
--}

--PagingExtensions RANAP-PROTOCOL-EXTENSION ::= {
-- Extension for Release 5 to enable NNSF 
--	{ ID id-GlobalCN-ID				CRITICALITY ignore	EXTENSION GlobalCN-ID				PRESENCE optional	} ,
--	...
--}

-- **************************************************************
--
-- COMMON ID ELEMENTARY PROCEDURE
--
-- **************************************************************

-- **************************************************************
--
-- Common ID
--
-- **************************************************************

--CommonID ::= SEQUENCE {
--	protocolIEs			ProtocolIE-Container       { {CommonID-IEs} },
--	protocolExtensions		ProtocolExtensionContainer { {CommonIDExtensions} }					OPTIONAL,
--	...
--}

CommonID ::= SEQUENCE {
	protocolIEs			ProtocolIE-Container,
	protocolExtensions		ProtocolExtensionContainer OPTIONAL,
	...
}

--CommonID-IEs RANAP-PROTOCOL-IES ::= {
--	{ ID id-PermanentNAS-UE-ID			CRITICALITY ignore	TYPE PermanentNAS-UE-ID				PRESENCE mandatory	},
--	...
--}

--CommonIDExtensions RANAP-PROTOCOL-EXTENSION ::= {
-- Extension for Release 5 to enable shared networks in connected mode 
--	{ ID id-SNA-Access-Information		CRITICALITY ignore	EXTENSION	SNA-Access-Information			PRESENCE optional		} |
-- Extension for Release 5 to enable specific behaviour by the RNC in relation with early UE handling 
--	{ ID id-UESBI-Iu	CRITICALITY ignore		EXTENSION UESBI-Iu	PRESENCE optional}|
-- Extension for Release 6 to indicate the selected plmn in GWCN configuration for network sharing non-supporting UEs --
--	{ ID id-SelectedPLMN-ID	 	CRITICALITY ignore	EXTENSION PLMNidentity		PRESENCE optional 	},
--	...
--}

-- **************************************************************
--
-- CN INVOKE TRACE ELEMENTARY PROCEDURE
--
-- *****************************************************

-- **************************************************************
--
-- CN Invoke Trace
--
-- **************************************************************

--CN-InvokeTrace ::= SEQUENCE {
--	protocolIEs			ProtocolIE-Container       { {CN-InvokeTraceIEs} },
--	protocolExtensions		ProtocolExtensionContainer { {CN-InvokeTraceExtensions} }				OPTIONAL,
--	...
--}
CN-InvokeTrace ::= SEQUENCE {
	protocolIEs			ProtocolIE-Container,
	protocolExtensions		ProtocolExtensionContainer OPTIONAL,
	...
}

--CN-InvokeTraceIEs RANAP-PROTOCOL-IES ::= {
--	{ ID id-TraceType 				CRITICALITY ignore	TYPE TraceType 					PRESENCE optional	} |
	-- This information is mandatory for GERAN Iu Mode, not applicable to UTRAN 
--	{ ID id-TraceReference				CRITICALITY ignore	TYPE TraceReference				PRESENCE mandatory	} |
--	{ ID id-TriggerID				CRITICALITY ignore	TYPE TriggerID					PRESENCE optional	} |
	-- This information is mandatory for GERAN Iu Mode, not applicable to UTRAN 
--	{ ID id-UE-ID					CRITICALITY ignore	TYPE UE-ID					PRESENCE optional	} |
	-- This information is mandatory for UTRAN, optional for GERAN Iu mode 
--	{ ID id-OMC-ID					CRITICALITY ignore	TYPE OMC-ID					PRESENCE optional	},
	-- This information is mandatory for GERAN Iu Mode, not applicable to UTRAN 
--	...
--}

--CN-InvokeTraceExtensions RANAP-PROTOCOL-EXTENSION ::= {
-- Extension for Release 6 to enable signalling based activation for Subscriber and Equipment Trace over Iu interface 
--	{ ID id-TracePropagationParameters		CRITICALITY ignore	EXTENSION TracePropagationParameters			PRESENCE optional	} ,
--	...
--}

-- **************************************************************
--
-- CN DEACTIVATE TRACE ELEMENTARY PROCEDURE
--
-- **************************************************************

-- **************************************************************
--
-- CN Deactivate Trace
--
-- **************************************************************

--CN-DeactivateTrace ::= SEQUENCE {
--	protocolIEs			ProtocolIE-Container       { {CN-DeactivateTraceIEs} },
--	protocolExtensions		ProtocolExtensionContainer { {CN-DeactivateTraceExtensions} }				OPTIONAL,
--	...
--}

CN-DeactivateTrace ::= SEQUENCE {
	protocolIEs			ProtocolIE-Container,
	protocolExtensions		ProtocolExtensionContainer OPTIONAL,
	...
}

--CN-DeactivateTraceIEs RANAP-PROTOCOL-IES ::= {
--	{ ID id-TraceReference				CRITICALITY ignore	TYPE TraceReference				PRESENCE mandatory } |
--	{ ID id-TriggerID				CRITICALITY ignore	TYPE TriggerID					PRESENCE optional },
	-- This information is optional for GERAN Iu Mode, not applicable to UTRAN 
--	...
--}

--CN-DeactivateTraceExtensions RANAP-PROTOCOL-EXTENSION ::= {
--	...
--}

-- **************************************************************
--
-- LOCATION REPORTING CONTROL ELEMENTARY PROCEDURE
--
-- **************************************************************

-- **************************************************************
--
-- Location Reporting Control
--
-- **************************************************************


--LocationReportingControl ::= SEQUENCE {
--	protocolIEs			ProtocolIE-Container       { {LocationReportingControlIEs} },
--	protocolExtensions		ProtocolExtensionContainer { {LocationReportingControlExtensions} }			OPTIONAL,
--	...
--}

LocationReportingControl ::= SEQUENCE {
	protocolIEs			ProtocolIE-Container,
	protocolExtensions		ProtocolExtensionContainer OPTIONAL,
	...
}

--LocationReportingControlIEs RANAP-PROTOCOL-IES ::= {
--	{ ID id-RequestType 				CRITICALITY ignore	TYPE RequestType 				PRESENCE mandatory	},
--	...
--}

--LocationReportingControlExtensions RANAP-PROTOCOL-EXTENSION ::= {
-- Extension for Release 4 to enhance the location request over Iu 
--	{ ID id-VerticalAccuracyCode 				CRITICALITY ignore	EXTENSION VerticalAccuracyCode 				PRESENCE optional	} |
-- Extension for Release 4 to enhance the location request over Iu
--	{ ID id-ResponseTime 				CRITICALITY ignore	EXTENSION ResponseTime 				PRESENCE optional	} |
-- Extension for Release 4 to enhance the location request over Iu 
--	{ ID id-PositioningPriority 				CRITICALITY ignore	EXTENSION PositioningPriority 				PRESENCE optional	} |
-- Extension for Release 4 to enhance the location request over Iu 
--	{ ID id-ClientType 				CRITICALITY ignore	EXTENSION ClientType 				PRESENCE optional	},
--	...
--}

-- **************************************************************
--
-- LOCATION REPORT ELEMENTARY PROCEDURE
--
-- **************************************************************

-- **************************************************************
--
-- Location Report
--
-- **************************************************************

--LocationReport ::= SEQUENCE {
--	protocolIEs			ProtocolIE-Container       { {LocationReportIEs} },
--	protocolExtensions		ProtocolExtensionContainer { {LocationReportExtensions} }				OPTIONAL,
--	...
--}

LocationReport ::= SEQUENCE {
	protocolIEs			ProtocolIE-Container,
	protocolExtensions		ProtocolExtensionContainer OPTIONAL,
	...
}

--LocationReportIEs RANAP-PROTOCOL-IES ::= {
--	{ ID id-AreaIdentity				CRITICALITY ignore	TYPE AreaIdentity				PRESENCE optional	} |
--	{ ID id-Cause					CRITICALITY ignore	TYPE Cause					PRESENCE optional	} |
--	{ ID id-RequestType 				CRITICALITY ignore	TYPE RequestType 				PRESENCE optional	}	,
--	...
--}

--LocationReportExtensions RANAP-PROTOCOL-EXTENSION ::= {
-- Extension for Release 4 to enable report of Last Known Service Area with its Age over Iu 
--	{ ID id-LastKnownServiceArea	CRITICALITY ignore	EXTENSION LastKnownServiceArea	PRESENCE optional} |
-- Extension for Release 5 to pass the positioning methods that have been used 
--	{ ID id-PositionData	CRITICALITY ignore		EXTENSION PositionData	PRESENCE optional}|
-- Extension for Release 5 to pass the positioning methods that have been used for GERAN Iu mode 
--	{ ID id-PositionDataSpecificToGERANIuMode		CRITICALITY ignore	EXTENSION PositionDataSpecificToGERANIuMode		PRESENCE optional	}|
	-- This extension is optional for GERAN Iu mode only, not applicable for UTRAN 
-- Extension for Release 6 to indicate whether the returned position estimate satisfies the requested accuracy or not --
--	{ ID id-AccuracyFulfilmentIndicator	CRITICALITY ignore	EXTENSION AccuracyFulfilmentIndicator	PRESENCE optional},
--	...
--}

-- **************************************************************
--
-- INITIAL UE MESSAGE ELEMENTARY PROCEDURE
--
-- **************************************************************

-- **************************************************************
--
-- Initial UE Message
--
-- **************************************************************

--InitialUE-Message ::= SEQUENCE {
--	protocolIEs			ProtocolIE-Container       { {InitialUE-MessageIEs} },
--	protocolExtensions		ProtocolExtensionContainer { {InitialUE-MessageExtensions} }				OPTIONAL,
--	...
--}

InitialUE-Message ::= SEQUENCE {
	protocolIEs			ProtocolIE-Container,
	protocolExtensions		ProtocolExtensionContainer OPTIONAL,
	...
}

--InitialUE-MessageIEs RANAP-PROTOCOL-IES ::= {
--	{ ID id-CN-DomainIndicator			CRITICALITY ignore	TYPE CN-DomainIndicator				PRESENCE mandatory	} |
--	{ ID id-LAI					CRITICALITY ignore	TYPE LAI					PRESENCE mandatory	} |
--	{ ID id-RAC					CRITICALITY ignore	TYPE RAC					PRESENCE conditional	
	-- This IE shall be present if the CN Domain Indicator IE is set to "PS domain" 											} |
--	{ ID id-SAI					CRITICALITY ignore	TYPE SAI					PRESENCE mandatory	} |
--	{ ID id-NAS-PDU					CRITICALITY ignore	TYPE NAS-PDU					PRESENCE mandatory	} |
--	{ ID id-IuSigConId				CRITICALITY ignore 	TYPE IuSignallingConnectionIdentifier  		PRESENCE mandatory 	} |
--	{ ID id-GlobalRNC-ID				CRITICALITY ignore	TYPE GlobalRNC-ID				PRESENCE mandatory 	},

--	...
--}

--InitialUE-MessageExtensions RANAP-PROTOCOL-EXTENSION ::= {
-- Extension for Release 5 to enable GERAN support over Iu-cs 
--	{ ID id-GERAN-Classmark					CRITICALITY ignore	EXTENSION GERAN-Classmark			PRESENCE optional	} |
-- Extension for Release 6 to convey the selected PLMN id in shared networks 
--	{ ID id-SelectedPLMN-ID	 				CRITICALITY ignore	EXTENSION PLMNidentity				PRESENCE optional 	} |
-- Extension for Release 6 to enable rerouting in MOCN configuration for network sharing non-supporting UEs 
--	{ ID id-PermanentNAS-UE-ID				CRITICALITY ignore	EXTENSION PermanentNAS-UE-ID		PRESENCE optional	} |
-- Extension for Release 6 to enable rerouting in MOCN configuration for network sharing non-supporting UEs 
--	{ ID id-NAS-SequenceNumber				CRITICALITY ignore	EXTENSION NAS-SequenceNumber		PRESENCE optional	} ,
--	...
--}

-- **************************************************************
--
-- DIRECT TRANSFER ELEMENTARY PROCEDURE
--
-- **************************************************************

-- **************************************************************
--
-- Direct Transfer
--
-- **************************************************************

--DirectTransfer ::= SEQUENCE {
--	protocolIEs			ProtocolIE-Container       { {DirectTransferIEs} },
--	protocolExtensions		ProtocolExtensionContainer { {DirectTransferExtensions} }				OPTIONAL,
--	...
--}

DirectTransfer ::= SEQUENCE {
	protocolIEs			ProtocolIE-Container,
	protocolExtensions		ProtocolExtensionContainer OPTIONAL,
	...
}

--DirectTransferIEs RANAP-PROTOCOL-IES ::= {
--	{ ID id-NAS-PDU					CRITICALITY ignore	TYPE NAS-PDU					PRESENCE mandatory	} |
--	{ ID id-LAI					CRITICALITY ignore	TYPE LAI					PRESENCE optional	} |
--	{ ID id-RAC					CRITICALITY ignore	TYPE RAC					PRESENCE optional	} |
--	{ ID id-SAI					CRITICALITY ignore	TYPE SAI					PRESENCE optional	} |
--	{ ID id-SAPI					CRITICALITY ignore	TYPE SAPI					PRESENCE optional	},
--	...
--}

--DirectTransferExtensions RANAP-PROTOCOL-EXTENSION ::= {
-- Extension for Release 6 to enable rerouting in MOCN configuration for network sharing non-supporting UEs 
--	{ ID id-RedirectionIndication			CRITICALITY ignore	EXTENSION RedirectionIndication					PRESENCE optional	}|
-- Extension for Release 6 to indicate the MOCN rerouting is completed 
--	{ ID id-RedirectionCompleted			CRITICALITY ignore	EXTENSION RedirectionCompleted					PRESENCE optional	},
--	...
--}

--RedirectionIndication ::= ProtocolIE-Container { {RedirectionIndication-IEs} }
RedirectionIndication ::= ProtocolIE-Container

--RedirectionIndication-IEs RANAP-PROTOCOL-IES ::= {
--	{	ID id-NAS-PDU				CRITICALITY ignore TYPE NAS-PDU				PRESENCE mandatory }|
--	{	ID id-RejectCauseValue		CRITICALITY ignore TYPE RejectCauseValue	PRESENCE mandatory}|
--	{	ID id-NAS-SequenceNumber	CRITICALITY ignore TYPE NAS-SequenceNumber	PRESENCE optional}|
--	{	ID id-PermanentNAS-UE-ID	CRITICALITY ignore TYPE PermanentNAS-UE-ID	PRESENCE optional},
--	...
--}

-- **************************************************************
--
-- OVERLOAD CONTROL ELEMENTARY PROCEDURE
--
-- **************************************************************

-- **************************************************************
--
-- Overload
--
-- **************************************************************

--Overload ::= SEQUENCE {
--	protocolIEs			ProtocolIE-Container       { {OverloadIEs} },
--	protocolExtensions		ProtocolExtensionContainer { {OverloadExtensions} }					OPTIONAL,
--	...
--}

Overload ::= SEQUENCE {
	protocolIEs			ProtocolIE-Container,
	protocolExtensions		ProtocolExtensionContainer OPTIONAL,
	...
}

--OverloadIEs RANAP-PROTOCOL-IES ::= {
--	{ ID id-NumberOfSteps				CRITICALITY ignore	TYPE NumberOfSteps				PRESENCE optional	} |
--	{ ID id-GlobalRNC-ID				CRITICALITY ignore	TYPE GlobalRNC-ID				PRESENCE optional	},
--	...
--}

--OverloadExtensions RANAP-PROTOCOL-EXTENSION ::= {
-- Extension for Release 99 to enable the indication to the RNC which CN domain is suffering the signalling traffic overload 
--	{ ID id-CN-DomainIndicator			CRITICALITY ignore	EXTENSION CN-DomainIndicator	PRESENCE optional	} |
-- Extension for Release 5 to enable NNSF
--	{ ID id-GlobalCN-ID					CRITICALITY ignore	EXTENSION GlobalCN-ID			PRESENCE optional	} ,
--	...
--}

-- **************************************************************
--
-- ERROR INDICATION ELEMENTARY PROCEDURE
--
-- **************************************************************

-- **************************************************************
--
-- Error Indication
--
-- **************************************************************

--ErrorIndication ::= SEQUENCE {
--	protocolIEs			ProtocolIE-Container       { {ErrorIndicationIEs} },
--	protocolExtensions		ProtocolExtensionContainer { {ErrorIndicationExtensions} }				OPTIONAL,
--	...
--}

ErrorIndication ::= SEQUENCE {
	protocolIEs			ProtocolIE-Container,
	protocolExtensions		ProtocolExtensionContainer OPTIONAL,
	...
}

--ErrorIndicationIEs RANAP-PROTOCOL-IES ::= {
--	{ ID id-Cause					CRITICALITY ignore	TYPE Cause					PRESENCE optional	} |
--	{ ID id-CriticalityDiagnostics			CRITICALITY ignore	TYPE CriticalityDiagnostics			PRESENCE optional	} |
--	{ ID id-CN-DomainIndicator			CRITICALITY ignore	TYPE CN-DomainIndicator				PRESENCE optional	} |
--	{ ID id-GlobalRNC-ID				CRITICALITY ignore	TYPE GlobalRNC-ID				PRESENCE optional	},
--	...
--}

--ErrorIndicationExtensions RANAP-PROTOCOL-EXTENSION ::= {
-- Extension for Release 4 
--	{ ID id-GlobalCN-ID				CRITICALITY ignore		EXTENSION GlobalCN-ID				PRESENCE optional},
--	...
--}

-- **************************************************************
--
-- SRNS DATA FORWARD ELEMENTARY PROCEDURE
--
-- **************************************************************

-- **************************************************************
--
-- SRNS Data Forward Command
--
-- **************************************************************

--SRNS-DataForwardCommand ::= SEQUENCE {
--	protocolIEs			ProtocolIE-Container       { {SRNS-DataForwardCommandIEs} },
--	protocolExtensions		ProtocolExtensionContainer { {SRNS-DataForwardCommandExtensions} }			OPTIONAL,
--	...
--}

SRNS-DataForwardCommand ::= SEQUENCE {
	protocolIEs			ProtocolIE-Container,
	protocolExtensions		ProtocolExtensionContainer OPTIONAL,
	...
}

--SRNS-DataForwardCommandIEs RANAP-PROTOCOL-IES ::= {
--	{ ID id-RAB-DataForwardingList			CRITICALITY ignore	TYPE RAB-DataForwardingList			PRESENCE optional	},
--	...
--}

--SRNS-DataForwardCommandExtensions RANAP-PROTOCOL-EXTENSION ::= {
--	...
--}

-- **************************************************************
--
-- FORWARD SRNS CONTEXT ELEMENTARY PROCEDURE
--
-- **************************************************************

-- **************************************************************
--
-- Forward SRNS Context
--
-- **************************************************************

--ForwardSRNS-Context ::= SEQUENCE {
--	protocolIEs			ProtocolIE-Container       { {ForwardSRNS-ContextIEs} },
--	protocolExtensions		ProtocolExtensionContainer { {ForwardSRNS-ContextExtensions} }				OPTIONAL,
--	...
--}

ForwardSRNS-Context ::= SEQUENCE {
	protocolIEs			ProtocolIE-Container,
	protocolExtensions		ProtocolExtensionContainer OPTIONAL,
	...
}

--ForwardSRNS-ContextIEs RANAP-PROTOCOL-IES ::= {
--	{ ID id-RAB-ContextList				CRITICALITY ignore	TYPE RAB-ContextList				PRESENCE mandatory	},
--	...
--}

--ForwardSRNS-ContextExtensions RANAP-PROTOCOL-EXTENSION ::= {
-- Extension for Release 5 to enable relocation of Source RNC PDCP context info 
--	{ ID id-SourceRNC-PDCP-context-info		CRITICALITY ignore	EXTENSION RRC-Container	PRESENCE optional},
--	...
--}

-- **************************************************************
--
-- RAB ASSIGNMENT ELEMENTARY PROCEDURE
--
-- **************************************************************

-- **************************************************************
--
-- RAB Assignment Request
--
-- **************************************************************

--RAB-AssignmentRequest ::= SEQUENCE {
--	protocolIEs			ProtocolIE-Container       { {RAB-AssignmentRequestIEs} },
--	protocolExtensions		ProtocolExtensionContainer { {RAB-AssignmentRequestExtensions} }			OPTIONAL,
--	...
--}

RAB-AssignmentRequest ::= SEQUENCE {
	protocolIEs			ProtocolIE-Container,
	protocolExtensions		ProtocolExtensionContainer OPTIONAL,
	...
}

--RAB-AssignmentRequestIEs RANAP-PROTOCOL-IES ::= {
--	{ ID id-RAB-SetupOrModifyList			CRITICALITY ignore	TYPE RAB-SetupOrModifyList			PRESENCE optional	} |
--	{ ID id-RAB-ReleaseList				CRITICALITY ignore	TYPE RAB-ReleaseList				PRESENCE optional	},
--	...
--}

--RAB-SetupOrModifyList 					::= RAB-IE-ContainerPairList { {RAB-SetupOrModifyItem-IEs} }
RAB-SetupOrModifyList 					::= RAB-IE-ContainerPairList 

--RAB-SetupOrModifyItem-IEs RANAP-PROTOCOL-IES-PAIR ::= {
--	{ ID id-RAB-SetupOrModifyItem			FIRST CRITICALITY  reject	FIRST TYPE  RAB-SetupOrModifyItemFirst
--	 						SECOND CRITICALITY ignore	SECOND TYPE RAB-SetupOrModifyItemSecond	
--																PRESENCE mandatory	},
--	...
--}

RAB-SetupOrModifyItemFirst ::= SEQUENCE {
	rAB-ID						RAB-ID,
	nAS-SynchronisationIndicator	NAS-SynchronisationIndicator	OPTIONAL,
	rAB-Parameters					RAB-Parameters		OPTIONAL,
	userPlaneInformation				UserPlaneInformation		OPTIONAL,
	transportLayerInformation				 TransportLayerInformation		OPTIONAL,
	service-Handover					Service-Handover			OPTIONAL,
--	iE-Extensions					ProtocolExtensionContainer { {RAB-SetupOrModifyItemFirst-ExtIEs} }			OPTIONAL,
	iE-Extensions					ProtocolExtensionContainer OPTIONAL,
	...
}

TransportLayerInformation ::= SEQUENCE {
	transportLayerAddress			TransportLayerAddress,
	iuTransportAssociation			IuTransportAssociation,
--	iE-Extensions					ProtocolExtensionContainer { {TransportLayerInformation-ExtIEs} }			OPTIONAL,
	iE-Extensions					ProtocolExtensionContainer	OPTIONAL,
	...
}

--TransportLayerInformation-ExtIEs RANAP-PROTOCOL-EXTENSION ::= {
--	...
--}

--RAB-SetupOrModifyItemFirst-ExtIEs RANAP-PROTOCOL-EXTENSION ::= {
--	...
--}

RAB-SetupOrModifyItemSecond ::= SEQUENCE {
	pDP-TypeInformation				PDP-TypeInformation 			OPTIONAL,
	dataVolumeReportingIndication			DataVolumeReportingIndication 	OPTIONAL,
	dl-GTP-PDU-SequenceNumber			DL-GTP-PDU-SequenceNumber 	OPTIONAL,
	ul-GTP-PDU-SequenceNumber			UL-GTP-PDU-SequenceNumber 	OPTIONAL,
	dl-N-PDU-SequenceNumber				DL-N-PDU-SequenceNumber 	OPTIONAL,
	ul-N-PDU-SequenceNumber				UL-N-PDU-SequenceNumber		OPTIONAL,
--	iE-Extensions					ProtocolExtensionContainer { {RAB-SetupOrModifyItemSecond-ExtIEs} }			OPTIONAL,
	iE-Extensions					ProtocolExtensionContainer OPTIONAL,
	...
}

--RAB-SetupOrModifyItemSecond-ExtIEs RANAP-PROTOCOL-EXTENSION ::= {
-- Extension for Release 4 to enable RAB Quality of Service negotiation over Iu 
--	{	ID id-Alt-RAB-Parameters	CRITICALITY ignore		EXTENSION Alt-RAB-Parameters		PRESENCE optional	} |
-- Extension for Release 5 to enable GERAN support over Iu-cs 
--	{ ID id-GERAN-BSC-Container					CRITICALITY ignore	EXTENSION GERAN-BSC-Container			PRESENCE optional	} ,
--	...
--}

--RAB-AssignmentRequestExtensions RANAP-PROTOCOL-EXTENSION ::= {
--	...
--}

-- **************************************************************
--
-- RAB Assignment Response
--
-- **************************************************************

--RAB-AssignmentResponse ::= SEQUENCE {
--	protocolIEs			ProtocolIE-Container       { {RAB-AssignmentResponseIEs} },
--	protocolExtensions		ProtocolExtensionContainer { {RAB-AssignmentResponseExtensions} }			OPTIONAL,
--	...
--}
RAB-AssignmentResponse ::= SEQUENCE {
	protocolIEs			ProtocolIE-Container,
	protocolExtensions		ProtocolExtensionContainer OPTIONAL,
	...
}

--RAB-AssignmentResponseIEs RANAP-PROTOCOL-IES ::= {
--	{ ID id-RAB-SetupOrModifiedList			CRITICALITY ignore	TYPE RAB-SetupOrModifiedList			PRESENCE optional	} |
--	{ ID id-RAB-ReleasedList			CRITICALITY ignore	TYPE RAB-ReleasedList				PRESENCE optional	} |
	
--	{ ID id-RAB-QueuedList				CRITICALITY ignore	TYPE RAB-QueuedList				PRESENCE optional	} |
--	{ ID id-RAB-FailedList				CRITICALITY ignore	TYPE RAB-FailedList				PRESENCE optional	} |
--	{ ID id-RAB-ReleaseFailedList			CRITICALITY ignore	TYPE RAB-ReleaseFailedList			PRESENCE optional	} |
--	{ ID id-CriticalityDiagnostics			CRITICALITY ignore	TYPE CriticalityDiagnostics		PRESENCE optional },
--	...
--}

--RAB-SetupOrModifiedList 				::= RAB-IE-ContainerList { {RAB-SetupOrModifiedItemIEs} }
RAB-SetupOrModifiedList 				::= RAB-IE-ContainerList

--RAB-SetupOrModifiedItemIEs RANAP-PROTOCOL-IES ::= {
--	{ ID id-RAB-SetupOrModifiedItem			CRITICALITY ignore	TYPE RAB-SetupOrModifiedItem			PRESENCE mandatory	},
--	...
--}

RAB-SetupOrModifiedItem ::= SEQUENCE {
	rAB-ID						RAB-ID,
	transportLayerAddress				TransportLayerAddress	OPTIONAL,
	iuTransportAssociation				IuTransportAssociation	OPTIONAL,
	dl-dataVolumes					DataVolumeList		OPTIONAL,
--	iE-Extensions					ProtocolExtensionContainer { {RAB-SetupOrModifiedItem-ExtIEs} }			OPTIONAL,
	iE-Extensions					ProtocolExtensionContainer OPTIONAL,
	...
}

--RAB-SetupOrModifiedItem-ExtIEs RANAP-PROTOCOL-EXTENSION ::= {
-- Extension for Release 4 to enable RAB Quality of Service negotiation over Iu 
--	{	ID id-Ass-RAB-Parameters	CRITICALITY ignore		EXTENSION Ass-RAB-Parameters		PRESENCE optional	},
--	...
--}

--RAB-ReleasedList 					::= RAB-IE-ContainerList { {RAB-ReleasedItemIEs} }
RAB-ReleasedList 					::= RAB-IE-ContainerList

--RAB-ReleasedItemIEs RANAP-PROTOCOL-IES ::= {
--	{ ID id-RAB-ReleasedItem			CRITICALITY ignore	TYPE RAB-ReleasedItem				PRESENCE mandatory	},
--	...
--}

RAB-ReleasedItem ::= SEQUENCE {
	rAB-ID						RAB-ID,
	dl-dataVolumes					DataVolumeList		OPTIONAL,
	dL-GTP-PDU-SequenceNumber		DL-GTP-PDU-SequenceNumber			OPTIONAL,
	uL-GTP-PDU-SequenceNumber		UL-GTP-PDU-SequenceNumber			OPTIONAL,
--	iE-Extensions					ProtocolExtensionContainer { {RAB-ReleasedItem-ExtIEs} }			OPTIONAL,
	iE-Extensions					ProtocolExtensionContainer OPTIONAL,
	...
}

--RAB-ReleasedItem-ExtIEs RANAP-PROTOCOL-EXTENSION ::= {
--	...
--}

DataVolumeList ::= SEQUENCE (SIZE (1..2)) OF
	SEQUENCE {
		dl-UnsuccessfullyTransmittedDataVolume		UnsuccessfullyTransmittedDataVolume,
		dataVolumeReference				DataVolumeReference	OPTIONAL,
--		iE-Extensions					ProtocolExtensionContainer { {DataVolumeList-ExtIEs} }			OPTIONAL,
		iE-Extensions					ProtocolExtensionContainer OPTIONAL,
		...
	}

--DataVolumeList-ExtIEs RANAP-PROTOCOL-EXTENSION ::= {
--	...
--}

--RAB-QueuedList 						::= RAB-IE-ContainerList { {RAB-QueuedItemIEs} }
RAB-QueuedList 						::= RAB-IE-ContainerList 

--RAB-QueuedItemIEs RANAP-PROTOCOL-IES ::= {
--	{ ID id-RAB-QueuedItem				CRITICALITY ignore	TYPE RAB-QueuedItem				PRESENCE mandatory	},
--	...
--}

RAB-QueuedItem ::= SEQUENCE {
	rAB-ID						RAB-ID,
--	iE-Extensions					ProtocolExtensionContainer { {RAB-QueuedItem-ExtIEs} }			OPTIONAL,
	iE-Extensions					ProtocolExtensionContainer OPTIONAL,
	...
}

--RAB-QueuedItem-ExtIEs RANAP-PROTOCOL-EXTENSION ::= {
--	...
--}

RAB-ReleaseFailedList ::= RAB-FailedList

--RAB-AssignmentResponseExtensions RANAP-PROTOCOL-EXTENSION ::= {
-- Extension for Release 5 to enable GERAN support over Iu-cs 
--	{ ID id-GERAN-Iumode-RAB-FailedList-RABAssgntResponse		CRITICALITY ignore	EXTENSION GERAN-Iumode-RAB-FailedList-RABAssgntResponse			PRESENCE optional} ,
--	...
--}

--GERAN-Iumode-RAB-FailedList-RABAssgntResponse		::= RAB-IE-ContainerList { {GERAN-Iumode-RAB-Failed-RABAssgntResponse-ItemIEs} }
GERAN-Iumode-RAB-FailedList-RABAssgntResponse		::= RAB-IE-ContainerList

--GERAN-Iumode-RAB-Failed-RABAssgntResponse-ItemIEs RANAP-PROTOCOL-IES ::= {
--	{ ID id-GERAN-Iumode-RAB-Failed-RABAssgntResponse-Item		CRITICALITY ignore	TYPE GERAN-Iumode-RAB-Failed-RABAssgntResponse-Item			PRESENCE mandatory	},
--	...
--}

GERAN-Iumode-RAB-Failed-RABAssgntResponse-Item ::= SEQUENCE {
	rAB-ID						RAB-ID,
	cause						Cause,
	gERAN-Classmark				GERAN-Classmark		OPTIONAL,
--	iE-Extensions				ProtocolExtensionContainer { {GERAN-Iumode-RAB-Failed-RABAssgntResponse-Item-ExtIEs} }			OPTIONAL,
	iE-Extensions				ProtocolExtensionContainer OPTIONAL,
	...
}

--GERAN-Iumode-RAB-Failed-RABAssgntResponse-Item-ExtIEs RANAP-PROTOCOL-EXTENSION ::= {
--	...
--}

-- **************************************************************
--
-- PRIVATE MESSAGE
--
-- **************************************************************

-- **************************************************************
--
-- PRIVATE MESSAGE
--
-- **************************************************************

--PrivateMessage ::= SEQUENCE {
--	privateIEs		PrivateIE-Container  { {PrivateMessage-IEs } },
--	...
--}
PrivateMessage ::= SEQUENCE {
	privateIEs		PrivateIE-Container,
	...
}

--PrivateMessage-IEs RANAP-PRIVATE-IES ::= {
--	...
--}

-- **************************************************************
--
-- RANAP RELOCATION INFORMATION ELEMENTARY PROCEDURE
--
-- **************************************************************

--RANAP-RelocationInformation ::= SEQUENCE {
--	protocolIEs			ProtocolIE-Container       { {RANAP-RelocationInformationIEs} },
--	protocolExtensions		ProtocolExtensionContainer { {RANAP-RelocationInformationExtensions} }			OPTIONAL,
--	...
--}

RANAP-RelocationInformation ::= SEQUENCE {
	protocolIEs			ProtocolIE-Container,
	protocolExtensions		ProtocolExtensionContainer OPTIONAL,
	...
}

--RANAP-RelocationInformationIEs RANAP-PROTOCOL-IES ::= {
--	{ ID id-DirectTransferInformationList-RANAP-RelocInf	
--							CRITICALITY ignore	TYPE DirectTransferInformationList-RANAP-RelocInf		
--																PRESENCE optional	} |
--	{ ID id-RAB-ContextList-RANAP-RelocInf		CRITICALITY ignore	TYPE RAB-ContextList-RANAP-RelocInf		PRESENCE optional	},
--	...
--}

--DirectTransferInformationList-RANAP-RelocInf		::= DirectTransfer-IE-ContainerList { {DirectTransferInformationItemIEs-RANAP-RelocInf} }
DirectTransferInformationList-RANAP-RelocInf		::= DirectTransfer-IE-ContainerList

--DirectTransferInformationItemIEs-RANAP-RelocInf RANAP-PROTOCOL-IES ::= {
--	{ ID id-DirectTransferInformationItem-RANAP-RelocInf
--							CRITICALITY ignore	TYPE DirectTransferInformationItem-RANAP-RelocInf
--																PRESENCE mandatory	},
--	...
--}

DirectTransferInformationItem-RANAP-RelocInf ::= SEQUENCE {
	nAS-PDU						NAS-PDU,
	sAPI						SAPI,
	cN-DomainIndicator			CN-DomainIndicator,
--	iE-Extensions					ProtocolExtensionContainer { {RANAP-DirectTransferInformationItem-ExtIEs-RANAP-RelocInf} }			OPTIONAL,
	iE-Extensions					ProtocolExtensionContainer OPTIONAL,
	...
}

--RANAP-DirectTransferInformationItem-ExtIEs-RANAP-RelocInf RANAP-PROTOCOL-EXTENSION ::= {
--	...
--}

--RAB-ContextList-RANAP-RelocInf 				::= RAB-IE-ContainerList { {RAB-ContextItemIEs-RANAP-RelocInf} }
RAB-ContextList-RANAP-RelocInf 				::= RAB-IE-ContainerList

--RAB-ContextItemIEs-RANAP-RelocInf RANAP-PROTOCOL-IES ::= {
--	{ ID id-RAB-ContextItem-RANAP-RelocInf		CRITICALITY ignore	TYPE RAB-ContextItem-RANAP-RelocInf			PRESENCE mandatory	},
--	...
--}

RAB-ContextItem-RANAP-RelocInf ::= SEQUENCE {
	rAB-ID				RAB-ID,
	dl-GTP-PDU-SequenceNumber			DL-GTP-PDU-SequenceNumber 	OPTIONAL,
	ul-GTP-PDU-SequenceNumber			UL-GTP-PDU-SequenceNumber 	OPTIONAL,
	dl-N-PDU-SequenceNumber				DL-N-PDU-SequenceNumber		OPTIONAL,
	ul-N-PDU-SequenceNumber				UL-N-PDU-SequenceNumber		OPTIONAL,
--	iE-Extensions					ProtocolExtensionContainer { {RAB-ContextItem-ExtIEs-RANAP-RelocInf} }			OPTIONAL,
	iE-Extensions					ProtocolExtensionContainer OPTIONAL,
	...
}

--RAB-ContextItem-ExtIEs-RANAP-RelocInf RANAP-PROTOCOL-EXTENSION ::= {
--	...
--}

--RANAP-RelocationInformationExtensions RANAP-PROTOCOL-EXTENSION ::= {
-- Extension for Release 5 to enable relocation of Source RNC PDCP context info 
--	{ ID id-SourceRNC-PDCP-context-info		CRITICALITY ignore	EXTENSION RRC-Container	PRESENCE optional},
--	...
--}

-- **************************************************************
--
-- RAB MODIFICATION REQUEST ELEMENTARY PROCEDURE
--
-- **************************************************************

-- **************************************************************
--
-- RAB Modify Request
--
-- **************************************************************

--RAB-ModifyRequest ::= SEQUENCE {
--	protocolIEs			ProtocolIE-Container       { {RAB-ModifyRequestIEs} },
--	protocolExtensions		ProtocolExtensionContainer { {RAB-ModifyRequestExtensions} }				OPTIONAL,
--	...
--}
RAB-ModifyRequest ::= SEQUENCE {
	protocolIEs			ProtocolIE-Container,
	protocolExtensions		ProtocolExtensionContainer OPTIONAL,
	...
}

--RAB-ModifyRequestIEs RANAP-PROTOCOL-IES ::= {
--	{ ID id-RAB-ModifyList			CRITICALITY ignore	TYPE RAB-ModifyList			PRESENCE mandatory},
--	...
--}

--RAB-ModifyList 			::= RAB-IE-ContainerList { {RAB-ModifyItemIEs} }
RAB-ModifyList 			::= RAB-IE-ContainerList

--RAB-ModifyItemIEs RANAP-PROTOCOL-IES ::= {
--	{ ID id-RAB-ModifyItem		CRITICALITY ignore	TYPE RAB-ModifyItem		PRESENCE mandatory	},
--	...
--}

RAB-ModifyItem ::= SEQUENCE {
	rAB-ID						RAB-ID,
	requested-RAB-Parameter-Values	Requested-RAB-Parameter-Values,
--	iE-Extensions					ProtocolExtensionContainer { {RAB-ModifyItem-ExtIEs} }			OPTIONAL,
	iE-Extensions					ProtocolExtensionContainer OPTIONAL,
	...
}

--RAB-ModifyItem-ExtIEs RANAP-PROTOCOL-EXTENSION ::= {
--	...
--}

--RAB-ModifyRequestExtensions RANAP-PROTOCOL-EXTENSION ::= {
--	...
--}

-- **************************************************************
--
-- LOCATION RELATED DATA ELEMENTARY PROCEDURE
--
-- **************************************************************

-- **************************************************************
--
-- Location Related Data Request
--
-- **************************************************************

--LocationRelatedDataRequest ::= SEQUENCE {
--	protocolIEs			ProtocolIE-Container       { {LocationRelatedDataRequestIEs} },
--	protocolExtensions		ProtocolExtensionContainer { {LocationRelatedDataRequestExtensions} }				OPTIONAL,
--	...
--}

LocationRelatedDataRequest ::= SEQUENCE {
	protocolIEs			ProtocolIE-Container,
	protocolExtensions		ProtocolExtensionContainer OPTIONAL,
	...
}

--LocationRelatedDataRequestIEs RANAP-PROTOCOL-IES ::= {
--	{ ID id-LocationRelatedDataRequestType		CRITICALITY reject	TYPE LocationRelatedDataRequestType		PRESENCE optional	},
	-- This IE is mandatory for UTRAN, optional for GERAN Iu Mode 
--	...
--}

--LocationRelatedDataRequestExtensions RANAP-PROTOCOL-EXTENSION ::= {
-- Extension for Release 5 to enable LCS support for GERAN Iu mode 
--	{ ID id-LocationRelatedDataRequestTypeSpecificToGERANIuMode		CRITICALITY reject	EXTENSION LocationRelatedDataRequestTypeSpecificToGERANIuMode		PRESENCE optional	},
	-- This extension is optional for GERAN Iu Mode only, not applicable for UTRAN 
--	...
--}

-- **************************************************************
--
-- Location Related Data Response
--
-- **************************************************************

--LocationRelatedDataResponse ::= SEQUENCE {
--	protocolIEs			ProtocolIE-Container       { { LocationRelatedDataResponseIEs} },
--	protocolExtensions		ProtocolExtensionContainer { { LocationRelatedDataResponseExtensions} }				OPTIONAL,
--	...
--}
LocationRelatedDataResponse ::= SEQUENCE {
	protocolIEs			ProtocolIE-Container,
	protocolExtensions		ProtocolExtensionContainer OPTIONAL,
	...
}

--LocationRelatedDataResponseIEs RANAP-PROTOCOL-IES ::= {
--	{ ID id-BroadcastAssistanceDataDecipheringKeys		CRITICALITY ignore	TYPE BroadcastAssistanceDataDecipheringKeys		PRESENCE optional	},
--	...
--}

--LocationRelatedDataResponseExtensions RANAP-PROTOCOL-EXTENSION ::= {
-- Extension for error handling
--	{ ID id-CriticalityDiagnostics			CRITICALITY ignore	EXTENSION CriticalityDiagnostics			PRESENCE optional	},
--	...
--}

-- **************************************************************
--
-- Location Related Data Failure
--
-- **************************************************************

--LocationRelatedDataFailure ::= SEQUENCE {
--	protocolIEs			ProtocolIE-Container       { { LocationRelatedDataFailureIEs} },
--	protocolExtensions		ProtocolExtensionContainer { { LocationRelatedDataFailureExtensions} }				OPTIONAL,
--	...
--}
LocationRelatedDataFailure ::= SEQUENCE {
	protocolIEs			ProtocolIE-Container,
	protocolExtensions		ProtocolExtensionContainer OPTIONAL,
	...
}

--LocationRelatedDataFailureIEs RANAP-PROTOCOL-IES ::= {
--	{ ID id-Cause				CRITICALITY ignore	TYPE Cause					PRESENCE mandatory	},
--	...
--}

--LocationRelatedDataFailureExtensions RANAP-PROTOCOL-EXTENSION ::= {
-- Extension for error handling
--	{ ID id-CriticalityDiagnostics		CRITICALITY ignore	EXTENSION CriticalityDiagnostics		PRESENCE optional	},
--	...
--}

-- **************************************************************
--
-- INFORMATION TRANSFER ELEMENTARY PROCEDURE
--
-- **************************************************************

-- **************************************************************
--
-- Information Transfer Indication
--
-- **************************************************************

--InformationTransferIndication ::= SEQUENCE {
--	protocolIEs			ProtocolIE-Container       { { InformationTransferIndicationIEs} },
--	protocolExtensions		ProtocolExtensionContainer { { InformationTransferIndicationExtensions} }				OPTIONAL,
--	...
--}
InformationTransferIndication ::= SEQUENCE {
	protocolIEs			ProtocolIE-Container,
	protocolExtensions		ProtocolExtensionContainer OPTIONAL,
	...
}

--InformationTransferIndicationIEs RANAP-PROTOCOL-IES ::= {
--	{ ID id-InformationTransferID		CRITICALITY reject	TYPE InformationTransferID		PRESENCE mandatory	} |
--	{ ID id-ProvidedData				CRITICALITY reject	TYPE ProvidedData				PRESENCE mandatory	} |
--	{ ID id-CN-DomainIndicator			CRITICALITY reject	TYPE CN-DomainIndicator			PRESENCE mandatory	} |
--	{ ID id-GlobalCN-ID					CRITICALITY ignore	TYPE GlobalCN-ID				PRESENCE optional},
--	...
--}

--InformationTransferIndicationExtensions RANAP-PROTOCOL-EXTENSION ::= {
--	...
--}

-- **************************************************************
--
-- Information Transfer Confirmation
--
-- **************************************************************

--InformationTransferConfirmation ::= SEQUENCE {
--	protocolIEs			ProtocolIE-Container       { { InformationTransferConfirmationIEs} },
--	protocolExtensions		ProtocolExtensionContainer { { InformationTransferConfirmationExtensions} }				OPTIONAL,
--	...
--}
InformationTransferConfirmation ::= SEQUENCE {
	protocolIEs			ProtocolIE-Container,
	protocolExtensions		ProtocolExtensionContainer OPTIONAL,
	...
}

--InformationTransferConfirmationIEs RANAP-PROTOCOL-IES ::= {
--	{ ID id-InformationTransferID		CRITICALITY ignore	TYPE InformationTransferID		PRESENCE mandatory	} |
--	{ ID id-CN-DomainIndicator			CRITICALITY ignore	TYPE CN-DomainIndicator			PRESENCE mandatory	} |
--	{ ID id-CriticalityDiagnostics		CRITICALITY ignore	TYPE CriticalityDiagnostics		PRESENCE optional 	} |
--	{ ID id-GlobalRNC-ID				CRITICALITY ignore	TYPE GlobalRNC-ID				PRESENCE mandatory	},
--	...
--}

--InformationTransferConfirmationExtensions RANAP-PROTOCOL-EXTENSION ::= {
--	...
--}

-- **************************************************************
--
-- Information Transfer Failure
--
-- **************************************************************

--InformationTransferFailure ::= SEQUENCE {
--	protocolIEs			ProtocolIE-Container       { { InformationTransferFailureIEs} },
--	protocolExtensions		ProtocolExtensionContainer { { InformationTransferFailureExtensions} }				OPTIONAL,
--	...
--}

InformationTransferFailure ::= SEQUENCE {
	protocolIEs			ProtocolIE-Container,
	protocolExtensions		ProtocolExtensionContainer OPTIONAL,
	...
}

--InformationTransferFailureIEs RANAP-PROTOCOL-IES ::= {
--	{ ID id-InformationTransferID		CRITICALITY ignore	TYPE InformationTransferID		PRESENCE mandatory	} |
--	{ ID id-CN-DomainIndicator			CRITICALITY ignore	TYPE CN-DomainIndicator			PRESENCE mandatory	} |
--	{ ID id-Cause						CRITICALITY ignore	TYPE Cause						PRESENCE mandatory	} |
--	{ ID id-CriticalityDiagnostics		CRITICALITY ignore	TYPE CriticalityDiagnostics		PRESENCE optional 	} |
--	{ ID id-GlobalRNC-ID				CRITICALITY ignore	TYPE GlobalRNC-ID				PRESENCE mandatory	},
--	...
--}

--InformationTransferFailureExtensions RANAP-PROTOCOL-EXTENSION ::= {
--	...
--}

-- **************************************************************
--
-- UE SPECIFIC INFORMATION ELEMENTARY PROCEDURE
--
-- **************************************************************

-- **************************************************************
--
-- UE Specific Information Indication
--
-- **************************************************************

--UESpecificInformationIndication ::= SEQUENCE {
--	protocolIEs			ProtocolIE-Container       { {UESpecificInformationIndicationIEs} },
--	protocolExtensions		ProtocolExtensionContainer { {UESpecificInformationIndicationExtensions} }					OPTIONAL,
--	...
--}

UESpecificInformationIndication ::= SEQUENCE {
	protocolIEs			ProtocolIE-Container,
	protocolExtensions		ProtocolExtensionContainer OPTIONAL,
	...
}

--UESpecificInformationIndicationIEs RANAP-PROTOCOL-IES ::= {
--	{ ID id-UESBI-Iu				CRITICALITY ignore	TYPE UESBI-Iu				PRESENCE optional	},
--	...
--}

--UESpecificInformationIndicationExtensions RANAP-PROTOCOL-EXTENSION ::= {
--	...
--}

-- **************************************************************
--
-- DIRECT INFORMATION TRANSFER ELEMENTARY PROCEDURE
--
-- **************************************************************

-- **************************************************************
--
-- Direct Information Transfer
--
-- **************************************************************

--DirectInformationTransfer ::= SEQUENCE {
--	protocolIEs			ProtocolIE-Container       { { DirectInformationTransferIEs} },
--	protocolExtensions		ProtocolExtensionContainer { { DirectInformationTransferExtensions} }				OPTIONAL,
--	...
--}

DirectInformationTransfer ::= SEQUENCE {
	protocolIEs			ProtocolIE-Container,
	protocolExtensions		ProtocolExtensionContainer OPTIONAL,
	...
}

--DirectInformationTransferIEs RANAP-PROTOCOL-IES ::= {
--	{ ID id-InterSystemInformationTransferType		CRITICALITY ignore	TYPE InterSystemInformationTransferType		PRESENCE optional	}	|
--	{ ID id-CN-DomainIndicator			CRITICALITY ignore	TYPE CN-DomainIndicator				PRESENCE mandatory	} |
--	{ ID id-GlobalRNC-ID 			CRITICALITY ignore	TYPE GlobalRNC-ID				PRESENCE optional	} |
--	{ ID id-GlobalCN-ID 			CRITICALITY ignore	TYPE GlobalCN-ID				PRESENCE optional	},
--	...
--}

--DirectInformationTransferExtensions RANAP-PROTOCOL-EXTENSION ::= {
--	...
--}

-- **************************************************************
--
-- UPLINK INFORMATION EXCHANGE ELEMENTARY PROCEDURE
--
-- **************************************************************

-- **************************************************************
--
-- Uplink Information Exchange Request
--
-- **************************************************************

--UplinkInformationExchangeRequest ::= SEQUENCE {
--	protocolIEs				ProtocolIE-Container		{ { UplinkInformationExchangeRequestIEs} },
--	protocolExtensions		ProtocolExtensionContainer	{ { UplinkInformationExchangeRequestExtensions} }			OPTIONAL,
--	...
--}

UplinkInformationExchangeRequest ::= SEQUENCE {
	protocolIEs				ProtocolIE-Container,
	protocolExtensions		ProtocolExtensionContainer OPTIONAL,
	...
}

--UplinkInformationExchangeRequestIEs RANAP-PROTOCOL-IES ::= {
--	{ ID id-InformationExchangeID		CRITICALITY reject	TYPE InformationExchangeID		PRESENCE mandatory	} |
--	{ ID id-InformationExchangeType		CRITICALITY reject	TYPE InformationExchangeType	PRESENCE mandatory	} |
--	{ ID id-InformationTransferType		CRITICALITY reject	TYPE InformationTransferType	PRESENCE conditional	
	-- This IE shall be present if the Information Exchange Type IE is set to "transfer"  											} |
--	{ ID id-InformationRequestType		CRITICALITY reject	TYPE InformationRequestType	PRESENCE conditional	
	-- This IE shall be present if the Information Exchange Type IE is set to "request"  											} |
--	{ ID id-CN-DomainIndicator			CRITICALITY reject	TYPE CN-DomainIndicator			PRESENCE mandatory	} |
--	{ ID id-GlobalRNC-ID				CRITICALITY reject	TYPE GlobalRNC-ID				PRESENCE mandatory	},
--	...
--}

--UplinkInformationExchangeRequestExtensions RANAP-PROTOCOL-EXTENSION ::= {
--	...
--}

-- **************************************************************
--
-- Uplink Information Exchange Response
--
-- **************************************************************

--UplinkInformationExchangeResponse ::= SEQUENCE {
--	protocolIEs				ProtocolIE-Container		{ { UplinkInformationExchangeResponseIEs} },
--	protocolExtensions		ProtocolExtensionContainer	{ { UplinkInformationExchangeResponseExtensions} }		OPTIONAL,
--	...
--}

UplinkInformationExchangeResponse ::= SEQUENCE {
	protocolIEs				ProtocolIE-Container,
	protocolExtensions		ProtocolExtensionContainer	OPTIONAL,
	...
}

--UplinkInformationExchangeResponseIEs RANAP-PROTOCOL-IES ::= {
--	{ ID id-InformationExchangeID		CRITICALITY ignore	TYPE InformationExchangeID		PRESENCE mandatory	} |
--	{ ID id-InformationRequested		CRITICALITY ignore	TYPE InformationRequested		PRESENCE optional		} |
--	{ ID id-CN-DomainIndicator			CRITICALITY ignore	TYPE CN-DomainIndicator			PRESENCE mandatory	} |
--	{ ID id-GlobalCN-ID					CRITICALITY ignore	TYPE GlobalCN-ID				PRESENCE optional		} |
--	{ ID id-CriticalityDiagnostics		CRITICALITY ignore	TYPE CriticalityDiagnostics		PRESENCE optional		} ,
--	...
--}

--UplinkInformationExchangeResponseExtensions RANAP-PROTOCOL-EXTENSION ::= {
--	...
--}

-- **************************************************************
--
-- Uplink Information Exchange Failure
--
-- **************************************************************

--UplinkInformationExchangeFailure ::= SEQUENCE {
--	protocolIEs			ProtocolIE-Container       { { UplinkInformationExchangeFailureIEs} },
--	protocolExtensions		ProtocolExtensionContainer { { UplinkInformationExchangeFailureExtensions} }				OPTIONAL,
--	...
--}
UplinkInformationExchangeFailure ::= SEQUENCE {
	protocolIEs			ProtocolIE-Container,
	protocolExtensions		ProtocolExtensionContainer OPTIONAL,
	...
}

--UplinkInformationExchangeFailureIEs RANAP-PROTOCOL-IES ::= {
--	{ ID id-InformationExchangeID		CRITICALITY ignore	TYPE InformationExchangeID		PRESENCE mandatory	} |
--	{ ID id-CN-DomainIndicator			CRITICALITY ignore	TYPE CN-DomainIndicator			PRESENCE mandatory	} |
--	{ ID id-GlobalCN-ID					CRITICALITY ignore	TYPE GlobalCN-ID				PRESENCE optional		} |
--	{ ID id-Cause						CRITICALITY ignore	TYPE Cause						PRESENCE mandatory	} |
--	{ ID id-CriticalityDiagnostics		CRITICALITY ignore	TYPE CriticalityDiagnostics		PRESENCE optional		} ,
--	...
--}

--UplinkInformationExchangeFailureExtensions RANAP-PROTOCOL-EXTENSION ::= {
--	...
--}

-- **************************************************************
--
-- MBMS SESSION START PROCEDURE
--
-- **************************************************************

-- **************************************************************
--
-- MBMS Session Start
--
-- **************************************************************

--MBMSSessionStart ::= SEQUENCE {
--	protocolIEs				ProtocolIE-Container		{ { MBMSSessionStartIEs} },
--	protocolExtensions		ProtocolExtensionContainer	{ { MBMSSessionStartExtensions} }			OPTIONAL,
--	...
--}

MBMSSessionStart ::= SEQUENCE {
	protocolIEs				ProtocolIE-Container,
	protocolExtensions		ProtocolExtensionContainer	OPTIONAL,
	...
}

--MBMSSessionStartIEs RANAP-PROTOCOL-IES ::= {
--	{ ID id-TMGI						CRITICALITY reject	TYPE TMGI									PRESENCE mandatory	} |
--	{ ID id-MBMSSessionIdentity		CRITICALITY ignore	TYPE MBMSSessionIdentity					PRESENCE optional	} |
--	{ ID id-MBMSBearerServiceType		CRITICALITY reject	TYPE MBMSBearerServiceType					PRESENCE mandatory	} |
--	{ ID id-IuSigConId					CRITICALITY reject 	TYPE IuSignallingConnectionIdentifier  	PRESENCE mandatory	}|
--	{ ID id-RAB-Parameters				CRITICALITY reject 	TYPE RAB-Parameters							PRESENCE mandatory	} |
--	{ ID id-PDP-TypeInformation			CRITICALITY ignore	TYPE PDP-TypeInformation					PRESENCE optional		} |
--	{ ID id-MBMSSessionDuration			CRITICALITY reject	TYPE MBMSSessionDuration					PRESENCE mandatory		} |
--	{ ID id-MBMSServiceArea				CRITICALITY reject	TYPE MBMSServiceArea						PRESENCE mandatory	} |
--	{ ID id-FrequenceLayerConvergenceFlag	CRITICALITY ignore	TYPE FrequenceLayerConvergenceFlag	PRESENCE optional		} |
--	{ ID id-RAListofIdleModeUEs			CRITICALITY ignore	TYPE RAListofIdleModeUEs					PRESENCE optional		} |
--	{ ID id-GlobalCN-ID					CRITICALITY reject	TYPE GlobalCN-ID							PRESENCE optional		} |
--	{ ID id-MBMSSessionRepetitionNumber	CRITICALITY	ignore	TYPE MBMSSessionRepetitionNumber			PRESENCE optional		} ,
--	...
--}

--MBMSSessionStartExtensions RANAP-PROTOCOL-EXTENSION ::= {
--	...
--}

-- **************************************************************
--
-- MBMS Session Start Response
--
-- **************************************************************

--MBMSSessionStartResponse::= SEQUENCE {
--	protocolIEs				ProtocolIE-Container		{ {MBMSSessionStartResponseIEs} },
--	protocolExtensions		ProtocolExtensionContainer	{ {MBMSSessionStartResponseExtensions} }		OPTIONAL,
--	...
--}
MBMSSessionStartResponse::= SEQUENCE {
	protocolIEs				ProtocolIE-Container,
	protocolExtensions		ProtocolExtensionContainer	OPTIONAL,
	...
}

--MBMSSessionStartResponseIEs RANAP-PROTOCOL-IES ::= {
--	{ ID id-TransportLayerInformation		CRITICALITY ignore	TYPE TransportLayerInformation		PRESENCE optional		} |
--	{ ID id-Cause							CRITICALITY ignore	TYPE Cause							PRESENCE optional		} |
--	{ ID id-CriticalityDiagnostics			CRITICALITY ignore	TYPE CriticalityDiagnostics			PRESENCE optional		} ,
--	...
--}

--MBMSSessionStartResponseExtensions RANAP-PROTOCOL-EXTENSION ::= {
--	...
--}

-- **************************************************************
--
-- MBMS Session Start Failure
--
-- **************************************************************

--MBMSSessionStartFailure ::= SEQUENCE {
--	protocolIEs				ProtocolIE-Container		{ { MBMSSessionStartFailureIEs} },
--	protocolExtensions		ProtocolExtensionContainer	{ { MBMSSessionStartFailureExtensions} }		OPTIONAL,
--	...
--}
MBMSSessionStartFailure ::= SEQUENCE {
	protocolIEs				ProtocolIE-Container,
	protocolExtensions		ProtocolExtensionContainer	OPTIONAL,
	...
}

--MBMSSessionStartFailureIEs RANAP-PROTOCOL-IES ::= {
--	{ ID id-Cause							CRITICALITY ignore	TYPE Cause							PRESENCE mandatory	} |
--	{ ID id-CriticalityDiagnostics			CRITICALITY ignore	TYPE CriticalityDiagnostics			PRESENCE optional		} ,
--	...
--}

--MBMSSessionStartFailureExtensions RANAP-PROTOCOL-EXTENSION ::= {
--	...
--}

-- **************************************************************
--
-- MBMS SESSION UPDATE PROCEDURE
--
-- **************************************************************

-- **************************************************************
--
-- MBMS Session Update
--
-- **************************************************************

--MBMSSessionUpdate ::= SEQUENCE {
--	protocolIEs				ProtocolIE-Container		{ { MBMSSessionUpdateIEs} },
--	protocolExtensions		ProtocolExtensionContainer	{ { MBMSSessionUpdateExtensions} }			OPTIONAL,
--	...
--}
MBMSSessionUpdate ::= SEQUENCE {
	protocolIEs				ProtocolIE-Container,
	protocolExtensions		ProtocolExtensionContainer OPTIONAL,
	...
}

--MBMSSessionUpdateIEs RANAP-PROTOCOL-IES ::= {
--	{ ID id-SessionUpdateID				CRITICALITY reject	TYPE SessionUpdateID						PRESENCE mandatory	} |
--	{ ID id-DeltaRAListofIdleModeUEs	CRITICALITY reject	TYPE DeltaRAListofIdleModeUEs				PRESENCE mandatory	},
--	...
--}

--MBMSSessionUpdateExtensions RANAP-PROTOCOL-EXTENSION ::= {
--	...
--}

-- **************************************************************
--
-- MBMS Session Update Response
--
-- **************************************************************

--MBMSSessionUpdateResponse ::= SEQUENCE {
--	protocolIEs				ProtocolIE-Container		{ { MBMSSessionUpdateResponseIEs} },
--	protocolExtensions		ProtocolExtensionContainer	{ { MBMSSessionUpdateResponseExtensions} }		OPTIONAL,
--	...
--}

MBMSSessionUpdateResponse ::= SEQUENCE {
	protocolIEs				ProtocolIE-Container,
	protocolExtensions		ProtocolExtensionContainer OPTIONAL,
	...
}

--MBMSSessionUpdateResponseIEs RANAP-PROTOCOL-IES ::= {
--	{ ID id-SessionUpdateID					CRITICALITY ignore	TYPE SessionUpdateID				PRESENCE mandatory	} |
--	{ ID id-TransportLayerInformation		CRITICALITY ignore	TYPE TransportLayerInformation		PRESENCE optional		} | 
--	{ ID id-Cause							CRITICALITY ignore	TYPE Cause							PRESENCE optional		} |
--	{ ID id-CriticalityDiagnostics			CRITICALITY ignore	TYPE CriticalityDiagnostics			PRESENCE optional		} ,
--	...
--}

--MBMSSessionUpdateResponseExtensions RANAP-PROTOCOL-EXTENSION ::= {
--	...
--}

-- **************************************************************
--
-- MBMS Session Update Failure
--
-- **************************************************************

--MBMSSessionUpdateFailure ::= SEQUENCE {
--	protocolIEs				ProtocolIE-Container		{ { MBMSSessionUpdateFailureIEs} },
--	protocolExtensions		ProtocolExtensionContainer	{ { MBMSSessionUpdateFailureExtensions} }		OPTIONAL,
--	...
--}

MBMSSessionUpdateFailure ::= SEQUENCE {
	protocolIEs				ProtocolIE-Container,
	protocolExtensions		ProtocolExtensionContainer	OPTIONAL,
	...
}

--MBMSSessionUpdateFailureIEs RANAP-PROTOCOL-IES ::= {
--	{ ID id-SessionUpdateID					CRITICALITY ignore	TYPE SessionUpdateID				PRESENCE mandatory	} |
--	{ ID id-Cause							CRITICALITY ignore	TYPE Cause							PRESENCE mandatory	} |
--	{ ID id-CriticalityDiagnostics			CRITICALITY ignore	TYPE CriticalityDiagnostics			PRESENCE optional		} ,
--	...
--}

--MBMSSessionUpdateFailureExtensions RANAP-PROTOCOL-EXTENSION ::= {
--	...
--}

-- **************************************************************
--
-- MBMS SESSION STOP PROCEDURE
--
-- **************************************************************

-- **************************************************************
--
-- MBMS Session Stop
--
-- **************************************************************

--MBMSSessionStop ::= SEQUENCE {
--	protocolIEs				ProtocolIE-Container		{ { MBMSSessionStopIEs} },
--	protocolExtensions		ProtocolExtensionContainer	{ { MBMSSessionStopExtensions} }			OPTIONAL,
--	...
--}
MBMSSessionStop ::= SEQUENCE {
	protocolIEs				ProtocolIE-Container,
	protocolExtensions		ProtocolExtensionContainer	OPTIONAL,
	...
}

--MBMSSessionStopIEs RANAP-PROTOCOL-IES ::= {
--	{ ID id-MBMSCNDe-Registration	CRITICALITY reject	TYPE MBMSCNDe-Registration				PRESENCE mandatory	},
--	...
--}

--MBMSSessionStopExtensions RANAP-PROTOCOL-EXTENSION ::= {
--	...
--}

-- **************************************************************
--
-- MBMS Session Stop Response
--
-- **************************************************************

--MBMSSessionStopResponse ::= SEQUENCE {
--	protocolIEs				ProtocolIE-Container		{ { MBMSSessionStopResponseIEs} },
--	protocolExtensions		ProtocolExtensionContainer	{ { MBMSSessionStopResponseExtensions} }		OPTIONAL,
--	...
--}
MBMSSessionStopResponse ::= SEQUENCE {
	protocolIEs				ProtocolIE-Container,
	protocolExtensions		ProtocolExtensionContainer	OPTIONAL,
	...
}

--MBMSSessionStopResponseIEs RANAP-PROTOCOL-IES ::= {
--	{ ID id-Cause							CRITICALITY ignore	TYPE Cause							PRESENCE optional		} |
--	{ ID id-CriticalityDiagnostics			CRITICALITY ignore	TYPE CriticalityDiagnostics			PRESENCE optional		} ,
--	...
--}

--MBMSSessionStopResponseExtensions RANAP-PROTOCOL-EXTENSION ::= {
--	...
--}

-- **************************************************************
--
-- MBMS UE LINKING PROCEDURE
--
-- **************************************************************

-- **************************************************************
--
-- MBMS UE Linking Request
--
-- **************************************************************

--MBMSUELinkingRequest ::= SEQUENCE {
--	protocolIEs				ProtocolIE-Container		{ { MBMSUELinkingRequestIEs} },
--	protocolExtensions		ProtocolExtensionContainer	{ { MBMSUELinkingRequestExtensions} }			OPTIONAL,
--	...
--}
MBMSUELinkingRequest ::= SEQUENCE {
	protocolIEs				ProtocolIE-Container,
	protocolExtensions		ProtocolExtensionContainer	OPTIONAL,
	...
}

--MBMSUELinkingRequestIEs RANAP-PROTOCOL-IES ::= {
--	{ ID id-JoinedMBMSBearerServicesList	CRITICALITY reject	TYPE JoinedMBMSBearerService-IEs		PRESENCE optional	} |
--	{ ID id-LeftMBMSBearerServicesList		CRITICALITY reject	TYPE LeftMBMSBearerService-IEs			PRESENCE optional	},
--	...
--}

LeftMBMSBearerService-IEs ::= SEQUENCE (SIZE (1.. 128)) OF
	SEQUENCE {
		tMGI				TMGI,
--		iE-Extensions		ProtocolExtensionContainer { {LeftMBMSBearerService-ExtIEs} } OPTIONAL,
--		iE-Extensions		ProtocolExtensionContainer OPTIONAL,
		...
	}

--LeftMBMSBearerService-ExtIEs RANAP-PROTOCOL-EXTENSION ::= {
--	...
--}

--MBMSUELinkingRequestExtensions RANAP-PROTOCOL-EXTENSION ::= {
--	...
--}

-- **************************************************************
--
-- MBMS UE Linking Response
--
-- **************************************************************

--MBMSUELinkingResponse ::= SEQUENCE {
--	protocolIEs				ProtocolIE-Container		{ { MBMSUELinkingResponseIEs} },
--	protocolExtensions		ProtocolExtensionContainer	{ { MBMSUELinkingResponseExtensions} }		OPTIONAL,
--	...
--}
MBMSUELinkingResponse ::= SEQUENCE {
	protocolIEs				ProtocolIE-Container,
	protocolExtensions		ProtocolExtensionContainer	OPTIONAL,
	...
}

--MBMSUELinkingResponseIEs RANAP-PROTOCOL-IES ::= {
--	{ ID id-UnsuccessfulLinkingList			CRITICALITY ignore	TYPE UnsuccessfulLinking-IEs		PRESENCE optional		} |
--	{ ID id-CriticalityDiagnostics			CRITICALITY ignore	TYPE CriticalityDiagnostics			PRESENCE optional		} ,
--	...
--}

UnsuccessfulLinking-IEs ::= SEQUENCE (SIZE (1.. 128)) OF
	SEQUENCE {
		tMGI				TMGI,
		cause				Cause,
--		iE-Extensions		ProtocolExtensionContainer { {UnsuccessfulLinking-ExtIEs} } OPTIONAL,
		iE-Extensions		ProtocolExtensionContainer  OPTIONAL,
		...
	}

--UnsuccessfulLinking-ExtIEs RANAP-PROTOCOL-EXTENSION ::= {
--	...
--}

--MBMSUELinkingResponseExtensions RANAP-PROTOCOL-EXTENSION ::= {
--	...
--}

-- **************************************************************
--
-- MBMS REGISTRATION PROCEDURE
--
-- **************************************************************

-- **************************************************************
--
-- MBMS Registration Request
--
-- **************************************************************


--MBMSRegistrationRequest ::= SEQUENCE {
--	protocolIEs				ProtocolIE-Container		{ { MBMSRegistrationRequestIEs} },
--	protocolExtensions		ProtocolExtensionContainer	{ { MBMSRegistrationRequestExtensions} }			OPTIONAL,
--	...
--}
MBMSRegistrationRequest ::= SEQUENCE {
	protocolIEs				ProtocolIE-Container,
	protocolExtensions		ProtocolExtensionContainer OPTIONAL,
	...
}

--MBMSRegistrationRequestIEs RANAP-PROTOCOL-IES ::= {
--	{ ID id-MBMSRegistrationRequestType		CRITICALITY reject	TYPE MBMSRegistrationRequestType				PRESENCE mandatory	} |
--	{ ID id-TMGI						CRITICALITY reject	TYPE TMGI									PRESENCE mandatory	} |
--	{ ID id-IPMulticastAddress			CRITICALITY reject	TYPE IPMulticastAddress						PRESENCE conditional	
	-- This IE shall be present if the MBMS Registration Request Type IE is set to "register"  									} |
--	{ ID id-APN							CRITICALITY reject	TYPE APN									PRESENCE conditional	
	-- This IE shall be present if the MBMS Registration Request Type IE is set to "register"  									} |
--	{ ID id-GlobalRNC-ID				CRITICALITY reject	TYPE GlobalRNC-ID							PRESENCE optional		},
--	...
--}

--MBMSRegistrationRequestExtensions RANAP-PROTOCOL-EXTENSION ::= {
--	...
--}

-- **************************************************************
--
-- MBMS Registration Response
--
-- **************************************************************

--MBMSRegistrationResponse ::= SEQUENCE {
--	protocolIEs				ProtocolIE-Container		{ { MBMSRegistrationResponseIEs} },
--	protocolExtensions		ProtocolExtensionContainer	{ { MBMSRegistrationResponseExtensions} }		OPTIONAL,
--	...
--}

MBMSRegistrationResponse ::= SEQUENCE {
	protocolIEs				ProtocolIE-Container,
	protocolExtensions		ProtocolExtensionContainer	OPTIONAL,
	...
}

--MBMSRegistrationResponseIEs RANAP-PROTOCOL-IES ::= {
--	{ ID id-TMGI							CRITICALITY ignore	TYPE TMGI							PRESENCE optional		} |
--	{ ID id-GlobalCN-ID						CRITICALITY ignore	TYPE GlobalCN-ID					PRESENCE optional		} |
--	{ ID id-CriticalityDiagnostics			CRITICALITY ignore	TYPE CriticalityDiagnostics			PRESENCE optional		} ,
--	...
--}

--MBMSRegistrationResponseExtensions RANAP-PROTOCOL-EXTENSION ::= {
--	...
--}

-- **************************************************************
--
-- MBMS Registration Failure
--
-- **************************************************************

--MBMSRegistrationFailure ::= SEQUENCE {
--	protocolIEs				ProtocolIE-Container		{ { MBMSRegistrationFailureIEs} },
--	protocolExtensions		ProtocolExtensionContainer	{ { MBMSRegistrationFailureExtensions} }		OPTIONAL,
--	...
--}

MBMSRegistrationFailure ::= SEQUENCE {
	protocolIEs				ProtocolIE-Container,
	protocolExtensions		ProtocolExtensionContainer	OPTIONAL,
	...
}

--MBMSRegistrationFailureIEs RANAP-PROTOCOL-IES ::= {
--	{ ID id-TMGI							CRITICALITY ignore	TYPE TMGI							PRESENCE optional		} |
--	{ ID id-GlobalCN-ID						CRITICALITY ignore	TYPE GlobalCN-ID					PRESENCE optional		} |
--	{ ID id-Cause							CRITICALITY ignore	TYPE Cause							PRESENCE mandatory	} |
--	{ ID id-CriticalityDiagnostics			CRITICALITY ignore	TYPE CriticalityDiagnostics			PRESENCE optional		} ,
--	...
--}

--MBMSRegistrationFailureExtensions RANAP-PROTOCOL-EXTENSION ::= {
--	...
--}

-- **************************************************************
--
-- MBMS CN DE-REGISTRATION PROCEDURE
--
-- **************************************************************

-- **************************************************************
--
-- MBMS CN De-Registration Request
--
-- **************************************************************

--MBMSCNDe-RegistrationRequest ::= SEQUENCE {
--	protocolIEs				ProtocolIE-Container		{ { MBMSCNDe-RegistrationRequestIEs} },
--	protocolExtensions		ProtocolExtensionContainer	{ { MBMSCNDe-RegistrationRequestExtensions} }			OPTIONAL,
--	...
--}

MBMSCNDe-RegistrationRequest ::= SEQUENCE {
	protocolIEs				ProtocolIE-Container,
	protocolExtensions		ProtocolExtensionContainer	OPTIONAL,
	...
}

--MBMSCNDe-RegistrationRequestIEs RANAP-PROTOCOL-IES ::= {
--	{ ID id-TMGI						CRITICALITY reject	TYPE TMGI									PRESENCE mandatory	} |
--	{ ID id-GlobalCN-ID					CRITICALITY reject	TYPE GlobalCN-ID							PRESENCE optional		},
--	...
--}

--MBMSCNDe-RegistrationRequestExtensions RANAP-PROTOCOL-EXTENSION ::= {
--	...
--}

-- **************************************************************
--
-- MBMS CN De-Registration Response
--
-- **************************************************************

--MBMSCNDe-RegistrationResponse ::= SEQUENCE {
--	protocolIEs				ProtocolIE-Container		{ { MBMSCNDe-RegistrationResponseIEs} },
--	protocolExtensions		ProtocolExtensionContainer	{ { MBMSCNDe-RegistrationResponseExtensions} }		OPTIONAL,
--	...
--}
MBMSCNDe-RegistrationResponse ::= SEQUENCE {
	protocolIEs				ProtocolIE-Container,
	protocolExtensions		ProtocolExtensionContainer	OPTIONAL,
	...
}

--MBMSCNDe-RegistrationResponseIEs RANAP-PROTOCOL-IES ::= {
--	{ ID id-TMGI							CRITICALITY ignore	TYPE TMGI							PRESENCE mandatory	} |
--	{ ID id-GlobalRNC-ID					CRITICALITY ignore	TYPE GlobalRNC-ID					PRESENCE mandatory	} |
--	{ ID id-Cause							CRITICALITY ignore	TYPE Cause							PRESENCE optional		} |
--	{ ID id-CriticalityDiagnostics			CRITICALITY ignore	TYPE CriticalityDiagnostics			PRESENCE optional		} ,
--	...
--}

--MBMSCNDe-RegistrationResponseExtensions RANAP-PROTOCOL-EXTENSION ::= {
--	...
--}

-- **************************************************************
--
-- MBMS RAB ESTABLISHMENT INDICATION PROCEDURE
--
-- **************************************************************

-- **************************************************************
--
-- MBMS RAB Establishment Indication
--
-- **************************************************************

--MBMSRABEstablishmentIndication ::= SEQUENCE {
--	protocolIEs				ProtocolIE-Container		{ { MBMSRABEstablishmentIndicationIEs} },
--	protocolExtensions		ProtocolExtensionContainer	{ { MBMSRABEstablishmentIndicationExtensions} }			OPTIONAL,
--	...
--}
MBMSRABEstablishmentIndication ::= SEQUENCE {
	protocolIEs				ProtocolIE-Container,
	protocolExtensions		ProtocolExtensionContainer	OPTIONAL,
	...
}

--MBMSRABEstablishmentIndicationIEs RANAP-PROTOCOL-IES ::= {
--	{ ID id-TransportLayerInformation		CRITICALITY ignore	TYPE TransportLayerInformation		PRESENCE mandatory	} ,
--	...
--}

--MBMSRABEstablishmentIndicationExtensions RANAP-PROTOCOL-EXTENSION ::= {
--	...
--}

-- **************************************************************
--
-- MBMS RAB RELEASE PROCEDURE
--
-- **************************************************************

-- **************************************************************
--
-- MBMS RAB Release Request
--
-- **************************************************************

--MBMSRABReleaseRequest ::= SEQUENCE {
--	protocolIEs				ProtocolIE-Container		{ {MBMSRABReleaseRequestIEs} },
--	protocolExtensions		ProtocolExtensionContainer	{ {MBMSRABReleaseRequestExtensions} }			OPTIONAL,
--	...
--}
MBMSRABReleaseRequest ::= SEQUENCE {
	protocolIEs				ProtocolIE-Container,
	protocolExtensions		ProtocolExtensionContainer	OPTIONAL,
	...
}

--MBMSRABReleaseRequestIEs RANAP-PROTOCOL-IES ::= {
--	{ ID id-Cause		CRITICALITY ignore	TYPE Cause				PRESENCE mandatory	},
--	...
--}


--MBMSRABReleaseRequestExtensions RANAP-PROTOCOL-EXTENSION ::= {
--	...
--}

-- **************************************************************
--
-- MBMS RAB Release
--
-- **************************************************************

--MBMSRABRelease ::= SEQUENCE {
--	protocolIEs				ProtocolIE-Container		{ {MBMSRABReleaseIEs} },
--	protocolExtensions		ProtocolExtensionContainer	{ {MBMSRABReleaseExtensions} }			OPTIONAL,
--	...
--}

MBMSRABRelease ::= SEQUENCE {
	protocolIEs				ProtocolIE-Container,
	protocolExtensions		ProtocolExtensionContainer OPTIONAL,
	...
}

--MBMSRABReleaseIEs RANAP-PROTOCOL-IES ::= {
--	{ ID id-Cause		CRITICALITY ignore	TYPE Cause	 			PRESENCE mandatory	},
--	...
--}

--MBMSRABReleaseExtensions RANAP-PROTOCOL-EXTENSION ::= {
--	...
--}

-- **************************************************************
--
-- MBMS RAB Release Failure
--
-- **************************************************************

--MBMSRABReleaseFailure ::= SEQUENCE {
--	protocolIEs				ProtocolIE-Container		{ {MBMSRABReleaseFailureIEs} },
--	protocolExtensions		ProtocolExtensionContainer	{ {MBMSRABReleaseFailureExtensions} }			OPTIONAL,
--	...
--}

MBMSRABReleaseFailure ::= SEQUENCE {
	protocolIEs				ProtocolIE-Container,
	protocolExtensions		ProtocolExtensionContainer OPTIONAL,
	...
}

--MBMSRABReleaseFailureIEs RANAP-PROTOCOL-IES ::= {
--	{ ID id-Cause		CRITICALITY ignore	TYPE Cause				PRESENCE mandatory	},
--	...
--}

--MBMSRABReleaseFailureExtensions RANAP-PROTOCOL-EXTENSION ::= {
--	...
--}


--END



--9.3.4	Information Element Definitions
-- **************************************************************
--
-- Information Element Definitions
--
-- **************************************************************

--RANAP-IEs { 
--itu-t (0) identified-organization (4) etsi (0) mobileDomain (0) 
--umts-Access (20) modules (3) ranap (0) version1 (1) ranap-IEs (2) }
--
--DEFINITIONS AUTOMATIC TAGS ::= 
--
--BEGIN

--IMPORTS
--	maxNrOfErrors,
--	maxNrOfPDPDirections,
--	maxNrOfPoints,
--	maxNrOfRABs,
--	maxNrOfSRBs,
--	maxNrOfSeparateTrafficDirections,
--	maxRAB-Subflows,
--	maxRAB-SubflowCombination,
--	maxNrOfLevels,
--	maxNrOfAltValues,
--	maxNrOfSNAs,
--	maxNrOfLAs,
--	maxNrOfPLMNsSN,
--	maxSet,
--	maxNrOfUEsToBeTraced,
--	maxNrOfInterfaces,
--	maxnoofMulticastServicesPerRNC,
--	maxMBMSSA,
--	maxMBMSRA,
--	maxnoofMulticastServicesPerUE,
--	maxNrOfEDCHMACdFlows-1,

--	id-CN-DomainIndicator,
--	id-MessageStructure,
--	id-SRB-TrCH-Mapping,
--	id-TypeOfError,
	
--	id-hS-DSCH-MAC-d-Flow-ID,
--	id-SignallingIndication,
--	id-CellLoadInformationGroup,
--	id-TraceRecordingSessionInformation,
--	id-MBMSLinkingInformation,
--	id-AlternativeRABConfiguration,
--	id-AlternativeRABConfigurationRequest,
--	id-E-DCH-MAC-d-Flow-ID
--
--FROM RANAP-Constants

--	Criticality,
--	ProcedureCode,
--	ProtocolIE-ID,
--	TriggeringMessage
--FROM RANAP-CommonDataTypes

--	ProtocolExtensionContainer{},
--	RANAP-PROTOCOL-EXTENSION
--FROM RANAP-Containers;

-- A

AccuracyFulfilmentIndicator ::= ENUMERATED{
	requested-Accuracy-Fulfilled,
	requested-Accuracy-Not-Fulfilled,
	...
}

AllocationOrRetentionPriority ::= SEQUENCE {
	priorityLevel			PriorityLevel,
	pre-emptionCapability		Pre-emptionCapability,
	pre-emptionVulnerability	Pre-emptionVulnerability,
	queuingAllowed			QueuingAllowed,
--	iE-Extensions			ProtocolExtensionContainer { {AllocationOrRetentionPriority-ExtIEs} } OPTIONAL,
	iE-Extensions			ProtocolExtensionContainer  OPTIONAL,
	...
}

--AllocationOrRetentionPriority-ExtIEs RANAP-PROTOCOL-EXTENSION ::= {
--	...
--}

Alt-RAB-Parameters ::= SEQUENCE {
	altMaxBitrateInf			Alt-RAB-Parameter-MaxBitrateInf 						OPTIONAL,
	altGuaranteedBitRateInf		Alt-RAB-Parameter-GuaranteedBitrateInf 					OPTIONAL,
--	iE-Extensions			ProtocolExtensionContainer { {Alt-RAB-Parameters-ExtIEs} } 	OPTIONAL,
	iE-Extensions			ProtocolExtensionContainer  	OPTIONAL,
	...
}

--Alt-RAB-Parameters-ExtIEs RANAP-PROTOCOL-EXTENSION ::= {
-- Extension for Release 6 to indicate an alternative RAB configuration --
--	{ ID id-AlternativeRABConfiguration		CRITICALITY ignore	EXTENSION RAB-Parameters	PRESENCE optional },
--	...
--}

Alt-RAB-Parameter-GuaranteedBitrateInf ::= SEQUENCE {
	altGuaranteedBitrateType			Alt-RAB-Parameter-GuaranteedBitrateType,
	altGuaranteedBitrates				Alt-RAB-Parameter-GuaranteedBitrates			OPTIONAL
	-- This IE shall be present if  the Type of Guaranteed Bit Rates Information IE is set to "Value range" or "Discrete values" --,
	...
}

Alt-RAB-Parameter-GuaranteedBitrateType ::= ENUMERATED{
	unspecified,
	value-range,
	discrete-values,
	...
}

Alt-RAB-Parameter-GuaranteedBitrates ::= SEQUENCE (SIZE (1..16)) OF
	Alt-RAB-Parameter-GuaranteedBitrateList


Alt-RAB-Parameter-GuaranteedBitrateList	::= SEQUENCE (SIZE (1..2)) OF GuaranteedBitrate


Alt-RAB-Parameter-MaxBitrateInf ::= SEQUENCE {
	altMaxBitrateType			Alt-RAB-Parameter-MaxBitrateType,
	altMaxBitrates				Alt-RAB-Parameter-MaxBitrates			OPTIONAL
	-- This IE shall be present if  the Type of Alternative Maximun Bit Rates Information IE is set to "Value range" or "Discrete values" --,
	...
}

Alt-RAB-Parameter-MaxBitrateType ::= ENUMERATED{
	unspecified,
	value-range,
	discrete-values,
	...
}

Alt-RAB-Parameter-MaxBitrates ::= SEQUENCE (SIZE (1..16)) OF
	Alt-RAB-Parameter-MaxBitrateList


Alt-RAB-Parameter-MaxBitrateList ::= SEQUENCE (SIZE (1..2)) OF MaxBitrate

AlternativeRABConfigurationRequest ::= ENUMERATED{
	alternative-RAB-configuration-Requested,
	...
}

APN	::= OCTET STRING (SIZE (1..255))
-- Reference: 23.003

AreaIdentity ::= CHOICE {
	sAI				SAI,
	geographicalArea		GeographicalArea,
	...
}

Ass-RAB-Parameters ::= SEQUENCE {
	assMaxBitrateInf			Ass-RAB-Parameter-MaxBitrateList 						OPTIONAL,
	assGuaranteedBitRateInf		Ass-RAB-Parameter-GuaranteedBitrateList 				OPTIONAL,
--	iE-Extensions			ProtocolExtensionContainer { {Ass-RAB-Parameters-ExtIEs} } 	OPTIONAL,
	iE-Extensions			ProtocolExtensionContainer OPTIONAL,
	...
}

--Ass-RAB-Parameters-ExtIEs RANAP-PROTOCOL-EXTENSION ::= {
--	...
--}


Ass-RAB-Parameter-GuaranteedBitrateList	::= SEQUENCE (SIZE (1..2)) OF GuaranteedBitrate


Ass-RAB-Parameter-MaxBitrateList ::= SEQUENCE (SIZE (1..2)) OF MaxBitrate

AuthorisedPLMNs ::= SEQUENCE (SIZE (1..32)) OF
	SEQUENCE {
		pLMNidentity			PLMNidentity,
		authorisedSNAsList		AuthorisedSNAs		OPTIONAL,
--		iE-Extensions			ProtocolExtensionContainer { {AuthorisedPLMNs-ExtIEs} } OPTIONAL,
		iE-Extensions			ProtocolExtensionContainer  OPTIONAL,
		...
	}

--AuthorisedPLMNs-ExtIEs RANAP-PROTOCOL-EXTENSION ::= {
--	...
--}

AuthorisedSNAs  ::= SEQUENCE (SIZE (1..65536)) OF  SNAC


-- B

BindingID				::= OCTET STRING (SIZE (4))

BroadcastAssistanceDataDecipheringKeys	::= SEQUENCE {
	cipheringKeyFlag		BIT STRING (SIZE (1)),
	currentDecipheringKey	BIT STRING (SIZE (56)),
	nextDecipheringKey		BIT STRING (SIZE (56)),
	...
}


-- C


Cause ::= CHOICE {
	radioNetwork			CauseRadioNetwork,
	transmissionNetwork		CauseTransmissionNetwork,
	nAS						CauseNAS,
	protocol				CauseProtocol,
	misc					CauseMisc,
	non-Standard			CauseNon-Standard,
	...,
	radioNetworkExtension	CauseRadioNetworkExtension
}

CauseMisc ::= INTEGER {
	om-intervention (113),
	no-resource-available (114),
	unspecified-failure (115),
	network-optimisation (116)
} (113..128)

CauseNAS ::= INTEGER {
	user-restriction-start-indication (81),
	user-restriction-end-indication (82),
	normal-release (83)
} (81..96)

CauseProtocol ::= INTEGER {
	transfer-syntax-error (97),
	semantic-error (98),
	message-not-compatible-with-receiver-state (99),
	abstract-syntax-error-reject (100),
	abstract-syntax-error-ignore-and-notify (101),
	abstract-syntax-error-falsely-constructed-message (102)

} (97..112)

CauseRadioNetwork ::= INTEGER {
	rab-pre-empted (1),
	trelocoverall-expiry (2),
	trelocprep-expiry (3),
	treloccomplete-expiry (4),
	tqueing-expiry (5),
	relocation-triggered (6),
	trellocalloc-expiry(7),
	unable-to-establish-during-relocation (8),
	unknown-target-rnc (9),
	relocation-cancelled (10),
	successful-relocation (11),
	requested-ciphering-and-or-integrity-protection-algorithms-not-supported (12),
	conflict-with-already-existing-integrity-protection-and-or-ciphering-information (13),
	failure-in-the-radio-interface-procedure (14),
	release-due-to-utran-generated-reason (15),
	user-inactivity (16),
	time-critical-relocation (17),
	requested-traffic-class-not-available (18),
	invalid-rab-parameters-value (19),
	requested-maximum-bit-rate-not-available (20),
	requested-guaranteed-bit-rate-not-available (21),
	requested-transfer-delay-not-achievable (22),
	invalid-rab-parameters-combination (23),
	condition-violation-for-sdu-parameters (24),
	condition-violation-for-traffic-handling-priority (25),
	condition-violation-for-guaranteed-bit-rate (26),
	user-plane-versions-not-supported (27),
	iu-up-failure (28),
	relocation-failure-in-target-CN-RNC-or-target-system(29),
	invalid-RAB-ID (30),
	no-remaining-rab (31),
	interaction-with-other-procedure (32),
	requested-maximum-bit-rate-for-dl-not-available (33), 
	requested-maximum-bit-rate-for-ul-not-available (34), 
	requested-guaranteed-bit-rate-for-dl-not-available (35), 
	requested-guaranteed-bit-rate-for-ul-not-available (36),
	repeated-integrity-checking-failure (37),
	requested-request-type-not-supported (38),
	request-superseded (39),
	release-due-to-UE-generated-signalling-connection-release (40),
	resource-optimisation-relocation (41),
	requested-information-not-available (42),
	relocation-desirable-for-radio-reasons (43),
	relocation-not-supported-in-target-RNC-or-target-system (44),
	directed-retry (45),
	radio-connection-with-UE-Lost (46),
	rNC-unable-to-establish-all-RFCs  (47),
	deciphering-keys-not-available(48),
	dedicated-assistance-data-not-available(49),
	relocation-target-not-allowed (50),
	location-reporting-congestion (51),
	reduce-load-in-serving-cell (52),
	no-radio-resources-available-in-target-cell (53),
	gERAN-Iumode-failure (54),
	access-restricted-due-to-shared-networks (55),
	incoming-relocation-not-supported-due-to-PUESBINE-feature (56),
	traffic-load-in-the-target-cell-higher-than-in-the-source-cell (57),
	mBMS-no-multicast-service-for-this-UE(58),
	mBMS-unknown-UE-ID(59),
	successful-MBMS-session-start-no-data-bearer-necessary(60),
	mBMS-superseded-due-to-NNSF(61),
	mBMS-UE-linking-already-done(62),
	mBMS-UE-de-linking-failure-no-existing-UE-linking(63),
	tMGI-unknown(64)
} (1..64)

CauseRadioNetworkExtension ::= INTEGER {
	iP-multicast-address-and-APN-not-valid(257),
	mBMS-de-registration-rejected-due-to-implicit-registration(258),
	mBMS-request-superseded(259),
	mBMS-de-registration-during-session-not-allowed(260),
	mBMS-no-data-bearer-necessary(261)
} (257..512)

CauseNon-Standard ::= INTEGER (129..256)
-- Cause value 256 shall not be used --

CauseTransmissionNetwork ::= INTEGER {
	signalling-transport-resource-failure (65),
	iu-transport-connection-failed-to-establish (66)
} (65..80)

Cell-Capacity-Class-Value ::= INTEGER (1..100,...)

CellLoadInformation ::= SEQUENCE {
	cell-Capacity-Class-Value	Cell-Capacity-Class-Value,
	loadValue					LoadValue,
	rTLoadValue					RTLoadValue						OPTIONAL,
	nRTLoadInformationValue		NRTLoadInformationValue			OPTIONAL,
--	iE-Extensions				ProtocolExtensionContainer { { CellLoadInformation-ExtIEs } }		OPTIONAL,
	iE-Extensions				ProtocolExtensionContainer 	OPTIONAL,
	...
}

--CellLoadInformation-ExtIEs RANAP-PROTOCOL-EXTENSION ::= {
--	...
--}

CellLoadInformationGroup ::= SEQUENCE {
	sourceCellID						SourceCellID,
	uplinkCellLoadInformation			CellLoadInformation		OPTIONAL,
	downlinkCellLoadInformation			CellLoadInformation		OPTIONAL,
--	iE-Extensions	ProtocolExtensionContainer { { CellLoadInformationGroup-ExtIEs } }	OPTIONAL,
	iE-Extensions	ProtocolExtensionContainer OPTIONAL,
	...
}

--CellLoadInformationGroup-ExtIEs RANAP-PROTOCOL-EXTENSION ::= {
--	...
--}

ClientType ::= ENUMERATED {
	emergency-Services,
	value-Added-Services,
	pLMN-Operator-Services,
	lawful-Intercept-Services,
	pLMN-Operator-Broadcast-Services,
	pLMN-Operator-O-et-M,
	pLMN-Operator-Anonymous-Statistics,
	pLMN-Operator-Target-MS-Service-Support,
	...
}

CriticalityDiagnostics ::= SEQUENCE {
	procedureCode			ProcedureCode			OPTIONAL,
	triggeringMessage		TriggeringMessage		OPTIONAL,
	procedureCriticality		Criticality			OPTIONAL,
	iEsCriticalityDiagnostics		CriticalityDiagnostics-IE-List 	OPTIONAL,
--	iE-Extensions			ProtocolExtensionContainer { {CriticalityDiagnostics-ExtIEs} } OPTIONAL,
	iE-Extensions			ProtocolExtensionContainer  OPTIONAL,
	...
}

--CriticalityDiagnostics-ExtIEs RANAP-PROTOCOL-EXTENSION ::= {
--	...
--}

CriticalityDiagnostics-IE-List ::= SEQUENCE (SIZE (1..256)) OF
	SEQUENCE {
		iECriticality		Criticality,
		iE-ID				ProtocolIE-ID,
		repetitionNumber		RepetitionNumber0		OPTIONAL,
--		iE-Extensions			ProtocolExtensionContainer { {CriticalityDiagnostics-IE-List-ExtIEs} } OPTIONAL,
		iE-Extensions			ProtocolExtensionContainer OPTIONAL,
		...
	}

--CriticalityDiagnostics-IE-List-ExtIEs RANAP-PROTOCOL-EXTENSION ::= {
-- Extension for Release 99 to enable reporting the message structure down to the erroneous IE --
--	{	ID id-MessageStructure	CRITICALITY ignore		EXTENSION MessageStructure	PRESENCE optional	} |
-- Extension for Release 99 to enable reporting if a reported error is due to a not understood or a missing IE --
--	{	ID id-TypeOfError		CRITICALITY ignore		EXTENSION TypeOfError		PRESENCE mandatory	},
--	...
--}

MessageStructure ::= SEQUENCE (SIZE (1..256)) OF
	SEQUENCE { 
		iE-ID					ProtocolIE-ID,
		repetitionNumber		RepetitionNumber1		OPTIONAL,
--		iE-Extensions			ProtocolExtensionContainer { {MessageStructure-ExtIEs} } OPTIONAL,
		iE-Extensions			ProtocolExtensionContainer OPTIONAL,
		...
	}


--MessageStructure-ExtIEs RANAP-PROTOCOL-EXTENSION ::= {
--	...
--}

CGI ::= SEQUENCE {
	pLMNidentity				PLMNidentity,
	lAC				LAC,
	cI				CI,
--	iE-Extensions			ProtocolExtensionContainer { {CGI-ExtIEs} } OPTIONAL
	iE-Extensions			ProtocolExtensionContainer  OPTIONAL
}

--CGI-ExtIEs RANAP-PROTOCOL-EXTENSION ::= {
--	...
--}

ChosenEncryptionAlgorithm ::= EncryptionAlgorithm

ChosenIntegrityProtectionAlgorithm 	::= IntegrityProtectionAlgorithm

CI					::= OCTET STRING (SIZE (2))

ClassmarkInformation2			::= OCTET STRING

ClassmarkInformation3			::= OCTET STRING

CN-DomainIndicator ::= ENUMERATED { 
	cs-domain, 
	ps-domain 
}

CN-ID				::= INTEGER (0..4095)


-- D

DataVolumeReference			::= INTEGER (0..255)

DataVolumeReportingIndication ::= ENUMERATED {
	do-report,
	do-not-report
}

DCH-ID ::= INTEGER (0..255)

DeliveryOfErroneousSDU ::= ENUMERATED { 
	yes, 
	no, 
	no-error-detection-consideration
}

DeliveryOrder::= ENUMERATED {
	delivery-order-requested,
	delivery-order-not-requested
}

DeltaRAListofIdleModeUEs ::= SEQUENCE {
	newRAListofIdleModeUEs					NewRAListofIdleModeUEs	OPTIONAL,
	rAListwithNoIdleModeUEsAnyMore			RAListwithNoIdleModeUEsAnyMore	OPTIONAL,
--	iE-Extensions			ProtocolExtensionContainer { {DeltaRAListofIdleModeUEs-ExtIEs} } OPTIONAL
	iE-Extensions			ProtocolExtensionContainer  OPTIONAL
}

NewRAListofIdleModeUEs ::= SEQUENCE (SIZE (1..65536)) OF
	RAC

RAListwithNoIdleModeUEsAnyMore ::= SEQUENCE (SIZE (1..65536)) OF
	RAC

--DeltaRAListofIdleModeUEs-ExtIEs RANAP-PROTOCOL-EXTENSION ::= {
--	...
--}

DL-GTP-PDU-SequenceNumber		::= INTEGER (0..65535)

DL-N-PDU-SequenceNumber 		::= INTEGER (0..65535)

D-RNTI					::= INTEGER (0..1048575)

DRX-CycleLengthCoefficient			::= INTEGER (6..9)

DSCH-ID ::= INTEGER (0..255)

-- E

E-DCH-MAC-d-Flow-ID		::= INTEGER (0.. 7)

EncryptionAlgorithm 			::= INTEGER { no-encryption (0), standard-UMTS-encryption-algorith-UEA1 (1) } (0..15)

EncryptionInformation ::= SEQUENCE {
--	permittedAlgorithms		PermittedEncryptionAlgorithms,
	encryptionpermittedAlgorithms		PermittedEncryptionAlgorithms,
--	key						EncryptionKey,
	encryptionkey			EncryptionKey,
--	iE-Extensions			ProtocolExtensionContainer { {EncryptionInformation-ExtIEs} } OPTIONAL
	iE-Extensions			ProtocolExtensionContainer  OPTIONAL
}

--EncryptionInformation-ExtIEs RANAP-PROTOCOL-EXTENSION ::= {
--	...
--}

EncryptionKey 				::= BIT STRING (SIZE (128))
-- Reference: 33.102

EquipmentsToBeTraced ::= CHOICE {
	iMEIlist				IMEIList,
	iMEISVlist				IMEISVList,
	iMEIgroup				IMEIGroup,
	iMEISVgroup				IMEISVGroup,
	...
}

Event ::= ENUMERATED { 
	stop-change-of-service-area, 
	direct, 
	change-of-servicearea, 
	...,
	stop-direct 
}

-- F

FrequenceLayerConvergenceFlag ::= ENUMERATED { 
	no-FLC-flag,
	...
}

-- G

GeographicalArea ::= CHOICE {
	point				GA-Point,
	pointWithUnCertainty		GA-PointWithUnCertainty,
	polygon				GA-Polygon,
	...,
	pointWithUncertaintyEllipse		GA-PointWithUnCertaintyEllipse,
	pointWithAltitude		GA-PointWithAltitude,
	pointWithAltitudeAndUncertaintyEllipsoid		GA-PointWithAltitudeAndUncertaintyEllipsoid,
	ellipsoidArc		GA-EllipsoidArc
}

GeographicalCoordinates ::= SEQUENCE {
	latitudeSign			ENUMERATED { north, south },
	latitude			INTEGER (0..8388607),
	longitude			INTEGER (-8388608..8388607),
--	iE-Extensions			ProtocolExtensionContainer { {GeographicalCoordinates-ExtIEs} } OPTIONAL,
	iE-Extensions			ProtocolExtensionContainer  OPTIONAL,
	...
}

--GeographicalCoordinates-ExtIEs RANAP-PROTOCOL-EXTENSION ::= {
--	...
--}

GA-AltitudeAndDirection ::= SEQUENCE {
	directionOfAltitude		ENUMERATED {height, depth},
	altitude		INTEGER (0..32767),
	...
}

GA-EllipsoidArc ::= SEQUENCE {
	geographicalCoordinates		GeographicalCoordinates,
	innerRadius					INTEGER (0..65535),
	uncertaintyRadius			INTEGER (0..127),
	offsetAngle					INTEGER (0..179),
	includedAngle				INTEGER (0..179),
	confidence					INTEGER (0..127),
--	iE-Extensions				ProtocolExtensionContainer { { GA-EllipsoidArc-ExtIEs} } OPTIONAL,
	iE-Extensions				ProtocolExtensionContainer  OPTIONAL,
	...
}

--GA-EllipsoidArc-ExtIEs RANAP-PROTOCOL-EXTENSION ::= {
--	...
--}

GA-Point ::= SEQUENCE {
	geographicalCoordinates		GeographicalCoordinates,
--	iE-Extensions			ProtocolExtensionContainer { {GA-Point-ExtIEs} } OPTIONAL,
	iE-Extensions			ProtocolExtensionContainer OPTIONAL,
	...
}

--GA-Point-ExtIEs RANAP-PROTOCOL-EXTENSION ::= {
--	...
--}

GA-PointWithAltitude ::= SEQUENCE {
	geographicalCoordinates		GeographicalCoordinates,
	altitudeAndDirection		GA-AltitudeAndDirection,
--	iE-Extensions				ProtocolExtensionContainer { { GA-PointWithAltitude-ExtIEs} } OPTIONAL,
	iE-Extensions				ProtocolExtensionContainer  OPTIONAL,
	...
}

--GA-PointWithAltitude-ExtIEs RANAP-PROTOCOL-EXTENSION ::= {
--	...
--}

GA-PointWithAltitudeAndUncertaintyEllipsoid ::= SEQUENCE {
	geographicalCoordinates		GeographicalCoordinates,
	altitudeAndDirection		GA-AltitudeAndDirection,
	uncertaintyEllipse			GA-UncertaintyEllipse,
	uncertaintyAltitude			INTEGER (0..127),
	confidence					INTEGER (0..127),
--	iE-Extensions				ProtocolExtensionContainer { { GA-PointWithAltitudeAndUncertaintyEllipsoid-ExtIEs} } OPTIONAL,
	iE-Extensions				ProtocolExtensionContainer  OPTIONAL,
	...
}

--GA-PointWithAltitudeAndUncertaintyEllipsoid-ExtIEs RANAP-PROTOCOL-EXTENSION ::= {
--	...
--}

GA-PointWithUnCertainty ::=SEQUENCE {
	geographicalCoordinates		GeographicalCoordinates,
--	iE-Extensions			ProtocolExtensionContainer { {GA-PointWithUnCertainty-ExtIEs} } OPTIONAL,
	iE-Extensions			ProtocolExtensionContainer OPTIONAL,
	uncertaintyCode			INTEGER (0..127)
}

--GA-PointWithUnCertainty-ExtIEs RANAP-PROTOCOL-EXTENSION ::= {
--	...
--}

GA-PointWithUnCertaintyEllipse ::= SEQUENCE {
	geographicalCoordinates		GeographicalCoordinates,
	uncertaintyEllipse			GA-UncertaintyEllipse,
	confidence					INTEGER (0..127),
--	iE-Extensions				ProtocolExtensionContainer { { GA-PointWithUnCertaintyEllipse-ExtIEs} } OPTIONAL,
	iE-Extensions				ProtocolExtensionContainer  OPTIONAL,
	...
}

--GA-PointWithUnCertaintyEllipse-ExtIEs RANAP-PROTOCOL-EXTENSION ::= {
--	...
--}

GA-Polygon ::= SEQUENCE (SIZE (1..15)) OF
	SEQUENCE {
		geographicalCoordinates		GeographicalCoordinates,
--		iE-Extensions			ProtocolExtensionContainer { {GA-Polygon-ExtIEs} } OPTIONAL,
		iE-Extensions			ProtocolExtensionContainer  OPTIONAL,
		...
	}

--GA-Polygon-ExtIEs RANAP-PROTOCOL-EXTENSION ::= {
--	...
--}

GA-UncertaintyEllipse ::= SEQUENCE {
	uncertaintySemi-major		INTEGER (0..127),
	uncertaintySemi-minor		INTEGER (0..127),
	orientationOfMajorAxis		INTEGER (0..179), 	-- The values 90..179 shall not be used.
	...
}

GERAN-BSC-Container				::= OCTET STRING
        -- GERAN BSC Container as defined in [11] --


GERAN-Cell-ID ::= SEQUENCE {
	lAI				LAI,
    rAC				RAC, 
	cI				CI,
--	iE-Extensions			ProtocolExtensionContainer { {GERAN-Cell-ID-ExtIEs} } OPTIONAL
	iE-Extensions			ProtocolExtensionContainer  OPTIONAL
}

--GERAN-Cell-ID-ExtIEs RANAP-PROTOCOL-EXTENSION ::= {
--	...
--}

GERAN-Classmark	 				::= OCTET STRING
        -- GERAN Classmark as defined in [11] --

GlobalCN-ID ::= SEQUENCE {
	pLMNidentity				PLMNidentity,
	cN-ID				CN-ID
}


GlobalRNC-ID ::= SEQUENCE {
	pLMNidentity				PLMNidentity,
	rNC-ID				RNC-ID
}

GTP-TEI					::= OCTET STRING (SIZE (4))

GuaranteedBitrate			::= INTEGER (0..16000000)
-- Unit is bits per sec

-- H

HS-DSCH-MAC-d-Flow-ID		::= INTEGER (0..7)

-- I


IMEI					::= OCTET STRING (SIZE (8))
-- Reference: 23.003

IMEIGroup	::= SEQUENCE {
	iMEI				IMEI,
	iMEIMask			BIT STRING (SIZE (7)),
--	iE-Extensions		ProtocolExtensionContainer { { IMEIGroup-ExtIEs} } OPTIONAL
	iE-Extensions		ProtocolExtensionContainer  OPTIONAL
}

--IMEIGroup-ExtIEs RANAP-PROTOCOL-EXTENSION ::= {
--	...
--}

IMEIList	::= SEQUENCE (SIZE (1..64)) OF IMEI

IMEISV					::= OCTET STRING (SIZE (8))
-- Reference: 23.003

IMEISVGroup	::= SEQUENCE {
	iMEISV				IMEISV,
	iMEISVMask			BIT STRING (SIZE (7)),
--	iE-Extensions		ProtocolExtensionContainer { { IMEISVGroup-ExtIEs} } OPTIONAL
	iE-Extensions		ProtocolExtensionContainer  OPTIONAL
}

--IMEISVGroup-ExtIEs RANAP-PROTOCOL-EXTENSION ::= {
--	...
--}

IMEISVList	::= SEQUENCE (SIZE (1..64)) OF IMEISV

IMSI					::= OCTET STRING (SIZE (3..8))
-- Reference: 23.003

InformationExchangeID ::= INTEGER (0.. 1048575)

InformationExchangeType ::= ENUMERATED { 
	transfer,
	request,
	... 
}

InformationRequested ::= CHOICE {
	requestedMBMSIPMulticastAddressandAPNRequest		RequestedMBMSIPMulticastAddressandAPNRequest,
	requestedMulticastServiceList						RequestedMulticastServiceList,
	...
}


InformationRequestType ::= CHOICE {
	mBMSIPMulticastAddressandAPNRequest		MBMSIPMulticastAddressandAPNRequest,
	permanentNAS-UE-ID						PermanentNAS-UE-ID,
	...
}

InformationTransferID  ::= INTEGER (0.. 1048575)

InformationTransferType ::= CHOICE {
	rNCTraceInformation			RNCTraceInformation,
	...
}

IntegrityProtectionAlgorithm		::= INTEGER { 
	standard-UMTS-integrity-algorithm-UIA1 (0),
	no-value (15)
} (0..15)

IntegrityProtectionInformation ::= SEQUENCE {
	permittedAlgorithms		PermittedIntegrityProtectionAlgorithms,
	key						IntegrityProtectionKey,
--	iE-Extensions			ProtocolExtensionContainer { {IntegrityProtectionInformation-ExtIEs} } OPTIONAL
	iE-Extensions			ProtocolExtensionContainer  OPTIONAL
}

--IntegrityProtectionInformation-ExtIEs RANAP-PROTOCOL-EXTENSION ::= {
--	...
--}

IntegrityProtectionKey			::= BIT STRING (SIZE (128))

InterSystemInformationTransferType ::= CHOICE {
	rIM-Transfer					RIM-Transfer,
	...
}

InterSystemInformation-TransparentContainer ::= SEQUENCE {
	downlinkCellLoadInformation			CellLoadInformation		OPTIONAL,
	uplinkCellLoadInformation			CellLoadInformation		OPTIONAL,
--	iE-Extensions			ProtocolExtensionContainer { { InterSystemInformation-TransparentContainer-ExtIEs} } OPTIONAL,
	iE-Extensions			ProtocolExtensionContainer  OPTIONAL,
	...
}

--InterSystemInformation-TransparentContainer-ExtIEs RANAP-PROTOCOL-EXTENSION ::= {
--...
--}

IPMulticastAddress ::= OCTET STRING (SIZE (4..16))
-- Reference: 23.003

IuSignallingConnectionIdentifier	::= BIT STRING (SIZE (24))

IuTransportAssociation ::= CHOICE {
	gTP-TEI				GTP-TEI,
	bindingID			BindingID,
	...
}

-- J
-- K

KeyStatus	::= ENUMERATED {
	old,
	new,
	...
}
-- L

LA-LIST  ::= SEQUENCE (SIZE (1..65536)) OF
	SEQUENCE {
		lAC						LAC,
		listOF-SNAs				ListOF-SNAs,
--		iE-Extensions			ProtocolExtensionContainer { { LA-LIST-ExtIEs} } OPTIONAL,
		iE-Extensions			ProtocolExtensionContainer OPTIONAL,
		...
	}

--LA-LIST-ExtIEs RANAP-PROTOCOL-EXTENSION ::= {
--	...
--}

LAC ::= OCTET STRING (SIZE (2))

LAI ::= SEQUENCE {
	pLMNidentity				PLMNidentity,
	lAC				LAC,
--	iE-Extensions			ProtocolExtensionContainer { {LAI-ExtIEs} } OPTIONAL
	iE-Extensions			ProtocolExtensionContainer  OPTIONAL
}

--LAI-ExtIEs RANAP-PROTOCOL-EXTENSION ::= {
--	...
--}

LastKnownServiceArea	::= SEQUENCE {
	sAI			SAI,
	ageOfSAI	INTEGER (0..32767),
--	iE-Extensions	ProtocolExtensionContainer { {LastKnownServiceArea-ExtIEs} } OPTIONAL,	
	iE-Extensions	ProtocolExtensionContainer  OPTIONAL,	
	...
}

--LastKnownServiceArea-ExtIEs RANAP-PROTOCOL-EXTENSION ::= {
--	...
--}

ListOF-SNAs ::= SEQUENCE (SIZE (1..65536)) OF SNAC

ListOfInterfacesToTrace ::= SEQUENCE (SIZE (1..16)) OF InterfacesToTraceItem

InterfacesToTraceItem ::= SEQUENCE {
	interface				ENUMERATED {iu-cs, iu-ps, iur, iub, uu, ...},
--	iE-Extensions			ProtocolExtensionContainer { {InterfacesToTraceItem-ExtIEs} }	OPTIONAL,
	iE-Extensions			ProtocolExtensionContainer 	OPTIONAL,
	...
}

--InterfacesToTraceItem-ExtIEs RANAP-PROTOCOL-EXTENSION ::= {
--	...
--}

LoadValue	::= INTEGER (0..100)

LocationRelatedDataRequestType	::= SEQUENCE {
	requestedLocationRelatedDataType			RequestedLocationRelatedDataType,
	requestedGPSAssistanceData					RequestedGPSAssistanceData	OPTIONAL,
	-- This IE shall be present if the Requested Location Related Data Type IE is set to ‘Dedicated Assistance Data for Assisted GPS’ –-
	...
}

LocationRelatedDataRequestTypeSpecificToGERANIuMode	::= ENUMERATED { 
	decipheringKeysEOTD,
	dedicatedMobileAssistedEOTDAssistanceData,
	dedicatedMobileBasedEOTDAssistanceData, 
	... 
}

L3-Information				::= OCTET STRING


-- M

MaxBitrate				::= INTEGER (1..16000000)
-- Unit is bits per sec

MaxSDU-Size				::= INTEGER (0..32768)
-- MaxSDU-Size
-- Unit is bit

MBMS-PTP-RAB-ID ::= BIT STRING (SIZE (8))

MBMSBearerServiceType ::= ENUMERATED {
	multicast,
	broadcast,
	...
}

MBMSCNDe-Registration ::= ENUMERATED {
	normalsessionstop,
	deregister,
	...
}

MBMSIPMulticastAddressandAPNRequest ::= SEQUENCE (SIZE (1..512)) OF
	TMGI

MBMSLinkingInformation ::= ENUMERATED {
	uE-has-joined-multicast-services,
	...
}

MBMSRegistrationRequestType ::= ENUMERATED {
	register,
	deregister,
	...
}

MBMSServiceArea ::= SEQUENCE {
	mBMSServiceAreaList		MBMSServiceAreaList,
--	iE-Extensions			ProtocolExtensionContainer { {MBMSServiceArea-ExtIEs} } OPTIONAL
	iE-Extensions			ProtocolExtensionContainer  OPTIONAL
}

MBMSServiceAreaList ::= SEQUENCE (SIZE (1..256)) OF
	MBMSServiceAreaCode

MBMSServiceAreaCode ::= INTEGER (0..65535)

--MBMSServiceArea-ExtIEs RANAP-PROTOCOL-EXTENSION ::= {
--	...
--}

MBMSSessionDuration ::= OCTET STRING (SIZE (3))



MBMSSessionIdentity ::= OCTET STRING (SIZE (1))

MBMSSessionRepetitionNumber ::= INTEGER (0..255)

-- N


NAS-PDU					::= OCTET STRING

NAS-SequenceNumber			::= BIT STRING (SIZE (2))
-- Reference: 24.008

NAS-SynchronisationIndicator	::= BIT STRING (SIZE (4))

NewBSS-To-OldBSS-Information		::= OCTET STRING

NonSearchingIndication ::= ENUMERATED {
	non-searching,
	searching
}

NRTLoadInformationValue	::= INTEGER (0..3)

NumberOfIuInstances			::= INTEGER (1..2)

NumberOfSteps				::= INTEGER (1..16)

-- O

OldBSS-ToNewBSS-Information		::= OCTET STRING

OMC-ID					::= OCTET STRING (SIZE (3..22))
-- Reference: GSM [25]

-- P

PagingAreaID ::= CHOICE {
	lAI				LAI,
	rAI				RAI,
	...
}

PagingCause ::= ENUMERATED { 
	terminating-conversational-call, 
	terminating-streaming-call, 
	terminating-interactive-call, 
	terminating-background-call, 
	terminating-low-priority-signalling,
	..., 
	terminating-high-priority-signalling
}

PDP-TypeInformation ::= SEQUENCE (SIZE (1..2)) OF
	PDP-Type

PDP-Type ::= ENUMERATED {
	empty,
	ppp,
	osp-ihoss  -- this value shall not be used -- ,
	ipv4,
	ipv6,
	...
}

PermanentNAS-UE-ID ::= CHOICE {
	iMSI				IMSI,
	...
}

PermittedEncryptionAlgorithms ::= SEQUENCE (SIZE (1..16)) OF
	EncryptionAlgorithm

PermittedIntegrityProtectionAlgorithms ::= SEQUENCE (SIZE (1..16)) OF
	IntegrityProtectionAlgorithm

PLMNidentity 				::= OCTET STRING (SIZE (3))

PLMNs-in-shared-network ::= SEQUENCE (SIZE (1..32)) OF
	SEQUENCE {
		pLMNidentity			PLMNidentity,
		lA-LIST					LA-LIST,
--		iE-Extensions			ProtocolExtensionContainer { { PLMNs-in-shared-network-ExtIEs} } OPTIONAL,
--		iE-Extensions			ProtocolExtensionContainer  OPTIONAL,
		...
	}

--PLMNs-in-shared-network-ExtIEs RANAP-PROTOCOL-EXTENSION ::= {
--	...
--}

PositioningDataDiscriminator ::= BIT STRING (SIZE(4))

PositioningDataSet ::= SEQUENCE(SIZE(1..9)) OF PositioningMethodAndUsage

PositioningMethodAndUsage ::= OCTET STRING (SIZE(1))

PositioningPriority	::= ENUMERATED {
	high-Priority,
	normal-Priority,
...
}

PositionData ::= SEQUENCE {
	positioningDataDiscriminator		PositioningDataDiscriminator,
	positioningDataSet					PositioningDataSet			OPTIONAL,
-- This IE shall be present if the PositioningDataDiscriminator IE is set to the value "0000"  --
--	iE-Extensions		ProtocolExtensionContainer { {PositionData-ExtIEs} } OPTIONAL,
	iE-Extensions		ProtocolExtensionContainer OPTIONAL,
	...
}

--PositionData-ExtIEs RANAP-PROTOCOL-EXTENSION ::= {
--	...
--}

PositionDataSpecificToGERANIuMode ::= OCTET STRING 

Pre-emptionCapability ::= ENUMERATED {
	shall-not-trigger-pre-emption,
	may-trigger-pre-emption
}

Pre-emptionVulnerability ::= ENUMERATED {
	not-pre-emptable,
	pre-emptable
}

PriorityLevel ::= INTEGER { spare (0), highest (1), lowest (14), no-priority (15) } (0..15)

ProvidedData ::= CHOICE {
	shared-network-information				Shared-Network-Information,
	... 
}

P-TMSI					::= OCTET STRING (SIZE (4))

-- Q

QueuingAllowed ::= ENUMERATED {
	queueing-not-allowed,
	queueing-allowed
}


-- R
RAB-AsymmetryIndicator::= ENUMERATED {
	symmetric-bidirectional,
	asymmetric-unidirectional-downlink,
	asymmetric-unidirectional-uplink,
	asymmetric-bidirectional,
	...
}

RAB-ID ::= BIT STRING (SIZE (8))

RAB-Parameter-GuaranteedBitrateList	::= SEQUENCE (SIZE (1..2)) OF GuaranteedBitrate

RAB-Parameter-MaxBitrateList		::= SEQUENCE (SIZE (1..2)) OF MaxBitrate

RAB-Parameters ::= SEQUENCE {
	trafficClass				TrafficClass,
	rAB-AsymmetryIndicator		RAB-AsymmetryIndicator,
	maxBitrate					RAB-Parameter-MaxBitrateList,
	guaranteedBitRate			RAB-Parameter-GuaranteedBitrateList OPTIONAL
	-- This IE shall be present the traffic class IE is set to "Conversational" or "Streaming" --,
	deliveryOrder				DeliveryOrder,
	maxSDU-Size					MaxSDU-Size,
	sDU-Parameters				SDU-Parameters,
	transferDelay				TransferDelay OPTIONAL
	-- This IE shall be present the traffic class IE is set to "Conversational" or "Streaming" --,
	trafficHandlingPriority		TrafficHandlingPriority OPTIONAL
	-- This IE shall be present the traffic class IE is set to "Interactive" --,
	allocationOrRetentionPriority	AllocationOrRetentionPriority OPTIONAL,
	sourceStatisticsDescriptor	SourceStatisticsDescriptor OPTIONAL
	-- This IE shall be present the traffic class IE is set to "Conversational" or "Streaming" --,
	relocationRequirement	RelocationRequirement OPTIONAL,
--	iE-Extensions			ProtocolExtensionContainer { {RAB-Parameters-ExtIEs} } OPTIONAL,
	iE-Extensions			ProtocolExtensionContainer OPTIONAL,
	...
}

--RAB-Parameters-ExtIEs RANAP-PROTOCOL-EXTENSION ::= {
-- Extension for Release 5 to enable indication that Interactive User Plane data is of a signalling nature 
--   { ID id-SignallingIndication    CRITICALITY ignore EXTENSION SignallingIndication PRESENCE optional },
--	...
--}

RAB-SubflowCombinationBitRate 	::= INTEGER (0..16000000)

RAB-TrCH-Mapping ::=	SEQUENCE ( SIZE (1..256)) OF 
	RAB-TrCH-MappingItem

RAB-TrCH-MappingItem ::= SEQUENCE {
	rAB-ID			RAB-ID,
	trCH-ID-List	TrCH-ID-List,
--	iE-Extensions			ProtocolExtensionContainer { { RAB-TrCH-MappingItem-ExtIEs} } OPTIONAL,
	iE-Extensions			ProtocolExtensionContainer  OPTIONAL,
	...
}

--RAB-TrCH-MappingItem-ExtIEs RANAP-PROTOCOL-EXTENSION ::= {
-- Extension for Release 99 to enable transfer of RAB Subflow mapping onto Iur transport channel Ids for a given indicated domain --
--	{	ID id-CN-DomainIndicator	CRITICALITY ignore		EXTENSION CN-DomainIndicator	PRESENCE optional	},
--	...
--}

RAC					::= OCTET STRING (SIZE (1))

RAI ::= SEQUENCE {
	lAI				LAI,
	rAC				RAC,
--	iE-Extensions			ProtocolExtensionContainer { {RAI-ExtIEs} } OPTIONAL,
	iE-Extensions			ProtocolExtensionContainer OPTIONAL,
	...
}

--RAI-ExtIEs RANAP-PROTOCOL-EXTENSION ::= {
--	...
--}

RAListofIdleModeUEs ::= CHOICE {
	notEmptyRAListofIdleModeUEs			NotEmptyRAListofIdleModeUEs,
	emptyFullRAListofIdleModeUEs			ENUMERATED {emptylist,fulllist,...},
	...
}

NotEmptyRAListofIdleModeUEs ::= SEQUENCE {
	rAofIdleModeUEs			RAofIdleModeUEs,
--	iE-Extensions			ProtocolExtensionContainer { {NotEmptyRAListofIdleModeUEs-ExtIEs} } OPTIONAL
	iE-Extensions			ProtocolExtensionContainer OPTIONAL
}

RAofIdleModeUEs ::= SEQUENCE (SIZE (1..65536)) OF
	RAC

--NotEmptyRAListofIdleModeUEs-ExtIEs RANAP-PROTOCOL-EXTENSION ::= {
--	...
--}

RateControlAllowed ::= ENUMERATED {
	not-allowed,
	allowed
}


RedirectionCompleted	::= ENUMERATED {
	redirection-completed,
	...
}

RejectCauseValue ::= ENUMERATED { 
	pLMN-Not-Allowed,
	location-Area-Not-Allowed,
	roaming-Not-Allowed-In-This-Location-Area,
	no-Suitable-Cell-In-Location-Area,
	gPRS-Services-Not-Allowed-In-This-PLMN,
	...
}


RelocationRequirement ::= ENUMERATED {
	lossless,
	none,
	...
--	realtime
}

RelocationType ::= ENUMERATED { 
	ue-not-involved,
	ue-involved,
	...
}

RepetitionNumber0 ::= INTEGER (0..255) 

RepetitionNumber1 ::= INTEGER (1..256)


ReportArea ::= ENUMERATED { 
	service-area, 
	geographical-area, 
	... 
}

RequestedGPSAssistanceData 	::= OCTET STRING (SIZE (1 .. 38 ))
        -- gpsAssistanceData as defined in 24.080 --

RequestedLocationRelatedDataType ::= ENUMERATED { 
	decipheringKeysUEBasedOTDOA,
	decipheringKeysAssistedGPS,
	dedicatedAssistanceDataUEBasedOTDOA,
	dedicatedAssistanceDataAssistedGPS, 
	... 
}

RequestedMBMSIPMulticastAddressandAPNRequest ::= SEQUENCE (SIZE (1..512)) OF
	MBMSIPMulticastAddressandAPNlist

MBMSIPMulticastAddressandAPNlist ::= SEQUENCE {
	tMGI					TMGI,
	iPMulticastAddress		IPMulticastAddress,
	aPN						APN,
--	iE-Extensions			ProtocolExtensionContainer { {MBMSIPMulticastAddressandAPNlist-ExtIEs} } 	OPTIONAL,
	iE-Extensions			ProtocolExtensionContainer  	OPTIONAL,
	...
}

--MBMSIPMulticastAddressandAPNlist-ExtIEs RANAP-PROTOCOL-EXTENSION ::= {
--	...
--}

RequestedMulticastServiceList ::= SEQUENCE (SIZE (1.. 128)) OF
	TMGI

Requested-RAB-Parameter-Values ::= SEQUENCE {
	requestedMaxBitrates				Requested-RAB-Parameter-MaxBitrateList			OPTIONAL,
	requestedGuaranteedBitrates				Requested-RAB-Parameter-GuaranteedBitrateList			OPTIONAL,
--	iE-Extensions			ProtocolExtensionContainer { { Requested-RAB-Parameter-Values-ExtIEs} } 	OPTIONAL,
	iE-Extensions			ProtocolExtensionContainer 	OPTIONAL,
	...
}

--Requested-RAB-Parameter-Values-ExtIEs RANAP-PROTOCOL-EXTENSION ::= {
-- Extension for Release 6 to enable RNC to request the execution of an alternative RAB configuration --
--	{ ID id-AlternativeRABConfigurationRequest		CRITICALITY ignore	EXTENSION AlternativeRABConfigurationRequest	PRESENCE optional },
--	...
--}

Requested-RAB-Parameter-MaxBitrateList ::= SEQUENCE (SIZE (1..2)) OF MaxBitrate

Requested-RAB-Parameter-GuaranteedBitrateList	::= SEQUENCE (SIZE (1..2)) OF GuaranteedBitrate


RequestType ::= SEQUENCE {
	event				Event,
	reportArea			ReportArea,
	accuracyCode		INTEGER (0..127)	OPTIONAL,
	...
}

ResidualBitErrorRatio ::= SEQUENCE {
	mantissa			INTEGER (1..9),
	exponent			INTEGER (1..8),
--	iE-Extensions			ProtocolExtensionContainer { {ResidualBitErrorRatio-ExtIEs} } OPTIONAL
	iE-Extensions			ProtocolExtensionContainer OPTIONAL
}
-- ResidualBitErrorRatio = mantissa * 10^-exponent

--ResidualBitErrorRatio-ExtIEs RANAP-PROTOCOL-EXTENSION ::= {
--	...
--}

ResponseTime	::= ENUMERATED {
	lowdelay,
	delaytolerant,
...
}

RIMInformation					::= OCTET STRING 

RIM-Transfer ::= SEQUENCE {
	rIMInformation				RIMInformation,
    rIMRoutingAddress			RIMRoutingAddress	OPTIONAL,
--	iE-Extensions			ProtocolExtensionContainer { {RIM-Transfer-ExtIEs} } OPTIONAL
	iE-Extensions			ProtocolExtensionContainer  OPTIONAL
}

--RIM-Transfer-ExtIEs RANAP-PROTOCOL-EXTENSION ::= {
--	...
--}

RIMRoutingAddress ::= CHOICE {
	globalRNC-ID					GlobalRNC-ID,
	gERAN-Cell-ID					GERAN-Cell-ID,
	...
}


RNC-ID					::= INTEGER (0..4095)
-- RNC-ID					::= BIT STRING (SIZE (12))
-- Harmonized with RNSAP and NBAP definitions


RNCTraceInformation::= SEQUENCE {
	traceReference					TraceReference,
	traceActivationIndicator		ENUMERATED {activated,deactivated},
	equipmentsToBeTraced			EquipmentsToBeTraced												OPTIONAL,
	-- This IE shall be present if the Trace Activation Indicator IE is set to "Activated".
--	iE-Extensions					ProtocolExtensionContainer { { RNCTraceInformation-ExtIEs} }		OPTIONAL
	iE-Extensions					ProtocolExtensionContainer OPTIONAL
}

--RNCTraceInformation-ExtIEs RANAP-PROTOCOL-EXTENSION ::= {
--	...
--}

RRC-Container				::= OCTET STRING

RTLoadValue	::= INTEGER (0..100)

-- S

SAC					::= OCTET STRING (SIZE (2))

SAI ::= SEQUENCE {
	pLMNidentity				PLMNidentity,
	lAC				LAC,
	sAC				SAC,
--	iE-Extensions			ProtocolExtensionContainer { {SAI-ExtIEs} } OPTIONAL
	iE-Extensions			ProtocolExtensionContainer OPTIONAL
}

--SAI-ExtIEs RANAP-PROTOCOL-EXTENSION ::= {
--	...
--}

SAPI ::= ENUMERATED {
	sapi-0,
	sapi-3,
	...
}

SessionUpdateID ::= INTEGER (0.. 1048575)

Shared-Network-Information ::= SEQUENCE {
		pLMNs-in-shared-network			PLMNs-in-shared-network,
--		iE-Extensions			ProtocolExtensionContainer { {Shared-Network-Information-ExtIEs} } OPTIONAL,
		iE-Extensions			ProtocolExtensionContainer  OPTIONAL,
		...
	}

--Shared-Network-Information-ExtIEs RANAP-PROTOCOL-EXTENSION ::= {
--	...
--}

SignallingIndication ::= ENUMERATED { 
	signalling, 
	... 
}

SDU-ErrorRatio ::= SEQUENCE {
	mantissa			INTEGER (1..9),
	exponent			INTEGER (1..6),
--	iE-Extensions			ProtocolExtensionContainer { {SDU-ErrorRatio-ExtIEs} } OPTIONAL
	iE-Extensions			ProtocolExtensionContainer  OPTIONAL
}
-- SDU-ErrorRatio = mantissa * 10^-exponent

--SDU-ErrorRatio-ExtIEs RANAP-PROTOCOL-EXTENSION ::= {
--	...
--}

SDU-FormatInformationParameters ::= SEQUENCE (SIZE (1..64)) OF
	SEQUENCE {
		subflowSDU-Size			SubflowSDU-Size 	OPTIONAL,
		rAB-SubflowCombinationBitRate	RAB-SubflowCombinationBitRate 	OPTIONAL,
--		iE-Extensions			ProtocolExtensionContainer { {SDU-FormatInformationParameters-ExtIEs} } OPTIONAL,
		iE-Extensions			ProtocolExtensionContainer  OPTIONAL,
		...
	}

--SDU-FormatInformationParameters-ExtIEs RANAP-PROTOCOL-EXTENSION ::= {
--	...
--}

SDU-Parameters ::= SEQUENCE (SIZE (1..7)) OF
	SEQUENCE {
		sDU-ErrorRatio			SDU-ErrorRatio OPTIONAL
		-- This IE shall be present if the Delivery Of Erroneous SDU IE is set to "Yes" or "No" --,
		residualBitErrorRatio		ResidualBitErrorRatio,
		deliveryOfErroneousSDU		DeliveryOfErroneousSDU,
		sDU-FormatInformationParameters	SDU-FormatInformationParameters OPTIONAL,
--		iE-Extensions			ProtocolExtensionContainer { {SDU-Parameters-ExtIEs} } OPTIONAL,
		iE-Extensions			ProtocolExtensionContainer  OPTIONAL,
		...
	}

--SDU-Parameters-ExtIEs RANAP-PROTOCOL-EXTENSION ::= {
--	...
--}

SNA-Access-Information ::= SEQUENCE {
		authorisedPLMNs			AuthorisedPLMNs,
--		iE-Extensions			ProtocolExtensionContainer { {SNA-Access-Information-ExtIEs} } OPTIONAL,
		iE-Extensions			ProtocolExtensionContainer  OPTIONAL,
		...
	}

--SNA-Access-Information-ExtIEs RANAP-PROTOCOL-EXTENSION ::= {
--	...
--}

SNAC				::= INTEGER (0..65535)

Service-Handover ::= ENUMERATED {
	handover-to-GSM-should-be-performed,
	handover-to-GSM-should-not-be-performed,
	handover-to-GSM-shall-not-be-performed,
	...
}

SourceCellID ::= CHOICE {
	sourceUTRANCellID			SourceUTRANCellID, 
	sourceGERANCellID			CGI,
	...
}

SourceID ::= CHOICE {
	sourceRNC-ID			SourceRNC-ID, 
	sAI				SAI,
	...
}


SourceRNC-ID ::= SEQUENCE {
	pLMNidentity				PLMNidentity,
	rNC-ID				RNC-ID,
--	iE-Extensions			ProtocolExtensionContainer { {SourceRNC-ID-ExtIEs} } OPTIONAL
	iE-Extensions			ProtocolExtensionContainer  OPTIONAL
}

--SourceRNC-ID-ExtIEs RANAP-PROTOCOL-EXTENSION ::= {
--	...
--}

SourceRNC-ToTargetRNC-TransparentContainer ::= SEQUENCE {
	rRC-Container			RRC-Container,
	numberOfIuInstances		NumberOfIuInstances,
	relocationType 			RelocationType,
	chosenIntegrityProtectionAlgorithm ChosenIntegrityProtectionAlgorithm	OPTIONAL,
	integrityProtectionKey		IntegrityProtectionKey			OPTIONAL,
	chosenEncryptionAlgorithForSignalling ChosenEncryptionAlgorithm		OPTIONAL,
	cipheringKey			EncryptionKey				OPTIONAL,
	chosenEncryptionAlgorithForCS	ChosenEncryptionAlgorithm		OPTIONAL,
	chosenEncryptionAlgorithForPS	ChosenEncryptionAlgorithm		OPTIONAL,
	d-RNTI				D-RNTI 					OPTIONAL
	-- This IE shall be present if the Relocation type IE is set to "UE not involved in relocation of SRNS" --,
	targetCellId			TargetCellId				OPTIONAL
	-- This IE shall be present if the Relocation type IE is set to "UE involved in relocation of SRNS" --,
  	rAB-TrCH-Mapping			RAB-TrCH-Mapping				OPTIONAL,
--	iE-Extensions			ProtocolExtensionContainer { {SourceRNC-ToTargetRNC-TransparentContainer-ExtIEs} } OPTIONAL,
	iE-Extensions			ProtocolExtensionContainer  OPTIONAL,
	...
}

--SourceRNC-ToTargetRNC-TransparentContainer-ExtIEs RANAP-PROTOCOL-EXTENSION ::= {
-- Extension for Release 99 to enable transfer of SRB mapping onto Iur transport channel Ids --
--	{	ID id-SRB-TrCH-Mapping	CRITICALITY reject		EXTENSION SRB-TrCH-Mapping	PRESENCE optional	}|
-- Extension for Release 5 to enable Inter RAN Load Information Exchange over Iu --
--	{ID id-CellLoadInformationGroup	CRITICALITY ignore		EXTENSION CellLoadInformationGroup		PRESENCE optional}|
-- Extension for Release 6 to provide Trace Recording Session Information to the Target RNC --
--	{ID id-TraceRecordingSessionInformation		CRITICALITY ignore		EXTENSION TraceRecordingSessionInformation		PRESENCE optional}|
-- Extension for Release 6 to indicate to the Target RNC that the UE has activated Multicast Service --
--	{ID id-MBMSLinkingInformation		CRITICALITY ignore		EXTENSION MBMSLinkingInformation	PRESENCE optional},
--	...
--}

SourceStatisticsDescriptor ::= ENUMERATED { 
	speech, 
	unknown, 
	... 
}

SourceUTRANCellID ::= SEQUENCE {
	pLMNidentity			PLMNidentity,
	uTRANcellID				TargetCellId,
--	iE-Extensions			ProtocolExtensionContainer { {SourceUTRANCellID-ExtIEs} } OPTIONAL
	iE-Extensions			ProtocolExtensionContainer  OPTIONAL
}

--SourceUTRANCellID-ExtIEs RANAP-PROTOCOL-EXTENSION ::= {
--	...
--}

SRB-ID ::= INTEGER (1..32)

SRB-TrCH-Mapping ::=	SEQUENCE ( SIZE (1..8)) OF 
	SRB-TrCH-MappingItem

SRB-TrCH-MappingItem ::= SEQUENCE {
	sRB-ID			SRB-ID,
	trCH-ID			TrCH-ID,
--	iE-Extensions			ProtocolExtensionContainer { { SRB-TrCH-MappingItem-ExtIEs} } OPTIONAL,
	iE-Extensions			ProtocolExtensionContainer  OPTIONAL,
	...
}


--SRB-TrCH-MappingItem-ExtIEs RANAP-PROTOCOL-EXTENSION ::= {
--	...
--}

SubflowSDU-Size				::= INTEGER (0..4095)
-- Unit is bit

-- T

TargetCellId				::= INTEGER (0..268435455)

TargetID ::= CHOICE {
	targetRNC-ID			TargetRNC-ID,
	cGI				CGI,
	...
}




TargetRNC-ID ::= SEQUENCE {
	lAI				LAI,
    rAC				RAC 		OPTIONAL,
	rNC-ID				RNC-ID,
--	iE-Extensions			ProtocolExtensionContainer { {TargetRNC-ID-ExtIEs} } OPTIONAL
	iE-Extensions			ProtocolExtensionContainer  OPTIONAL
}

--TargetRNC-ID-ExtIEs RANAP-PROTOCOL-EXTENSION ::= {
--	...
--}

TargetRNC-ToSourceRNC-TransparentContainer ::= SEQUENCE {
	rRC-Container			RRC-Container,
	d-RNTI					D-RNTI 					OPTIONAL
	-- May be included to allow the triggering of the Relocation Detect procedure from the Iur Interface --,
--	iE-Extensions			ProtocolExtensionContainer { {TargetRNC-ToSourceRNC-TransparentContainer-ExtIEs} } OPTIONAL,
	iE-Extensions			ProtocolExtensionContainer  OPTIONAL,
	...
}

--TargetRNC-ToSourceRNC-TransparentContainer-ExtIEs RANAP-PROTOCOL-EXTENSION ::= {
--	...
--}

-- TBCD-STRING 				::= OCTET STRING

TemporaryUE-ID ::= CHOICE {
	tMSI				TMSI,
	p-TMSI				P-TMSI,
	...
}

TMGI ::= SEQUENCE {
	pLMNidentity			PLMNidentity,
	serviceID				OCTET STRING (SIZE (3)),
--	iE-Extensions			ProtocolExtensionContainer { {TMGI-ExtIEs} } OPTIONAL
	iE-Extensions			ProtocolExtensionContainer OPTIONAL
}

--TMGI-ExtIEs RANAP-PROTOCOL-EXTENSION ::= {
--	...
--}

TMSI					::= OCTET STRING (SIZE (4))

TraceDepth ::= ENUMERATED { 
	minimum,
	medium,
	maximum,
	...
}

TracePropagationParameters ::= SEQUENCE {
	traceRecordingSessionReference		TraceRecordingSessionReference,
	traceDepth							TraceDepth,
	listOfInterfacesToTrace				ListOfInterfacesToTrace		OPTIONAL,
--	iE-Extensions			ProtocolExtensionContainer { { TracePropagationParameters-ExtIEs} } OPTIONAL,
	iE-Extensions			ProtocolExtensionContainer  OPTIONAL,
	...
}

--TracePropagationParameters-ExtIEs RANAP-PROTOCOL-EXTENSION ::= {
--	...
--}

TraceRecordingSessionInformation	::= SEQUENCE {
	traceReference						TraceReference,
	traceRecordingSessionReference		TraceRecordingSessionReference,
--	iE-Extensions						ProtocolExtensionContainer { { TraceRecordingSessionInformation-ExtIEs} } OPTIONAL,
	iE-Extensions						ProtocolExtensionContainer OPTIONAL,
	...
}

--TraceRecordingSessionInformation-ExtIEs RANAP-PROTOCOL-EXTENSION ::= {
--	...
--}

TraceRecordingSessionReference		::= INTEGER (0..65535)

TraceReference				::= OCTET STRING (SIZE (2..3))

TraceType				::= OCTET STRING (SIZE (1))
-- Reference: GSM TS 12.08

TrafficClass ::= ENUMERATED { 
	conversational, 
	streaming, 
	interactive, 
	background,
	...
}

TrafficHandlingPriority 		::= INTEGER { spare (0), highest (1), lowest (14), no-priority-used (15) } (0..15)

TransferDelay 				::= INTEGER (0..65535)
-- Unit is millisecond

UnsuccessfullyTransmittedDataVolume	::= INTEGER (0..4294967295)

TransportLayerAddress 			::= BIT STRING (SIZE (1..160, ...))

TrCH-ID ::= SEQUENCE {
	dCH-ID				DCH-ID		OPTIONAL,
	dSCH-ID				DSCH-ID		OPTIONAL,
	uSCH-ID				USCH-ID		OPTIONAL,
--	iE-Extensions			ProtocolExtensionContainer { { TrCH-ID-ExtIEs} } OPTIONAL,
	iE-Extensions			ProtocolExtensionContainer  OPTIONAL,
	...
}

--TrCH-ID-ExtIEs RANAP-PROTOCOL-EXTENSION ::= {
-- Extension for Release 5 to enable transfer of HS-DSCH-MAC-d-Flow-ID onto Iur transport channel ID --
--	{ID id-hS-DSCH-MAC-d-Flow-ID	CRITICALITY ignore		EXTENSION HS-DSCH-MAC-d-Flow-ID		PRESENCE optional}|
-- Extension for Release 6 to enable transfer of E-DCH-MAC-d-Flow-ID onto Iur transport channel ID --
--	{ID id-E-DCH-MAC-d-Flow-ID	CRITICALITY ignore		EXTENSION E-DCH-MAC-d-Flow-ID PRESENCE optional},
--	...
--}

TrCH-ID-List ::=  SEQUENCE (SIZE (1..7)) OF 
	TrCH-ID

TriggerID				::= OCTET STRING (SIZE (3..22)) 

TypeOfError ::= ENUMERATED {
	not-understood,
	missing,
	...
}


-- U

UE-ID ::= CHOICE {
	imsi				IMSI,
	imei				IMEI,
	...,
	imeisv				IMEISV

}

UESBI-Iu ::= SEQUENCE {
	uESBI-IuA		UESBI-IuA	OPTIONAL,
	uESBI-IuB		UESBI-IuB	OPTIONAL,
--	iE-Extensions		ProtocolExtensionContainer { {UESBI-Iu-ExtIEs} } OPTIONAL,
	iE-Extensions		ProtocolExtensionContainer OPTIONAL,
	...
}

--UESBI-Iu-ExtIEs RANAP-PROTOCOL-EXTENSION ::= {
--	...
--}

UESBI-IuA				::= BIT STRING (SIZE(1..128))
-- Reference: TR25.994 --
UESBI-IuB				::= BIT STRING (SIZE(1..128))
-- Reference: TR25.995 --

UL-GTP-PDU-SequenceNumber		::= INTEGER (0..65535)

UL-N-PDU-SequenceNumber 		::= INTEGER (0..65535)

UP-ModeVersions				::= BIT STRING (SIZE (16))

USCH-ID						::= INTEGER (0..255)

UserPlaneMode ::= ENUMERATED { 
	transparent-mode, 
	support-mode-for-predefined-SDU-sizes, 
	... 
}

-- V

VerticalAccuracyCode			::= INTEGER (0..127)

-- END

-- 9.3.5	Common Definitions
-- **************************************************************
--
-- Common definitions
--
-- **************************************************************

--RANAP-CommonDataTypes {
--itu-t (0) identified-organization (4) etsi (0) mobileDomain (0) 
--umts-Access (20) modules (3) ranap (0) version1 (1) ranap-CommonDataTypes (3)  }

--DEFINITIONS AUTOMATIC TAGS ::= 

--BEGIN

Criticality		::= ENUMERATED { reject, ignore, notify }

Presence		::= ENUMERATED { optional, conditional, mandatory }

PrivateIE-ID	::= CHOICE {
	local				INTEGER (0..65535),
	global				OBJECT IDENTIFIER
}

ProcedureCode		::= INTEGER{
	id-RAB-Assignment					( 0 ),
	id-Iu-Release						( 1 ),
	id-RelocationPreparation			( 2 ),
	id-RelocationResourceAllocation		( 3 ),
	id-RelocationCancel					( 4 ),
	id-SRNS-ContextTransfer				( 5 ),
	id-SecurityModeControl				( 6 ),
	id-DataVolumeReport					( 7 ),
	id-Reset							( 9 ),
	id-RAB-ReleaseRequest				( 10 ),
	id-Iu-ReleaseRequest				( 11 ),
	id-RelocationDetect					( 12 ),
	id-RelocationComplete				( 13 ),
	id-Paging							( 14 ),
	id-CommonID							( 15 ),
	id-CN-InvokeTrace					( 16 ),
	id-LocationReportingControl			( 17 ),
	id-LocationReport					( 18 ),
	id-InitialUE-Message				( 19 ),
	id-DirectTransfer					( 20 ),
	id-OverloadControl					( 21 ),
	id-ErrorIndication					( 22 ),
	id-SRNS-DataForward					( 23 ),
	id-ForwardSRNS-Context				( 24 ),
	id-privateMessage					( 25 ),
	id-CN-DeactivateTrace				( 26 ),
	id-ResetResource					( 27 ),
	id-RANAP-Relocation					( 28 ),
	id-RAB-ModifyRequest				( 29 ),
	id-LocationRelatedData				( 30 ),
	id-InformationTransfer				( 31 ),
	id-UESpecificInformation			( 32 ),
	id-UplinkInformationExchange		( 33 ),
	id-DirectInformationTransfer		( 34 ),
	id-MBMSSessionStart					( 35 ),
	id-MBMSSessionUpdate				( 36 ),
	id-MBMSSessionStop					( 37 ),
	id-MBMSUELinking					( 38 ),
	id-MBMSRegistration					( 39 ),
	id-MBMSCNDe-Registration-Procedure	( 40 ),
	id-MBMSRABEstablishmentIndication	( 41 ),
	id-MBMSRABRelease					( 42 )
	} (0..255)

-- Wireshark adapt.
ProcedureCodeSuccessfulOutcome		::= INTEGER (0..255)
ProcedureCodeUnsuccessfulOutcome	::= INTEGER (0..255)
ProcedureCodeOutcome				::= INTEGER (0..255)

ProtocolExtensionID	::= INTEGER (0..65535)

ProtocolIE-ID		::= INTEGER {
	id-AreaIdentity 								(0),
	id-CN-DomainIndicator 							(3),
	id-Cause 										(4),
	id-ChosenEncryptionAlgorithm 					(5),
	id-ChosenIntegrityProtectionAlgorithm 			(6),
	id-ClassmarkInformation2 						(7),
	id-ClassmarkInformation3 						(8),
	id-CriticalityDiagnostics 						(9),
	id-DL-GTP-PDU-SequenceNumber 					(10),
	id-EncryptionInformation 						(11),
	id-IntegrityProtectionInformation 				(12),
	id-IuTransportAssociation 						(13),
	id-L3-Information 								(14),
	id-LAI 											(15),
	id-NAS-PDU 										(16),
	id-NonSearchingIndication 						(17),
	id-NumberOfSteps 								(18),
	id-OMC-ID 										(19),
	id-OldBSS-ToNewBSS-Information 					(20),
	id-PagingAreaID 								(21),
	id-PagingCause 									(22),
	id-PermanentNAS-UE-ID 							(23),
	id-RAB-ContextItem 								(24),
	id-RAB-ContextList 								(25),
	id-RAB-DataForwardingItem 						(26),
	id-RAB-DataForwardingItem-SRNS-CtxReq 			(27),
	id-RAB-DataForwardingList 						(28),
	id-RAB-DataForwardingList-SRNS-CtxReq 			(29),
	id-RAB-DataVolumeReportItem 					(30),
	id-RAB-DataVolumeReportList 					(31),
	id-RAB-DataVolumeReportRequestItem 				(32),
	id-RAB-DataVolumeReportRequestList 				(33),
	id-RAB-FailedItem 								(34),
	id-RAB-FailedList 								(35),
	id-RAB-ID 										(36),
	id-RAB-QueuedItem 								(37),
	id-RAB-QueuedList 								(38),
	id-RAB-ReleaseFailedList 						(39),
	id-RAB-ReleaseItem 								(40),
	id-RAB-ReleaseList 								(41),
	id-RAB-ReleasedItem 							(42),
	id-RAB-ReleasedList 							(43),
	id-RAB-ReleasedList-IuRelComp 					(44),
	id-RAB-RelocationReleaseItem 					(45),
	id-RAB-RelocationReleaseList 					(46),
	id-RAB-SetupItem-RelocReq 						(47),
	id-RAB-SetupItem-RelocReqAck 					(48),
	id-RAB-SetupList-RelocReq 						(49),
	id-RAB-SetupList-RelocReqAck 					(50),
	id-RAB-SetupOrModifiedItem 						(51),
	id-RAB-SetupOrModifiedList 						(52),
	id-RAB-SetupOrModifyItem 						(53),
	id-RAB-SetupOrModifyList 						(54),
	id-RAC 											(55),
	id-RelocationType 								(56),
	id-RequestType 									(57),
	id-SAI 											(58),
	id-SAPI 										(59),
	id-SourceID 									(60),
	id-SourceRNC-ToTargetRNC-TransparentContainer 	(61),
	id-TargetID 									(62),
	id-TargetRNC-ToSourceRNC-TransparentContainer 	(63),
	id-TemporaryUE-ID 								(64),
	id-TraceReference 								(65),
	id-TraceType 									(66),
	id-TransportLayerAddress 						(67),
	id-TriggerID 									(68),
	id-UE-ID 										(69),
	id-UL-GTP-PDU-SequenceNumber 					(70),
	id-RAB-FailedtoReportItem						(71),
	id-RAB-FailedtoReportList 						(72),
	id-KeyStatus									(75),
	id-DRX-CycleLengthCoefficient 					(76),
	id-IuSigConIdList								(77),
	id-IuSigConIdItem								(78),
	id-IuSigConId									(79),
	id-DirectTransferInformationList-RANAP-RelocInf	(81),
	id-RAB-ContextItem-RANAP-RelocInf				(82),
	id-RAB-ContextList-RANAP-RelocInf				(83),
	id-RAB-ContextFailedtoTransferItem				(84),
	id-RAB-ContextFailedtoTransferList				(85),
	id-GlobalRNC-ID									(86),
	id-RAB-ReleasedItem-IuRelComp					(87),
	id-MessageStructure								(88),
	id-Alt-RAB-Parameters							(89),
	id-Ass-RAB-Parameters							(90),
	id-RAB-ModifyList								(91),
	id-RAB-ModifyItem								(92),
	id-TypeOfError									(93),
	id-BroadcastAssistanceDataDecipheringKeys		(94),
	id-LocationRelatedDataRequestType				(95),
	id-GlobalCN-ID									(96),
	id-LastKnownServiceArea							(97),
	id-SRB-TrCH-Mapping								(98),
	id-InterSystemInformation-TransparentContainer	(99),
	id-NewBSS-To-OldBSS-Information 						(100),
	id-SourceRNC-PDCP-context-info							(103),
	id-InformationTransferID								(104),
	id-SNA-Access-Information								(105),
	id-ProvidedData											(106),
	id-GERAN-BSC-Container									(107),
	id-GERAN-Classmark										(108),
	id-GERAN-Iumode-RAB-Failed-RABAssgntResponse-Item		(109),
	id-GERAN-Iumode-RAB-FailedList-RABAssgntResponse		(110),
	id-VerticalAccuracyCode									(111),
	id-ResponseTime											(112),
	id-PositioningPriority									(113),
	id-ClientType											(114),
	id-LocationRelatedDataRequestTypeSpecificToGERANIuMode	(115),
	id-SignallingIndication									(116),
	id-hS-DSCH-MAC-d-Flow-ID								(117),
	id-UESBI-Iu												(118),
	id-PositionData											(119),
	id-PositionDataSpecificToGERANIuMode					(120),
	id-CellLoadInformationGroup								(121),
	id-AccuracyFulfilmentIndicator							(122),
	id-InformationTransferType								(123),
	id-TraceRecordingSessionInformation						(124),
	id-TracePropagationParameters							(125),
	id-InterSystemInformationTransferType					(126),
	id-SelectedPLMN-ID										(127),
	id-RedirectionCompleted									(128),
	id-RedirectionIndication								(129),
	id-NAS-SequenceNumber									(130),
	id-RejectCauseValue										(131),
	id-APN													(132),
	id-CNMBMSLinkingInformation								(133),
	id-DeltaRAListofIdleModeUEs								(134),
	id-FrequenceLayerConvergenceFlag						(135),
	id-InformationExchangeID								(136),
	id-InformationExchangeType								(137),
	id-InformationRequested									(138),
	id-InformationRequestType								(139),
	id-IPMulticastAddress									(140),
	id-JoinedMBMSBearerServicesList							(141),
	id-LeftMBMSBearerServicesList							(142),
	id-MBMSBearerServiceType								(143),
	id-MBMSCNDe-Registration								(144),
	id-MBMSServiceArea										(145),
	id-MBMSSessionDuration									(146),
	id-MBMSSessionIdentity									(147),
	id-PDP-TypeInformation									(148),
	id-RAB-Parameters										(149),
	id-RAListofIdleModeUEs									(150),
	id-MBMSRegistrationRequestType							(151),
	id-SessionUpdateID										(152),
	id-TMGI													(153),
	id-TransportLayerInformation							(154),
	id-UnsuccessfulLinkingList								(155),
	id-MBMSLinkingInformation								(156),
	id-MBMSSessionRepetitionNumber							(157),
	id-AlternativeRABConfiguration							(158),
	id-AlternativeRABConfigurationRequest    				(159),
	id-E-DCH-MAC-d-Flow-ID									(160)
	}
(0..65535)

TriggeringMessage	::= ENUMERATED { initiating-message, successful-outcome, unsuccessfull-outcome, outcome }
-- END

-- **************************************************************
--
-- Extension constants
--
-- **************************************************************

maxPrivateIEs 						INTEGER ::= 65535
maxProtocolExtensions 				INTEGER ::= 65535
maxProtocolIEs						INTEGER ::= 65535

--9.3.7	Container Definitions
-- **************************************************************
--
-- Container definitions
--
-- **************************************************************

--RANAP-Containers {
--itu-t (0) identified-organization (4) etsi (0) mobileDomain (0) 
--umts-Access (20) modules (3) ranap (0) version1 (1) ranap-Containers (5) }

--DEFINITIONS AUTOMATIC TAGS ::= 

--BEGIN

-- **************************************************************
--
-- IE parameter types from other modules.
--
-- **************************************************************

--IMPORTS
--	Criticality,
--	Presence,
--	PrivateIE-ID,
--	ProtocolExtensionID,
--	ProtocolIE-ID
--FROM RANAP-CommonDataTypes

--	maxPrivateIEs,
--	maxProtocolExtensions,
--	maxProtocolIEs
--FROM RANAP-Constants;

-- **************************************************************
--
-- Container for Protocol IEs
--
-- **************************************************************


ProtocolIE-Container ::= 
	SEQUENCE (SIZE (0..65535)) OF
	ProtocolIE-Field 

ProtocolIE-Field ::= SEQUENCE {
	id					ProtocolIE-ID,
	criticality			Criticality,
	value				RANAP-PROTOCOL-IES-Value
}


RANAP-PROTOCOL-IES-Value ::= ANY

-- **************************************************************
--
-- Container for Protocol IE Pairs
--
-- **************************************************************

--ProtocolIE-ContainerPair {RANAP-PROTOCOL-IES-PAIR : IEsSetParam} ::= 
--	SEQUENCE (SIZE (0..maxProtocolIEs)) OF
--	ProtocolIE-FieldPair {{IEsSetParam}}

ProtocolIE-ContainerPair ::= 
	SEQUENCE (SIZE (0..65535)) OF
	ProtocolIE-FieldPair 

--ProtocolIE-FieldPair {RANAP-PROTOCOL-IES-PAIR : IEsSetParam} ::= SEQUENCE {
--	id				RANAP-PROTOCOL-IES-PAIR.&id			({IEsSetParam}),
--	firstCriticality		RANAP-PROTOCOL-IES-PAIR.&firstCriticality	({IEsSetParam}{@id}),
--	firstValue			RANAP-PROTOCOL-IES-PAIR.&FirstValue	        ({IEsSetParam}{@id}),
--	secondCriticality		RANAP-PROTOCOL-IES-PAIR.&secondCriticality	({IEsSetParam}{@id}),
--	secondValue			RANAP-PROTOCOL-IES-PAIR.&SecondValue	        ({IEsSetParam}{@id})
--}

ProtocolIE-FieldPair ::= SEQUENCE {
	id						ProtocolIE-ID,
	firstCriticality		Criticality,
	firstValue				FirstValue,
	secondCriticality		Criticality,
	secondValue				SecondValue
}

FirstValue ::= ANY
SecondValue ::= ANY

-- **************************************************************
--
-- Container Lists for Protocol IE Containers
--
-- **************************************************************

--ProtocolIE-ContainerList {INTEGER : lowerBound, INTEGER : upperBound, RANAP-PROTOCOL-IES : IEsSetParam} ::=
--	SEQUENCE (SIZE (lowerBound..upperBound)) OF
--	ProtocolIE-Container {{IEsSetParam}}


ProtocolIE-ContainerList ::=
	SEQUENCE  OF
	ProtocolIE-Container

ProtocolIE-ContainerList15 ::= 
	SEQUENCE  (SIZE (1..15)) OF
	ProtocolIE-Container

ProtocolIE-ContainerList256 ::= 
	SEQUENCE  (SIZE (1..256)) OF
	ProtocolIE-Container

ProtocolIE-ContainerList250 ::= 
	SEQUENCE  (SIZE (1..250)) OF
	ProtocolIE-Container

--ProtocolIE-ContainerPairList {INTEGER : lowerBound, INTEGER : upperBound, RANAP-PROTOCOL-IES-PAIR : IEsSetParam} ::=
--	SEQUENCE (SIZE (lowerBound..upperBound)) OF
--	ProtocolIE-ContainerPair {{IEsSetParam}}

ProtocolIE-ContainerPairList ::=
	SEQUENCE  OF
	ProtocolIE-ContainerPair 

ProtocolIE-ContainerPairList256 ::=
	SEQUENCE  (SIZE (1..256)) OF
	ProtocolIE-ContainerPair

-- **************************************************************
--
-- Container for Protocol Extensions
--
-- **************************************************************

--ProtocolExtensionContainer {RANAP-PROTOCOL-EXTENSION : ExtensionSetParam} ::= 
--	SEQUENCE (SIZE (1..maxProtocolExtensions)) OF
--	ProtocolExtensionField {{ExtensionSetParam}}

ProtocolExtensionContainer ::= 
	SEQUENCE (SIZE (1..65535)) OF
	ProtocolExtensionField 

--ProtocolExtensionField {RANAP-PROTOCOL-EXTENSION : ExtensionSetParam} ::= SEQUENCE {
--	id				RANAP-PROTOCOL-EXTENSION.&id			({ExtensionSetParam}),
--	criticality			RANAP-PROTOCOL-EXTENSION.&criticality		({ExtensionSetParam}{@id}),
--	extensionValue			RANAP-PROTOCOL-EXTENSION.&Extension		({ExtensionSetParam}{@id})
--}

ProtocolExtensionField ::= SEQUENCE {
	id					ProtocolExtensionID,
	criticality			Criticality,
	extensionValue		Extension
}

Extension ::= ANY
-- **************************************************************
--
-- Container for Private IEs
--
-- **************************************************************

--PrivateIE-Container {RANAP-PRIVATE-IES : IEsSetParam } ::= 
--	SEQUENCE (SIZE (1.. maxPrivateIEs)) OF
--	PrivateIE-Field {{IEsSetParam}}

PrivateIE-Container ::= 
	SEQUENCE (SIZE (1.. 65535)) OF
	PrivateIE-Field

--PrivateIE-Field {RANAP-PRIVATE-IES : IEsSetParam} ::= SEQUENCE {
--	id				RANAP-PRIVATE-IES.&id			({IEsSetParam}),
--	criticality			RANAP-PRIVATE-IES.&criticality		({IEsSetParam}{@id}),
--	value			RANAP-PRIVATE-IES.&Value		({IEsSetParam}{@id})
--}
PrivateIE-Field ::= SEQUENCE {
	id				PrivateIE-ID,
	criticality		Criticality,
	value			RANAP-PRIVATE-IES-Value
}

RANAP-PRIVATE-IES-Value ::= ANY

--END

END

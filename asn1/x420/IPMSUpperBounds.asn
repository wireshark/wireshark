-- $Id$
-- Module IPMSUpperBounds (X.420:06/1999)
-- See also ITU-T X.420 (06/1999)
-- See also the index of all ASN.1 assignments needed in this document

IPMSUpperBounds {joint-iso-itu-t mhs(6) ipms(1) modules(0) upper-bounds(10)
  version-1999(1)} DEFINITIONS IMPLICIT TAGS ::=
BEGIN

-- Prologue
-- Exports everything.
IMPORTS -- nothing -- ;

-- Upper bounds
ub-alpha-code-length INTEGER ::= 16

ub-auto-forward-comment INTEGER ::= 256

ub-circulation-list-members INTEGER ::= 256

ub-distribution-codes INTEGER ::= 16

ub-extended-subject-length INTEGER ::= 256

ub-free-form-name INTEGER ::= 64

ub-information-categories INTEGER ::= 16

ub-information-category-length INTEGER ::= 64

ub-ipm-identifier-suffix INTEGER ::= 2

ub-local-ipm-identifier INTEGER ::= 64

ub-manual-handling-instruction-length INTEGER ::= 128

ub-manual-handling-instructions INTEGER ::= 16

ub-originators-reference-length INTEGER ::= 64

ub-precedence INTEGER ::= 127

ub-subject-field INTEGER ::= 128

ub-telephone-number INTEGER ::= 32

END -- of IPMSUpperBounds

-- Generated by Asnp, the ASN.1 pretty-printer of France Telecom R&D

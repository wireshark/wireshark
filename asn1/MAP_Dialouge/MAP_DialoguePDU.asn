MAP-DialogueAS{ ccitt(0) identified-organization(4) etsi(0) mobileDomain(0) gsm-Network(1) 1 map-DialoguePDU(1) version1(1) }

DEFINITIONS::=

BEGIN

MAP-DialoguePDU ::= CHOICE {

	map-open [0] IMPLICIT SEQUENCE {

		destinationReference [0] IMPLICIT DestinationReference OPTIONAL,
		originationReference [1] IMPLICIT OriginationReference OPTIONAL,
		... },

	map-accept [1] IMPLICIT SEQUENCE {
		... },
		map-close [2] IMPLICIT SEQUENCE {
		... },
		map-refuse [3] IMPLICIT SEQUENCE {
			reason Reason,
				... },
		map-userAbort [4] IMPLICIT SEQUENCE {
			map-UserAbortChoice MAP-UserAbortChoice,
			... },
		map-providerAbort [5] IMPLICIT SEQUENCE {
			map-ProviderAbortReason MAP-ProviderAbortReason,
			... }}
-- Ethereal adaptation
ApplicationProcedureCancellation ::= ENUMERATED {
	handoverCancellation (0),
	radioChannelRelease (1),
	networkPathRelease (2),
	callRelease (3),
	associatedProcedureFailure (4),
	tandemDialogueRelease (5),
	remoteOperationsFailure (6)
}


ResourceUnavailable ::= ENUMERATED {
	shortTermResourceLimitation (0),
	longTermResourceLimitation (1)
}
DestinationReference ::= OCTET STRING
OriginationReference ::= OCTET STRING
-- end ethereal adaptation
	MAP-OpenInfo ::= SEQUENCE {
		destinationReference [0] IMPLICIT DestinationReference OPTIONAL,
		originationReference [1] IMPLICIT OriginationReference OPTIONAL,
	... }


	MAP-AcceptInfo ::= SEQUENCE {
	... }


	MAP-CloseInfo ::= SEQUENCE {
	... }


	MAP-RefuseInfo ::= SEQUENCE {
		reason Reason,
		... }

	Reason ::= ENUMERATED {
		noReasonGiven (0),
		invalidDestinationReference (1),
		invalidOriginatingReference (2)}

	MAP-UserAbortInfo ::= SEQUENCE {
		map-UserAbortChoice MAP-UserAbortChoice,
	... }

MAP-UserAbortChoice ::= CHOICE {
	userSpecificReason [0] IMPLICIT NULL,
	userResourceLimitation [1] IMPLICIT NULL,
	resourceUnavailable [2] IMPLICIT ResourceUnavailable,
	applicationProcedureCancellation [3] IMPLICIT ApplicationProcedureCancellation
}

ResourceUnavailableReason ::= ENUMERATED {
	shortTermResourceLimitation (0),
	longTermResourceLimitation (1)
}

ProcedureCancellationReason ::= ENUMERATED {
	handoverCancellation (0),
	radioChannelRelease (1),
	networkPathRelease (2),
	callRelease (3),
	associatedProcedureFailure (4),
	tandemDialogueRelease (5),
	remoteOperationsFailure (6)
}

MAP-ProviderAbortInfo ::= SEQUENCE {
	map-ProviderAbortReason MAP-ProviderAbortReason,
... }

MAP-ProviderAbortReason ::= ENUMERATED {
	abnormalDialogue (0),
	invalidPDU (1)}
END

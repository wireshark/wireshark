-- Module Parameter-ASN1Module (X.721:02/1992)
Parameter-ASN1Module {joint-iso-itu-t ms(9) smi(3) part2(2) asn1Module(2) 3}
DEFINITIONS IMPLICIT TAGS ::=
BEGIN

smi2Parameter OBJECT IDENTIFIER ::=
  {joint-iso-itu-t ms(9) smi(3) part2(2) parameter(5)}

MiscellaneousError ::= NULL

END

-- Generated by Asnp, the ASN.1 pretty-printer of France Telecom R&D

-- Module PKCS-1
-- Transcribed from RFC2313

PKCS-1 {iso(1) member-body(2) us(840) rsadsi(113549) pkcs(1) 1 } DEFINITIONS ::=
BEGIN

IMPORTS
  AlgorithmIdentifier
    FROM AuthenticationFramework {joint-iso-itu-t ds(5) module(1)
      authenticationFramework(7) 4};

--  EXPORTS All 
--  The types and values defined in this module have been transcribed from RFC2313

RSAPublicKey ::= SEQUENCE {
     modulus INTEGER, -- n
     publicExponent INTEGER -- e 
}

RSAPrivateKey ::= SEQUENCE {
     version Version,
     modulus INTEGER, -- n
     publicExponent INTEGER, -- e
     privateExponent INTEGER, -- d
     prime1 INTEGER, -- p
     prime2 INTEGER, -- q
     exponent1 INTEGER, -- d mod (p-1)
     exponent2 INTEGER, -- d mod (q-1)
     coefficient INTEGER -- (inverse of q) mod p 
}

Version ::= INTEGER

DigestInfo ::= SEQUENCE {
     digestAlgorithm DigestAlgorithmIdentifier,
     digest Digest 
}

DigestAlgorithmIdentifier ::= AlgorithmIdentifier

Digest ::= OCTET STRING


-- These algorithms have NULL parameters
-- md2 OBJECT IDENTIFIER ::= { iso(1) member-body(2) US(840) rsadsi(113549) digestAlgorithm(2) 2 }
-- md4 OBJECT IDENTIFIER ::= { iso(1) member-body(2) US(840) rsadsi(113549) digestAlgorithm(2) 4 } 
-- md5 OBJECT IDENTIFIER ::= { iso(1) member-body(2) US(840) rsadsi(113549) digestAlgorithm(2) 5 }


-- pkcs-1 OBJECT IDENTIFIER ::= { iso(1) member-body(2) US(840) rsadsi(113549) pkcs(1) 1 }
-- rsaEncryption OBJECT IDENTIFIER ::= { pkcs-1 1 }
-- md2WithRSAEncryption OBJECT IDENTIFIER ::= { pkcs-1 2 }
-- md4WithRSAEncryption OBJECT IDENTIFIER ::= { pkcs-1 3 }
-- md5WithRSAEncryption OBJECT IDENTIFIER ::= { pkcs-1 4 }

END

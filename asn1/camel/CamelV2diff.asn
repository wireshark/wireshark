-- Hand crafted ASN1 file for the differences between latest spec and V2
-- statments sufixed with V2 to be able to generate this with the latest ASN1 spec.
-- .cnf and -template is used to call the statmets here.

CAP-DataTypesV2 {ccitt(0) identified-organization(4) etsi(0) mobileDomain(0) gsm-Network(1) modules(3)cap-datatypes(52) version2(1)}

--  This module contains the type definitions for the CAP v.2 data types.

DEFINITIONS IMPLICIT TAGS ::=
BEGIN
	IMPORTS

	NAEA-CIC
FROM MAP-CommonDataTypes {itu-t(0) identified-organization(4) etsi(0) mobileDomain(0)
gsm-Network(1) modules(3) map-CommonDataTypes(18) version12(12)}

;

-- From:
-- CAP-Operations {ccitt(0) identified-organization(4) etsi(0) mobileDomain(0)
-- gsm-Network(1) modules(3) cap-operations(50) version2(1)}
--  This module contains the type definitions for the CAP v.2 operations.
EstablishTemporaryConnectionArgV2 	::= SEQUENCE {
	assistingSSPIPRoutingAddress		[0] AssistingSSPIPRoutingAddress,
	correlationID						[1] CorrelationID						OPTIONAL,
	scfID								[3] ScfID								OPTIONAL,
	extensions							[4] SEQUENCE SIZE(1..numOfExtensions)	OF
															ExtensionField 		OPTIONAL,
	serviceInteractionIndicatorsTwo		[7] ServiceInteractionIndicatorsTwo		OPTIONAL,
 	...,
	na-info							[50] NA-Info							OPTIONAL
	}
--	na-info is included at the discretion of the
--	gsmSCF operator.

-- Use of the text parameter is  network operator/equipment vendor specific.
-- End CAP-Operations

--  TYPE DEFINITIONS FOR CAP v.2 DATA TYPES FOLLOW

InitialDPArgExtensionV2				::= SEQUENCE {
	naCarrierInformation				[0] NACarrierInformation				OPTIONAL,
	gmscAddress							[1] ISDN-AddressString					OPTIONAL,
	...


}

NACarrierInformation				::= SEQUENCE {
		naCarrierId						[0] NAEA-CIC								OPTIONAL,
		naCICSelectionType				[1] NACarrierSelectionInfo					OPTIONAL,
		...}

NACarrierSelectionInfo				::= OCTET STRING (SIZE (1))
--  NA carrier selection information octet carries the same values as ANSI
--  ISUP T1.113:				'00'H - not indicated or not explicitly provided
--						'01'H - subscribed not dialed
--						'02'H - subscribed and dialed
--						'03'H - subscribed with dialing undetermined
--						'04'H - dialed CIC not subscribed

NAChargeNumber						::= OCTET STRING (SIZE (2..7))
--  This parameter uniquely identifies the chargeable number for a call sent into a North American
-- long distance carrier. It transports the ChargeNumber Parameter Field
--  as defined in ANSI ISUP T1.113. This provides
--  - 1 octet for the nature of address indicator field, plus
--  - 1 octet for a numbering plan field, plus
--  - up to 5 octets for the address signal (up to 10 digits)

--	The Charge Number in ANSI T1.113 normally contains a 10 digit national number within the North
--	American Numbering Plan (NANP); longer (e.g. international) charge numbers are not supported in
--	T1.113

NA-Info							::= SEQUENCE {
	naCarrierInformation				[0] NACarrierInformation				OPTIONAL,
	naOliInfo							[1] NAOliInfo							OPTIONAL,
	naChargeNumber						[2] NAChargeNumber						OPTIONAL,
	...}


CAMEL-AChBillingChargingCharacteristicsV2 ::= CHOICE {
	timeDurationCharging					[0] SEQUENCE {
			maxCallPeriodDuration				[0] INTEGER (1..864000),
			releaseIfdurationExceeded			[1] ReleaseIfDurationExceeded 	OPTIONAL,
			tariffSwitchInterval				[2] INTEGER (1..86400)			OPTIONAL
		}
	}
--  tariffSwitchInterval is measured in 1 second units.
--  maxCallPeriodDuration is measured in100 millisecond units

ReleaseIfDurationExceeded			::= SEQUENCE {
		tone							BOOLEAN DEFAULT FALSE,
		...,
		extensions						[10] SEQUENCE SIZE(1..numOfExtensions) 			OF
																ExtensionField			OPTIONAL
		}

END

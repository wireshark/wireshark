-- This ASN definition is implemented from hand from itu-t documents

MEDIA-GATEWAY-CONTROL-BCP {itu-t(0) recommendation(0) h(8) h248(248) 
modules(0) media-gateway-control(0) version2(2)} 
DEFINITIONS AUTOMATIC TAGS ::= 
BEGIN 
       
BNCChar ::= ENUMERATED {
	aal1(1),
	aal2(2),
	aal1struct(3),
	ipRtp(4),
	tdm(5)
}

END

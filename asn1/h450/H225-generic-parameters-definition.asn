-- H225-generic-parameters-definition.asn
--
-- Taken from ITU ASN.1 database
-- http://www.itu.int/ITU-T/asn1/database/itu-t/h/h450.1/1998/H225-generic-parameters-definition.asn
--

-- Module H225-generic-parameters-definition (H.450.1:02/1998)
H225-generic-parameters-definition {itu-t recommendation h 450 1 version1(0)
  h225-generic-parameters(6)} DEFINITIONS AUTOMATIC TAGS ::=
BEGIN

H225InformationElement ::= OCTET STRING

END -- of H225 Generic parameters definition

-- Generated by Asnp, the ASN.1 pretty-printer of France Telecom R&D

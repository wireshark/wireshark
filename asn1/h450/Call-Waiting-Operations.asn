-- Call-Waiting-Operations.asn
--
-- Taken from ITU ASN.1 database
-- http://www.itu.int/ITU-T/asn1/database/itu-t/h/h450.6/1999/Call-Waiting-Operations.asn
--
-- $Id$
--

-- Module Call-Waiting-Operations (H.450.6:05/1999)
Call-Waiting-Operations {itu-t recommendation h 450 6 version1(0)
  call-waiting-operations(0)} DEFINITIONS AUTOMATIC TAGS ::=
BEGIN

IMPORTS
  OPERATION, ERROR
    FROM Remote-Operations-Information-Objects {joint-iso-itu-t
      remote-operations(4) informationObjects(5) version1(0)}
  EXTENSION, Extension{}
    FROM Manufacturer-specific-service-extension-definition {itu-t
      recommendation h 450 1 version1(0) msi-definition(18)}
  MixedExtension
    FROM Call-Hold-Operations {itu-t recommendation h 450 4 version1(0)
      call-hold-operations(0)};

CallWaitingOperations OPERATION ::= {callWaiting}

callWaiting OPERATION ::=
  { -- sent from served endpoint to the calling endpoint in ALERTING message
  ARGUMENT         CallWaitingArg
  OPTIONAL         TRUE
  RETURN RESULT    FALSE
  ALWAYS RESPONDS  FALSE
  CODE             local:105
}

CallWaitingArg ::= SEQUENCE {
  nbOfAddWaitingCalls  INTEGER(0..255) OPTIONAL,
  -- indicates the number of waiting calls at the served user 
  -- in addition to the call to which this operation applies.
  extensionArg         SEQUENCE SIZE (0..255) OF MixedExtension OPTIONAL,
  ...
}

END -- of Call-Waiting-Operations

-- Generated by Asnp, the ASN.1 pretty-printer of France Telecom R&D

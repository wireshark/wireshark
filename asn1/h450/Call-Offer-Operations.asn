-- Call-Offer-Operations.asn
--
-- Taken from ITU ASN.1 database
-- http://www.itu.int/ITU-T/asn1/database/itu-t/h/h450.10/2001/Call-Offer-Operations.asn
--
-- $Id$
--

-- Module Call-Offer-Operations (H.450.10:03/2001)
Call-Offer-Operations {itu-t recommendation h 450 10 version1(0)
  call-offer-operations(0)} DEFINITIONS AUTOMATIC TAGS ::=
BEGIN

IMPORTS
  OPERATION, ERROR
    FROM Remote-Operations-Information-Objects {joint-iso-itu-t
      remote-operations(4) informationObjects(5) version1(0)}
  MixedExtension
    FROM Call-Hold-Operations {itu-t recommendation h 450 4 version1(0)
      call-hold-operations(0)}
  callWaiting
    FROM Call-Waiting-Operations {itu-t recommendation h 450 6 version1(0)
      call-waiting-operations(0)};

H323CallOfferOperations OPERATION ::=
  {callOfferRequest | callWaiting | remoteUserAlerting | cfbOverride}

callOfferRequest OPERATION ::= -- sent from calling to called endpoint
   {
  ARGUMENT         CoReqOptArg
  OPTIONAL         TRUE
  RETURN RESULT    FALSE
  ALWAYS RESPONDS  FALSE
  CODE             local:34
}

remoteUserAlerting OPERATION ::= -- sent from called to calling endpoint
   {
  ARGUMENT         RUAlertOptArg
  OPTIONAL         TRUE
  RETURN RESULT    FALSE
  ALWAYS RESPONDS  FALSE
  CODE             local:115
}

cfbOverride OPERATION ::= -- sent from calling to called endpoint
   {
  ARGUMENT         CfbOvrOptArg
  OPTIONAL         TRUE
  RETURN RESULT    FALSE
  ALWAYS RESPONDS  FALSE
  CODE             local:49
}

CoReqOptArg ::= SEQUENCE {
  extension  SEQUENCE SIZE (0..255) OF MixedExtension OPTIONAL,
  ...
}

RUAlertOptArg ::= SEQUENCE {
  extension  SEQUENCE SIZE (0..255) OF MixedExtension OPTIONAL,
  ...
}

CfbOvrOptArg ::= SEQUENCE {
  extension  SEQUENCE SIZE (0..255) OF MixedExtension OPTIONAL,
  ...
}

END -- of Call-Offer-Operations

-- Generated by Asnp, the ASN.1 pretty-printer of France Telecom R&D

-- Module H4501-Supplementary-ServiceAPDU-Structure (H.450.1:02/1998)
H4501-Supplementary-ServiceAPDU-Structure {itu-t recommendation h 450 
  1 version1(0) h4501-facility-information-structure(2)} DEFINITIONS AUTOMATIC
TAGS ::=
BEGIN

IMPORTS
  AliasAddress, PartyNumber, PresentationIndicator, ScreeningIndicator, NonStandardParameter, CallIdentifier
    FROM H323-MESSAGES -- see H.225.0 V2
      
  OPERATION, ROS{}, InvokeId
    FROM Remote-Operations-Apdus {itu-t recommendation h 450 1 version1(0)
      remote-operations-apdus(11)};

H4501SupplementaryService ::= SEQUENCE {
  networkFacilityExtension  NetworkFacilityExtension OPTIONAL, -- see 8.1
  interpretationApdu        InterpretationApdu OPTIONAL, -- see 8.2
  serviceApdu               ServiceApdus, -- H.450.x supplementary services
  ...
}

NetworkFacilityExtension ::= SEQUENCE {
  sourceEntity              EntityType,
  sourceEntityAddress       AddressInformation OPTIONAL,
  destinationEntity         EntityType,
  destinationEntityAddress  AddressInformation OPTIONAL,
  ...
}

EntityType ::= CHOICE {endpoint   NULL,
                       anyEntity  NULL,
                       ...
}

AddressInformation ::= AliasAddress

InterpretationApdu ::= CHOICE {
  discardAnyUnrecognizedInvokePdu       NULL,
  clearCallIfAnyInvokePduNotRecognized  NULL,
  -- this value also applies to Call independent signalling connections 
  rejectAnyUnrecognizedInvokePdu        NULL,
  -- this coding is implied by the absence of an interpretation APDU.
  ...
}

ServiceApdus ::= CHOICE {
  rosApdus
    SEQUENCE OF
      ROS{x--{InvokeIdSet}, {OperationSet}, {OperationSet}--},
  -- see 8.3; other alternatives may be defined in future versions
  ...
}

Notassignedlocalopcode ::= OCTET STRING -- Dummy assigment used

-- actual values are defined by individual supplementary service specifications 
-- (e.g. H.450.x or manufacturer specific)
-- 
-- END of H4501- Supplementary-ServiceAPDU-Structure
-- Imported : 
-- Module Addressing-Data-Elements (H.450.1:02/1998)
-- Addressing-Data-Elements {itu-t recommendation h 450 1 version1(0)
--   addressing-data-elements(9)} DEFINITIONS AUTOMATIC TAGS ::=
PresentedAddressScreened ::= CHOICE {
  presentationAllowedAddress           AddressScreened,
  presentationRestricted               NULL,
  numberNotAvailableDueToInterworking  NULL,
  presentationRestrictedAddress        AddressScreened,
  ...
}

PresentedAddressUnscreened ::= CHOICE {
  presentationAllowedAddress           Address,
  presentationRestricted               NULL,
  numberNotAvailableDueToInterworking  NULL,
  presentationRestrictedAddress        Address,
  ...
}

PresentedNumberScreened ::= CHOICE {
  presentationAllowedAddress           NumberScreened,
  presentationRestricted               NULL,
  numberNotAvailableDueToInterworking  NULL,
  presentationRestrictedAddress        NumberScreened,
  ...
}

PresentedNumberUnscreened ::= CHOICE {
  presentationAllowedAddress           PartyNumber,
  presentationRestricted               NULL,
  numberNotAvailableDueToInterworking  NULL,
  presentationRestrictedAddress        PartyNumber,
  ...
}

AddressScreened ::= SEQUENCE {
  partyNumber         PartyNumber,
  screeningIndicator  ScreeningIndicator,
  partySubaddress     PartySubaddress OPTIONAL,
  ...
}

NumberScreened ::= SEQUENCE {
  partyNumber         PartyNumber,
  screeningIndicator  ScreeningIndicator,
  ...
}

Address ::= SEQUENCE {
  partyNumber      PartyNumber,
  partySubaddress  PartySubaddress OPTIONAL,
  ...
}

-- PartyNumber defined in Recommendation H.225.0
-- PublicPartyNumber defined in Recommendation H.225.0
-- PrivatePartyNumber defined in Recommendation H.225.0
-- NumberDigits defined in Recommendation H.225.0
-- PublicTypeOfNumber defined in Recommendation H.225.0
-- PrivateTypeOfNumber defined in Recommendation H.225.0
-- PresentationIndicator defined in Recommendation H.225.0 (v3 and beyond)
-- ScreeningIndicator defined in Recommendation H.225.0 (v3 and beyond)
EndpointAddress ::= SEQUENCE {
  destinationAddress                              SEQUENCE OF AliasAddress,
  -- multiple alias addresses may be used to address the same H.323 endpoint
  remoteExtensionAddress                          AliasAddress OPTIONAL,
  ...,
  destinationAddressPresentationIndicator
    PresentationIndicator OPTIONAL,
  -- Note 1, 2
  destinationAddressScreeningIndicator            ScreeningIndicator OPTIONAL,
  remoteExtensionAddressPresentationIndicator
    PresentationIndicator OPTIONAL,
  -- Note 1, 2
  remoteExtensionAddressScreeningIndicator        ScreeningIndicator OPTIONAL
}

-- Note 1: If this element is not available, presentation allowed shall be assumed.
-- Note 2: If an H.450 APDU that carries this element EndpointAddress also
-- contains an element PresentationAllowedIndicator, then the setting of the
-- element PresentationAllowedIndicator shall take precedence in case of
-- conflicting presentation information.
PartySubaddress ::= CHOICE {
  userSpecifiedSubaddress  UserSpecifiedSubaddress,
  -- not recommended.
  nsapSubaddress           NSAPSubaddress,
  -- according to Recommendation X.213. 
  ...
}

UserSpecifiedSubaddress ::= SEQUENCE {
  subaddressInformation  SubaddressInformation,
  oddCountIndicator      BOOLEAN OPTIONAL,
  -- used when the coding of subaddress is BCD
  ...
}

NSAPSubaddress ::= OCTET STRING(SIZE (1..20))

-- specified according to X.213. Some networks may
-- limit the subaddress value to some other length
-- e.g. 4 octets
SubaddressInformation ::= OCTET STRING(SIZE (1..20))

-- coded according to user requirements. Some networks 
-- may limit the subaddress value to some other length
-- e.g. 4 octets
PresentationAllowedIndicator ::= BOOLEAN

--END 
-- of Addressing-Data-Elements

-- Module Call-Transfer-Operations (H.450.2:02/1998)
-- Call-Transfer-Operations {itu-t recommendation h 450 2 version1(0)
--  call-transfer-operations(0)} DEFINITIONS AUTOMATIC TAGS ::=
--  Edited for Wireshark purposes

CallTransferIdentify ::= DummyArg
CallTransferAbandon ::= DummyArg
CallTransferInitiate ::= CTInitiateArg
CallTransferSetup ::= CTSetupArg
CallTransferUpdate ::= CTUpdateArg
SubaddressTransfer ::= SubaddressTransferArg
CallTransferComplete ::= CTCompleteArg
CallTransferActive ::= CTActiveArg

DummyArg ::= CHOICE {
  extensionSeq     ExtensionSeq,
  nonStandardData  NonStandardParameter
}
DummyRes ::= CHOICE {
  extensionSeq     ExtensionSeq,
  nonStandardData  NonStandardParameter
}

CTInitiateArg ::= SEQUENCE {
  callIdentity       CallIdentity,
  reroutingNumber    EndpointAddress,
  argumentExtension  ArgumentExtension OPTIONAL,
  ...
}
ArgumentExtension ::= CHOICE {extensionSeq     ExtensionSeq,
            nonStandardData  NonStandardParameter}

CTSetupArg ::= SEQUENCE {
  callIdentity        CallIdentity,
  transferringNumber  EndpointAddress OPTIONAL,
  argumentExtension   ArgumentExtension OPTIONAL,
  ...
}

CTIdentifyRes ::= SEQUENCE {
  callIdentity     CallIdentity,
  reroutingNumber  EndpointAddress,
  resultExtension
    CHOICE {extensionSeq     ExtensionSeq,
            nonStandardData  NonStandardParameter} OPTIONAL,
  ...
}

CTUpdateArg ::= SEQUENCE {
  redirectionNumber      EndpointAddress,
  redirectionInfo        BMPString(SIZE (1..128)) OPTIONAL,
  basicCallInfoElements  H225InformationElement OPTIONAL,
  -- Information element 
  -- Progress indicator may be conveyed
  argumentExtension      ArgumentExtension OPTIONAL,
  ...
}

SubaddressTransferArg ::= SEQUENCE {
  redirectionSubaddress  PartySubaddress,
  argumentExtension      ArgumentExtension OPTIONAL,
  ...
}

CTCompleteArg ::= SEQUENCE {
  endDesignation         EndDesignation,
  redirectionNumber      EndpointAddress,
  -- number of new connected user
  basicCallInfoElements  H225InformationElement OPTIONAL,
  -- Information element Progress indicator may be conveyed
  redirectionInfo        BMPString(SIZE (1..128)) OPTIONAL,
  callStatus             CallStatus DEFAULT answered,
  argumentExtension      ArgumentExtension OPTIONAL,
  ...
}

EndDesignation ::= ENUMERATED {primaryEnd(0), secondaryEnd(1), ...
                               }

CallStatus ::= ENUMERATED {answered(0), alerting(1), ...
                           }

CTActiveArg ::= SEQUENCE {
  connectedAddress       EndpointAddress,
  -- number of new connected user
  basicCallInfoElements  H225InformationElement OPTIONAL,
  -- Information element Progress indicator may be conveyed
  connectedInfo          BMPString(SIZE (1..128)) OPTIONAL,
  argumentExtension      ArgumentExtension OPTIONAL,
  ...
}

CallIdentity ::= NumericString(SIZE (0..4))
-- size 0 means 'empty'

ExtensionSeq ::= SEQUENCE OF Extension
--END 
-- of Call-Transfer-Operations

-- Module Call-Diversion-Operations (H.450.3:02/1998)
--Call-Diversion-Operations {itu-t recommendation h 450 3 version1(0)
--  call-diversion-operations(0)} DEFINITIONS AUTOMATIC TAGS ::=
--BEGIN
--
--IMPORTS
--  OPERATION, ERROR
--    FROM Remote-Operations-Information-Objects {joint-iso-itu-t
--      remote-operations(4) informationObjects(5) version1(0)}
--  EXTENSION, Extension{}
--    FROM Manufacturer-specific-service-extension-definition {itu-t
--      recommendation h 450 1 version1(0) msi-definition(18)}
--  H225InformationElement
--    FROM H225-generic-parameters-definition {itu-t recommendation h 450 
--      1 version1(0) h225-generic-parameters(6)}
--  NonStandardParameter
--    FROM H323-MESSAGES
--  EndpointAddress, PartySubaddress, PresentationAllowedIndicator
--    FROM Addressing-Data-Elements {itu-t recommendation h 450 1 version1(0)
--      addressing-data-elements(9)}
--  userNotSubscribed, notAvailable, invalidServedUserNumber,
--    basicServiceNotProvided, resourceUnavailable,
--    supplementaryServiceInteractionNotAllowed
--    FROM H4501-General-Error-List {itu-t recommendation h 450 1 version1(0)
--      general-error-list(1)};
-- activateDiversionQ OPERATION ::=
--  { sent from the activating h.323-endpoint to the served h.323-endpoint
--  ARGUMENT
ActivateDiversionQArg ::=    SEQUENCE {procedure          Procedure,
              basicService       BasicService,
              divertedToAddress  EndpointAddress,
              servedUserNr       EndpointAddress,
              activatingUserNr   EndpointAddress,
              extension
                CHOICE {extensionSeq     ExtensionSeq,
                        nonStandardData  NonStandardParameter} OPTIONAL,
              ...}
--  RESULT
ActivateDiversionQRes ::=
    CHOICE {extensionSeq     ExtensionSeq,
            nonStandardData  NonStandardParameter}

-- deactivateDiversionQ OPERATION ::=
--  {  sent from the deactivating h.323-endpoint to the served h.323-endpoint
--  ARGUMENT
DeactivateDiversionQArg ::=
    SEQUENCE {procedure           Procedure,
              basicService        BasicService,
              servedUserNr        EndpointAddress,
              deactivatingUserNr  EndpointAddress,
              extension
                CHOICE {extensionSeq     ExtensionSeq,
                        nonStandardData  NonStandardParameter} OPTIONAL,
              ...}
--  RESULT
DeactivateDiversionQRes ::=
    CHOICE {extensionSeq     ExtensionSeq,
            nonStandardData  NonStandardParameter}
--  OPTIONAL  TRUE
--  ERRORS
--    {userNotSubscribed | notAvailable | invalidServedUserNumber |
--      temporarilyUnavailable | notAuthorized | unspecified}
--  CODE      local:16
--}

-- interrogateDiversionQ OPERATION ::=
--  {  sent from the interrogating h.323-endpoint to the served h.323-endpoint
--  ARGUMENT
InterrogateDiversionQ ::=   SEQUENCE {procedure            Procedure,
              basicService         BasicService DEFAULT allServices,
              servedUserNr         EndpointAddress,
              interrogatingUserNr  EndpointAddress,
              extension
                CHOICE {extensionSeq     ExtensionSeq,
                        nonStandardData  NonStandardParameter} OPTIONAL,
              ...}
--  RESULT    IntResultList
InterrogateDiversionQRes ::= IntResultList

--  ERRORS
--    {userNotSubscribed | notAvailable | invalidServedUserNumber |
--      temporarilyUnavailable | notAuthorized | unspecified}
--  CODE      local:17
--}

-- checkRestriction OPERATION ::=
--  {  sent from the served h.323-endpoint to the diverted-to h.323-endpoint
--  ARGUMENT
CheckRestrictionArg ::=
    SEQUENCE {servedUserNr  EndpointAddress,
              basicService  BasicService,
              divertedToNr  EndpointAddress,
              extension
                CHOICE {extensionSeq     ExtensionSeq,
                        nonStandardData  NonStandardParameter} OPTIONAL,
              ...}
 -- RESULT
CheckRestrictionRes ::=    CHOICE {extensionSeq     ExtensionSeq,
            nonStandardData  NonStandardParameter}
-- OPTIONAL  TRUE
--  ERRORS
--    {notAvailable | invalidServedUserNumber | invalidDivertedNumber |
--      specialServiceNumber | unspecified}
--  CODE      local:18
--}

-- callRerouting OPERATION ::=
--  {  sent from the served h.323-endpoint to the rerouting h.323-endpoint
--  ARGUMENT
CallReroutingArg ::=
    SEQUENCE {reroutingReason          DiversionReason,
              originalReroutingReason  DiversionReason OPTIONAL,
              calledAddress            EndpointAddress,
              diversionCounter         INTEGER(1..15),
              h225InfoElement          H225InformationElement,
              -- The H.225 information elements Bearer capability, 
              -- High layer compatibility, Low layer compatibility and 
              -- Progress Indicator information element may  be embedded 
              -- in the h225InfoElement in accordance with H.450.1. 
              lastReroutingNr          EndpointAddress,
              subscriptionOption       SubscriptionOption,
              callingPartySubaddress   PartySubaddress OPTIONAL,
              callingNumber            EndpointAddress,
              callingInfo              BMPString(SIZE (1..128)) OPTIONAL,
              originalCalledNr         EndpointAddress OPTIONAL,
              redirectingInfo          BMPString(SIZE (1..128)) OPTIONAL,
              originalCalledInfo       BMPString(SIZE (1..128)) OPTIONAL,
              extension
                CHOICE {extensionSeq     ExtensionSeq,
                        nonStandardData  NonStandardParameter} OPTIONAL,
              ...}
--  RESULT
CallReroutingRes ::=    CHOICE {extensionSeq     ExtensionSeq,
            nonStandardData  NonStandardParameter}

--  OPTIONAL  TRUE
--  ERRORS
--    {userNotSubscribed | notAvailable | resourceUnavailable |
--      invalidDivertedNumber | specialServiceNumber |
--      diversionToServedUserNumber | numberOfDiversionsExceeded |
--      supplementaryServiceInteractionNotAllowed | unspecified}
--  CODE      local:19
-- }

-- divertingLegInformation1 OPERATION ::=
--  {  sent from the re-routing h.323-endpoint to the originating h.323-endpoint  
-- if the re-routing endpoint equals the originating endpoint, this operation 

  -- is not applicable; may also be sent from the rerouting endpoint to other 
  -- members of a conference, if subscription option allows. 
--  ARGUMENT
DivertingLegInformation1Arg ::=
    SEQUENCE {diversionReason     DiversionReason,
              subscriptionOption  SubscriptionOption,
              nominatedNr         EndpointAddress,
              nominatedInfo       BMPString(SIZE (1..128)) OPTIONAL,
              redirectingNr       EndpointAddress OPTIONAL,
              redirectingInfo     BMPString(SIZE (1..128)) OPTIONAL,
              extension
                CHOICE {extensionSeq     ExtensionSeq,
                        nonStandardData  NonStandardParameter} OPTIONAL,
              ...}
 -- RETURN RESULT    FALSE
 -- ALWAYS RESPONDS  FALSE
 -- CODE             local:20
--}

-- divertingLegInformation2 OPERATION ::=
--  { sent from the re-routing h.323-endpoint to the diverted-to h.323-endpoint 
--  ARGUMENT
DivertingLegInformation2Arg ::=
    SEQUENCE {diversionCounter         INTEGER(1..15),
              diversionReason          DiversionReason,
              originalDiversionReason  DiversionReason OPTIONAL,
              divertingNr              EndpointAddress OPTIONAL,
              originalCalledNr         EndpointAddress OPTIONAL,
              redirectingInfo          BMPString(SIZE (1..128)) OPTIONAL,
              originalCalledInfo       BMPString(SIZE (1..128)) OPTIONAL,
              extension
                CHOICE {extensionSeq     ExtensionSeq,
                        nonStandardData  NonStandardParameter} OPTIONAL,
              ...}
  -- The divertingNr element is mandatory except in the case of interworking
 -- RETURN RESULT    FALSE
 -- ALWAYS RESPONDS  FALSE
 -- CODE             local:21
--}

-- divertingLegInformation3 OPERATION ::= {
  --sent from the diverted-to h.323-endpoint to the originating h.323-endpoint
--  ARGUMENT
DivertingLegInformation3Arg ::=
    SEQUENCE {presentationAllowedIndicator  PresentationAllowedIndicator,
              redirectionNr                 EndpointAddress OPTIONAL,
              redirectionInfo               BMPString(SIZE (1..128)) OPTIONAL,
              extension
                CHOICE {extensionSeq     ExtensionSeq,
                        nonStandardData  NonStandardParameter} OPTIONAL,
              ...}
--  RETURN RESULT    FALSE
--  ALWAYS RESPONDS  FALSE
--  CODE             local:22
--}

-- divertingLegInformation4 OPERATION ::= {
  -- If call diversion in not performed by the forwarding terminal but by a
  --  gatekeeper, the gatekeeper may send divertingLegInformation4 apdu to the 
  -- forwarding terminal. 
--  ARGUMENT
DivertingLegInformation4Arg ::=    SEQUENCE {diversionReason     DiversionReason,
              subscriptionOption  SubscriptionOption,
              callingNr           EndpointAddress,
              callingInfo         BMPString(SIZE (1..128)) OPTIONAL,
              nominatedNr         EndpointAddress,
              nominatedInfo       BMPString(SIZE (1..128)) OPTIONAL,
              extension
                CHOICE {extensionSeq     ExtensionSeq,
                        nonStandardData  NonStandardParameter} OPTIONAL,
              ...}
--  RETURN RESULT    FALSE
--  ALWAYS RESPONDS  FALSE
--  CODE             local:100
--}

-- cfnrDivertedLegFailed OPERATION ::=
--  {  sent from the rerouting h.323-terminal to the served  h.323-endpoint
--  ARGUMENT
CfnrDivertedLegFailedArg ::=
    CHOICE {extensionSeq     ExtensionSeq,
            nonStandardData  NonStandardParameter}
--  OPTIONAL         TRUE
--  RETURN RESULT    FALSE
--  ALWAYS RESPONDS  FALSE
--  CODE             local:23
-- }

-- This indicates that the diverted-to leg has been cleared during SS-CFNR execution.
-- Definitions of general used data types:
DiversionReason ::= ENUMERATED {unknown(0), cfu(1), cfb(2), cfnr(3), ...
                                }

-- The value unknown is only used if received from another network when interworking.
IntResultList ::= SET SIZE (0..29) OF IntResult

IntResult ::= SEQUENCE {
  servedUserNr       EndpointAddress,
  basicService       BasicService,
  procedure          Procedure,
  divertedToAddress  EndpointAddress,
  remoteEnabled      BOOLEAN DEFAULT FALSE,
  extension
    CHOICE {extensionSeq     ExtensionSeq,
            nonStandardData  NonStandardParameter} OPTIONAL,
  ...
}

Procedure ::= ENUMERATED {cfu(0), cfb(1), cfnr(2), ...
                          }

SubscriptionOption ::= ENUMERATED {
  noNotification(0), notificationWithoutDivertedToNr(1),
  notificationWithDivertedToNr(2), ...
  }

-- invalidDivertedNumber ERROR ::= {CODE  local:12
-- }

-- specialServiceNumber ERROR ::= {CODE  local:14
-- }

-- diversionToServedUserNumber ERROR ::= {CODE  local:15
-- }

-- numberOfDiversionsExceeded ERROR ::= {CODE  local:24
-- }

-- temporarilyUnavailable ERROR ::= {CODE  local:1000
-- }

-- notAuthorized ERROR ::= {CODE  local:1007
-- }

-- unspecified ERROR ::= {
--   PARAMETER
--     CHOICE {extension    Extension,
--             nonStandard  NonStandardParameter}
--   CODE       local:1008
-- }
-- BasicService defined for MWI should do for Wireshark purposes
 -- BasicService ::= ENUMERATED {
 -- allServices(0),
  -- speech (1),
  -- unrestrictedDigitalInformation (2),
  -- audio3.1KHz (3),
  -- telephony (32),
  -- teletex (33),
  -- telefaxGroup4Class1 (34),
  -- videotexSyntaxBased (35),
  -- videotelephony (36), 
--  ...
--  }

-- For multimedia calls the value "allServices" shall be used only. 
-- The usage of the other codepoints for multimedia calls is for further study.
-- Defined elsewhere for Wireshark
-- ExtensionSeq ::= SEQUENCE OF Extension
--
-- ExtensionSet EXTENSION ::=
--  {...}

-- Actual values defined by individual manufacturers
-- END 
-- of Call-Diversion-Operations

-- Module Call-Hold-Operations (H.450.4:05/1999)
-- Call-Hold-Operations {itu-t recommendation h 450 4 version1(0)
--   call-hold-operations(0)} DEFINITIONS AUTOMATIC TAGS ::=
-- BEGIN

-- IMPORTS
--   OPERATION, ERROR
--     FROM Remote-Operations-Information-Objects {joint-iso-itu-t
--       remote-operations(4) informationObjects(5) version1(0)}
--   EXTENSION, Extension{}
--     FROM Manufacturer-specific-service-extension-definition {itu-t
--       recommendation h 450 1 version1(0) msi-definition(18)}
--   notAvailable, invalidCallState, resourceUnavailable,
--     supplementaryServiceInteractionNotAllowed
--     FROM H4501-General-Error-List {itu-t recommendation h 450 1 version1(0)
--       general-error-list(1)}
--   NonStandardParameter
--     FROM H323-MESSAGES; 
-- see H.225.0

-- CallHoldOperations OPERATION ::=
--   {holdNotific | retrieveNotific | remoteHold | remoteRetrieve}

-- holdNotific OPERATION ::=
--   {  sent from holding to held H.323 endpoint to invoke near-end call hold feature
-- 
--   ARGUMENT         HoldNotificArg
--   OPTIONAL         TRUE
--   RETURN RESULT    FALSE
--   ALWAYS RESPONDS  FALSE
--   CODE             local:101
-- }

HoldNotificArg ::= SEQUENCE {
  extensionArg  SEQUENCE SIZE (0..255) OF MixedExtension OPTIONAL,
  ...
}

-- retrieveNotific OPERATION ::=
--   {  sent from holding to held H.323 endpoint to invoke retrieval of near-end call hold feature

--   ARGUMENT         RetrieveNotificArg
--   OPTIONAL         TRUE
--   RETURN RESULT    FALSE
--   ALWAYS RESPONDS  FALSE
--   CODE             local:102
-- }

RetrieveNotificArg ::= SEQUENCE {
  extensionArg  SEQUENCE SIZE (0..255) OF MixedExtension OPTIONAL,
  ...
 }

-- remoteHold OPERATION ::=
--   { sent from holding to held H.323 endpoint to invoke remote-end call hold feature

--   ARGUMENT  RemoteHoldArg
--   OPTIONAL  TRUE
--   RESULT    RemoteHoldRes
--   OPTIONAL  TRUE
--   ERRORS
--     {notAvailable
--       |  feature not available in combination with the basic service
--        invalidCallState |  hold not possible in current call state
--        resourceUnavailable |  maximum number of calls on hold reached
--        supplementaryServiceInteractionNotAllowed |
      
      -- other supplementary service prohibits hold
--       undefined -- -- undefined reason--
-- }
--   CODE      local:103
-- }

RemoteHoldArg ::= SEQUENCE {
  extensionArg  SEQUENCE SIZE (0..255) OF MixedExtension OPTIONAL,
  ...
}

RemoteHoldRes ::= SEQUENCE {
  extensionRes  SEQUENCE SIZE (0..255) OF MixedExtension OPTIONAL,
  ...
}

-- remoteRetrieve OPERATION ::=
--   {  sent from holding to held H.323 endpoint to invoke retrieval of remote-end call hold feature

--   ARGUMENT  RemoteRetrieveArg
--   OPTIONAL  TRUE
--   RESULT    RemoteRetrieveRes
--   OPTIONAL  TRUE
--   ERRORS
--     {invalidCallState |
      
      -- Call to which retrieve request applies is not in state Hold_RE_Held
--       undefined --  -- undefined reason  } --
--   CODE      local:104
-- }

RemoteRetrieveArg ::= SEQUENCE {
  extensionArg  SEQUENCE SIZE (0..255) OF MixedExtension OPTIONAL,
  ...
}

RemoteRetrieveRes ::= SEQUENCE {
  extensionRes  SEQUENCE SIZE (0..255) OF MixedExtension OPTIONAL,
  ...
}

MixedExtension ::= CHOICE {
  extension        Extension,
  nonStandardData  NonStandardParameter
}

-- ExtensionSet EXTENSION ::=
--   {...}

-- Actual values defined by individual manufacturers
-- undefined ERROR ::= {
--   PARAMETER  SEQUENCE SIZE (0..255) OF MixedExtension
--   OPTIONAL   TRUE
--   CODE       local:2002
-- }

-- END 
-- of Call-Hold-Operations



-- Module Call-Park-Pickup-Operations (H.450.5:05/1999)
-- Call-Park-Pickup-Operations {itu-t recommendation h 450 5 version1(0)
--   call-park-pickup-operations(0)} DEFINITIONS AUTOMATIC TAGS ::=
-- BEGIN
-- 
-- IMPORTS
--   OPERATION, ERROR
--     FROM Remote-Operations-Information-Objects {joint-iso-itu-t
--       remote-operations(4) informationObjects(5) version1(0)}
--   EXTENSION, Extension{}
--     FROM Manufacturer-specific-service-extension-definition {itu-t
--       recommendation h 450 1 version1(0) msi-definition(18)}
--   notAvailable, invalidCallState, resourceUnavailable,
--     supplementaryServiceInteractionNotAllowed
--     FROM H4501-General-Error-List {itu-t recommendation h 450 1 version1(0)
--       general-error-list(1)}
--   EndpointAddress
--     FROM Addressing-Data-Elements {itu-t recommendation h 450 1 version1(0)
--       addressing-data-elements(9)}
--   MixedExtension
--     FROM Call-Hold-Operations {itu-t recommendation h 450 4 version1(0)
--       call-hold-operations(0)}
--   NonStandardParameter, CallIdentifier
--     FROM H323-MESSAGES; 
-- see H.225.0

-- CallParkPickupOperations OPERATION ::=
--   {cpRequest | cpSetup | groupIndicationOn | groupIndicationOff | pickrequ |
--    pickup | pickExe | cpNotify | cpickupNotify}

-- cpRequest OPERATION ::=
--   { sent from parking endpoint to the parked endpoint to invoke SS-PARK
--   ARGUMENT  CpRequestArg
--   RESULT    CpRequestRes
--   ERRORS
--     {notAvailable |
      
      -- feature not available in combination with the basic service
 --      invalidCallState |  call park not possible in current call state
 --       resourceUnavailable |  maximum number of parked calls reached
 --       supplementaryServiceInteractionNotAllowed |
      
      -- other supplementary service prohibits call park invocation
--       undefined undefined reason  } --
--   CODE      local:106
-- }

CpRequestArg ::= SEQUENCE {
  parkingNumber     EndpointAddress,
  parkedNumber      EndpointAddress,
  parkedToNumber    EndpointAddress,
  parkedToPosition  ParkedToPosition OPTIONAL,
  extensionArg      SEQUENCE SIZE (0..255) OF MixedExtension OPTIONAL,
  ...
}

CpRequestRes ::= SEQUENCE {
  parkedToNumber    EndpointAddress,
  parkedToPosition  ParkedToPosition OPTIONAL,
  parkCondition     ParkCondition,
  extensionRes      SEQUENCE SIZE (0..255) OF MixedExtension OPTIONAL,
  ...
}

-- cpSetup OPERATION ::= {   sent from parked endpoint to the parked-to endpoint 
--   ARGUMENT  CpSetupArg
--   RESULT    CpSetupRes
--   ERRORS
--     {notAvailable |
      
      -- feature not available in combination with the basic service
 --      invalidCallState |  call park not possible in current call state
 --       resourceUnavailable |  maximum number of parked calls reached
 --       supplementaryServiceInteractionNotAllowed |
      
      -- other supplementary service prohibits call park invocation
 --      undefined  undefined reason }
 --  CODE      local:107
-- }

CpSetupArg ::= SEQUENCE {
  parkingNumber     EndpointAddress,
  parkedNumber      EndpointAddress,
  parkedToNumber    EndpointAddress,
  parkedToPosition  ParkedToPosition OPTIONAL,
  extensionArg      SEQUENCE SIZE (0..255) OF MixedExtension OPTIONAL,
  ...
}

CpSetupRes ::= SEQUENCE {
  parkedToNumber    EndpointAddress,
  parkedToPosition  ParkedToPosition OPTIONAL,
  parkCondition     ParkCondition,
  extensionRes      SEQUENCE SIZE (0..255) OF MixedExtension OPTIONAL,
  ...
}

-- groupIndicationOn OPERATION ::=
--   { sent from the parked-to endpoint/alerting endpoint to the group members 
--   ARGUMENT  GroupIndicationOnArg
--   RESULT    GroupIndicationOnRes
--   ERRORS    {undefined undefined reason  } --
--   CODE      local:108
-- }

GroupIndicationOnArg ::= SEQUENCE {
  callPickupId       CallIdentifier,
  -- identification of the call to be retrieved (parked or alerting call);
  -- its value equals the value of the CallIdentifier as assigned for the parked/
  -- alerting call within Setup-UUIE
  groupMemberUserNr  EndpointAddress,
  retrieveCallType   CallType,
  partyToRetrieve    EndpointAddress, -- Parked or Calling User 
  retrieveAddress    EndpointAddress, -- parked-to or alerting entity address
  
  -- (may also be a GK, see 9.2)
  parkPosition       ParkedToPosition OPTIONAL,
  extensionArg       SEQUENCE SIZE (0..255) OF MixedExtension OPTIONAL,
  ...
}

GroupIndicationOnRes ::= SEQUENCE {
  extensionRes  SEQUENCE SIZE (0..255) OF MixedExtension OPTIONAL,
  ...
}

-- groupIndicationOff OPERATION ::=
--   { sent from the parked-to endpoint/alerting endpoint to the group members 
--   ARGUMENT  GroupIndicationOffArg
--   RESULT    GroupIndicationOffRes
--   ERRORS
--     {invalidCallState |  group indication is not on
--        undefined undefined reason  } --
--   CODE      local:109
-- }

GroupIndicationOffArg ::= SEQUENCE {
  callPickupId       CallIdentifier,
  -- identification of the call that has been picked up (parked or alerting call)
  groupMemberUserNr  EndpointAddress,
  extensionArg       SEQUENCE SIZE (0..255) OF MixedExtension OPTIONAL,
  ...
}

GroupIndicationOffRes ::= SEQUENCE {
  extensionRes  SEQUENCE SIZE (0..255) OF MixedExtension OPTIONAL,
  ...
}

-- pickrequ OPERATION ::= { sent from the picking-up user to the parked-to/
  -- alerting endpoint as part of the SS-PICKUP invocation
--   ARGUMENT  PickrequArg
--   RESULT    PickrequRes
--   ERRORS
--    {undefined |  undefined reason
      
--       callAlreadyPickedUp  call has already been picked up by another user }
--   CODE      local:110
-- }

PickrequArg ::= SEQUENCE {
  picking-upNumber  EndpointAddress,
  callPickupId      CallIdentifier OPTIONAL,
  -- identification of the call to be picked up (parked or alerting call), if known
  partyToRetrieve   EndpointAddress OPTIONAL, -- Parked or Calling User
  retrieveAddress   EndpointAddress, -- parked-to or alerting entity address
  parkPosition      ParkedToPosition OPTIONAL,
  extensionArg      SEQUENCE SIZE (0..255) OF MixedExtension OPTIONAL,
  ...
}

PickrequRes ::= SEQUENCE {
  callPickupId  CallIdentifier,
  -- identification of the call that is being picked up (parked or alerting call), 
  -- if not sent in pickrequ invoke, it is assigned at the parked-to/alerting
  -- endpoint and reflects the CallIdentification of the parked/alerting call for
  -- later association with the pickExe invoke APDU. 
  extensionRes  SEQUENCE SIZE (0..255) OF MixedExtension OPTIONAL,
  ...
}

-- pickup OPERATION ::=
--   { sent from the parked-to/alerting endpoint to the parked/calling endpoint
  -- after the picking-up user has invoked SS-PICKUP. The picking-up user may
  -- be local (i.e. parked-to/alerting endpoint equals picking-up
  -- endpoint) or may be remote (i.e. picking-up user is located at a
  -- remote picking-up endpoint having sent pickrequ invoke APDU to the
  -- parked-to/alerting endpoint). 
--   ARGUMENT  PickupArg
--   RESULT    PickupRes
--   ERRORS
--     {undefined |  undefined reason
      
--       callAlreadyPickedUp  call has already been picked up by another user }
--   CODE      local:111
-- }

PickupArg ::= SEQUENCE {
  callPickupId      CallIdentifier,
  -- identification of this call to be picked up (parked or alerting call); 
  -- equals the CallIdentifier value that was assigned to this call in Setup-UUIE
  picking-upNumber  EndpointAddress,
  extensionArg      SEQUENCE SIZE (0..255) OF MixedExtension OPTIONAL,
  ...
}

PickupRes ::= SEQUENCE {
  extensionRes  SEQUENCE SIZE (0..255) OF MixedExtension OPTIONAL,
  ...
}

-- pickExe OPERATION ::=
--   { sent from the parked/calling endpoint to the picking-up endpoint
--   ARGUMENT  PickExeArg
--   RESULT    PickExeRes
--   ERRORS
--     {undefined |  undefined reason
      
--       callPickupIdInvalid
      -- value not matching with the previous SS-PICKUP request
--       }
--   CODE      local:112
-- }

PickExeArg ::= SEQUENCE {
  callPickupId      CallIdentifier,
  -- identification of the parked/alerting call to be picked-up; 
  -- required at picking-up endpoint to associate the SS-PICKUP invoked with this
  -- incoming setup message carrying the pickExe invoke APDU.
  picking-upNumber  EndpointAddress,
  partyToRetrieve   EndpointAddress, -- Parked or Calling User
  extensionArg      SEQUENCE SIZE (0..255) OF MixedExtension OPTIONAL,
  ...
}

PickExeRes ::= SEQUENCE {
  extensionRes  SEQUENCE SIZE (0..255) OF MixedExtension OPTIONAL,
  ...
}

-- cpNotify OPERATION ::=
--   { sent from the parking-to to parked endpoint in case of local park.
--   ARGUMENT         CpNotifyArg
--   OPTIONAL         TRUE
--   RETURN RESULT    FALSE
--   ALWAYS RESPONDS  FALSE
--   CODE             local:113
-- }

CpNotifyArg ::= SEQUENCE {
  parkingNumber  EndpointAddress OPTIONAL,
  extensionArg   SEQUENCE SIZE (0..255) OF MixedExtension OPTIONAL,
  ...
}

-- cpickupNotify OPERATION ::=
--   { sent from parked-to to parked endpoint in case of SS-PICKUP from local park

--   ARGUMENT         CpickupNotifyArg
--   OPTIONAL         TRUE
--   RETURN RESULT    FALSE
--   ALWAYS RESPONDS  FALSE
--   CODE             local:114
-- }

CpickupNotifyArg ::= SEQUENCE {
  picking-upNumber  EndpointAddress OPTIONAL,
  extensionArg      SEQUENCE SIZE (0..255) OF MixedExtension OPTIONAL,
  ...
}

ParkedToPosition ::= INTEGER(0..65535)

ParkCondition ::= ENUMERATED {
  unspecified(0), parkedToUserIdle(1), parkedToUserBusy(2), parkedToGroup(3),
  ...
  }

CallType ::= ENUMERATED {parkedCall(0), alertingCall(1), ...
                         }

-- callPickupIdInvalid ERROR ::= {CODE  local:2000
-- }

-- callAlreadyPickedUp ERROR ::= {CODE  local:2001
-- }

-- undefined ERROR ::= {
--   PARAMETER  SEQUENCE SIZE (0..255) OF MixedExtension
--   OPTIONAL   TRUE
--   CODE       local:2002
-- }

-- END 
-- of Call-Park-Pickup-Operations

-- Module Call-Waiting-Operations (H.450.6:05/1999)
-- Call-Waiting-Operations {itu-t recommendation h 450 6 version1(0)
--   call-waiting-operations(0)} DEFINITIONS AUTOMATIC TAGS ::=
-- BEGIN

-- IMPORTS
--   OPERATION, ERROR
--     FROM Remote-Operations-Information-Objects {joint-iso-itu-t
--       remote-operations(4) informationObjects(5) version1(0)}
--   EXTENSION, Extension{}
--     FROM Manufacturer-specific-service-extension-definition {itu-t
--       recommendation h 450 1 version1(0) msi-definition(18)}
--   MixedExtension
--     FROM Call-Hold-Operations {itu-t recommendation h 450 4 version1(0)
--       call-hold-operations(0)};

-- CallWaitingOperations OPERATION ::= {callWaiting}

-- callWaiting OPERATION ::=
--   {  sent from served endpoint to the calling endpoint in ALERTING message
--   ARGUMENT         CallWaitingArg
--   OPTIONAL         TRUE
--   RETURN RESULT    FALSE
--   ALWAYS RESPONDS  FALSE
--   CODE             local:105
-- }

CallWaitingArg ::= SEQUENCE {
  nbOfAddWaitingCalls  INTEGER(0..255) OPTIONAL,
  -- indicates the number of waiting calls at the served user 
  -- in addition to the call to which this operation applies.
  extensionArg         SEQUENCE SIZE (0..255) OF MixedExtension OPTIONAL,
  ...
}

-- END 
-- of Call-Waiting-Operations


-- Module Message-Waiting-Indication-Operations (H.450.7:05/1999)
--Message-Waiting-Indication-Operations {itu-t recommendation h 450 7 version1(0)
--  message-waiting-operations(0)} DEFINITIONS AUTOMATIC TAGS ::=
--H323-MWI-Operations OPERATION ::=
--  {mwiActivate | mwiDeactivate | mwiInterrogate}

MwiActivate ::= MWIActivateArg
MwiDeactivate ::= MWIDeactivateArg

MwiInterrogate ::= MWIInterrogateArg

MWIActivateArg ::= SEQUENCE {
  servedUserNr   EndpointAddress,
  basicService   BasicService,
  msgCentreId    MsgCentreId OPTIONAL,
  nbOfMessages   NbOfMessages OPTIONAL,
  originatingNr  EndpointAddress OPTIONAL,
  timestamp      TimeStamp OPTIONAL,
  priority       INTEGER(0..9) OPTIONAL,
  -- the value 0 means the highest priority and 9 the lowest
  extensionArg   ExtensionArg OPTIONAL,
  ...
}

MwiDummyRes ::= SEQUENCE SIZE (0..255) OF MixedExtension

MWIDeactivateArg ::= SEQUENCE {
  servedUserNr  EndpointAddress,
  basicService  BasicService,
  msgCentreId   MsgCentreId OPTIONAL,
  callbackReq   BOOLEAN OPTIONAL,
  extensionArg  ExtensionArg OPTIONAL,
  ...
}

MWIInterrogateArg ::= SEQUENCE {
  servedUserNr  EndpointAddress,
  basicService  BasicService,
  msgCentreId   MsgCentreId OPTIONAL,
  callbackReq   BOOLEAN OPTIONAL,
  extensionArg  ExtensionArg OPTIONAL,
  ...
}

MWIInterrogateRes ::= SEQUENCE SIZE (1..64) OF MWIInterrogateResElt

MWIInterrogateResElt ::= SEQUENCE {
  basicService   BasicService,
  msgCentreId    MsgCentreId OPTIONAL,
  nbOfMessages   NbOfMessages OPTIONAL,
  originatingNr  EndpointAddress OPTIONAL,
  timestamp      TimeStamp OPTIONAL,
  priority       INTEGER(0..9) OPTIONAL,
  -- the value 0 means the highest priority and 9 the lowest
  extensionArg   ExtensionArg OPTIONAL,
  ...
}

MsgCentreId ::= CHOICE {
  -- only partyNumber provides a callable identification
  integer        INTEGER(0..65535),
  mwipartyNumber    EndpointAddress,
  numericString  NumericString(SIZE (1..10))
}

NbOfMessages ::= INTEGER(0..65535)

TimeStamp ::= GeneralizedTime(SIZE (12..19))

ExtensionArg ::= SEQUENCE SIZE (0..255) OF MixedExtension

-- a VisibleString representation of date and time following ISO 8601 
-- containing:
--	- the (local) date in 8 digits (YYYYMMDD),
--	- followed by (local) time of day in 4 or 6 digits [HHMM(SS)],
--	-	optionally followed by the letter "Z" or by a local time differential 
--		from UTC time in 5 digits ("+"HHMM or "-"HHMM);
-- Examples:
--	1) 19970621194530, meaning 21 June 1997, 19:45:30;
--	2) 19970621194530Z, meaning the same as 1);
--	3) 19970621194530-0500, meaning the same as 1), 
--		5 hours retarded in relation to UTC time
--undefined ERROR ::= {
--  PARAMETER  SEQUENCE SIZE (0..255) OF MixedExtension
--  OPTIONAL   TRUE
--  CODE       local:2002
--}

--invalidMsgCentreId ERROR ::=
--  {  returned by a Message Centre endpoint when an unknown Message 
  -- Centre Identifier is specified in a mwiInterrogate invoke
--  CODE  local:1018
--}

BasicService ::= ENUMERATED {
  -- MWI Services:
  --	for compatibility among vendors, speech is recommended for voice mail
  --	indications
  allServices(0), speech(1), unrestrictedDigitalInformation(2), audio3100Hz(3),
  telephony(32), teletex(33), telefaxGroup4Class1(34), videotexSyntaxBased(35),
  videotelephony(36), telefaxGroup2-3(37), reservedNotUsed1(38),
  reservedNotUsed2(39), reservedNotUsed3(40), reservedNotUsed4(41),
  reservedNotUsed5(42),
  --
  -- MWI Service Classes:
  email(51), video(52), fileTransfer(53), shortMessageService(54),
  speechAndVideo(55), speechAndFax(56), speechAndEmail(57), videoAndFax(58),
  videoAndEmail(59), faxAndEmail(60), speechVideoAndFax(61),
  speechVideoAndEmail(62), speechFaxAndEmail(63), videoFaxAndEmail(64),
  speechVideoFaxAndEmail(65), multimediaUnknown(66),
  serviceUnknown(67),
  --
  -- Reserved for future additions:
  futureReserve1(68), futureReserve2(69), futureReserve3(70),
  futureReserve4(71), futureReserve5(72), futureReserve6(73),
  futureReserve7(74), futureReserve8(75)}

-- notActivated ERROR ::= {CODE  local:31
-- }

--END 
-- of Message-Waiting-Indication-Operations

-- Module Name-Operations (H.450.8:02/2000)
-- Name-Operations {itu-t recommendation h 450 8 version1(0) name-operations(0)}
-- DEFINITIONS AUTOMATIC TAGS ::=
-- BEGIN

-- IMPORTS
--   OPERATION, ERROR
--     FROM Remote-Operations-Information-Objects {joint-iso-itu-t
--       remote-operations(4) informationObjects(5) version1(0)}
--   EXTENSION, Extension{}
--     FROM Manufacturer-specific-service-extension-definition {itu-t
--       recommendation h 450 1 version1(0) msi-definition(18)}
--   MixedExtension
--     FROM Call-Hold-Operations {itu-t recommendation h 450 4 version1(0)
--       call-hold-operations(0)};

-- NameOperations OPERATION ::=
--   {callingName | alertingName | connectedName | busyName}

-- callingName OPERATION ::= {
--   ARGUMENT
--     SEQUENCE {name          Name,
--               extensionArg  SEQUENCE SIZE (0..255) OF MixedExtension OPTIONAL,
--              ...}
--   RETURN RESULT    FALSE
--   ALWAYS RESPONDS  FALSE
--   CODE             local:0
-- }

-- alertingName OPERATION ::= {
--   ARGUMENT
--     SEQUENCE {name          Name,
--               extensionArg  SEQUENCE SIZE (0..255) OF MixedExtension OPTIONAL,
--              ...}
--   RETURN RESULT    FALSE
--   ALWAYS RESPONDS  FALSE
--   CODE             local:1
-- }

-- connectedName OPERATION ::= {
--   ARGUMENT
--     SEQUENCE {name          Name,
--               extensionArg  SEQUENCE SIZE (0..255) OF MixedExtension OPTIONAL,
--               ...}
--   RETURN RESULT    FALSE
--   ALWAYS RESPONDS  FALSE
--   CODE             local:2
-- }


-- busyName OPERATION ::= {
--   ARGUMENT
--     SEQUENCE {name          Name,
--               extensionArg  SEQUENCE SIZE (0..255) OF MixedExtension OPTIONAL,
--               ...}
--   RETURN RESULT    FALSE
--   ALWAYS RESPONDS  FALSE
--   CODE             local:3
-- }
-- It all translates to NameArg doesn't it ?

NameArg ::= SEQUENCE {name          Name,
               extensionArg  SEQUENCE SIZE (0..255) OF MixedExtension OPTIONAL,
               ...}

Name ::= CHOICE {
  namePresentationAllowed     NamePresentationAllowed,
  namePresentationRestricted  NamePresentationRestricted,
  nameNotAvailable            NULL,
  ...
}

NamePresentationAllowed ::= CHOICE {
  simpleName    SimpleName,
  extendedName  ExtendedName,
  ...
}

NamePresentationRestricted ::= CHOICE {
  simpleName      SimpleName,
  extendedName    ExtendedName,
  restrictedNull  NULL, -- only used in case of interworking where other network
  
  -- provides indication that the name is restricted without
  -- the name itself
  ...
}

SimpleName ::= OCTET STRING(SIZE (1..50))

ExtendedName ::= BMPString(SIZE (1..256)) -- Basic ISO/IEC 10646-1 (Unicode)
                          
-- 
-- END 
-- of Name-Operations
-- Module Call-Completion-Operations (H.450.9:11/2000)
-- Call-Completion-Operations {itu-t recommendation h 450 9 version1(0)
--   call-completion-operations(0)} DEFINITIONS AUTOMATIC TAGS ::=
-- BEGIN

-- IMPORTS
--   OPERATION, ERROR
--     FROM Remote-Operations-Information-Objects {joint-iso-itu-t
--       remote-operations(4) informationObjects(5) version1(0)}
--   EXTENSION, Extension{}
--     FROM Manufacturer-specific-service-extension-definition {itu-t
--       recommendation h 450 1 version1(0) msi-definition(18)}
--   CallIdentifier
--     FROM H323-MESSAGES see ITU-T H.225.0
--       
--   EndpointAddress
--     FROM Addressing-Data-Elements {itu-t recommendation h 450 1 version1(0)
--       addressing-data-elements(9)}
--   MixedExtension, undefined
--     FROM Call-Hold-Operations {itu-t recommendation h 450 4 version1(0)
--       call-hold-operations(0)}
--   supplementaryServiceInteractionNotAllowed
--     FROM H4501-General-Error-List {itu-t recommendation h 450 1 version1(0)
--       general-error-list(1)}
--   BasicService
--     FROM Message-Waiting-Indication-Operations {itu-t recommendation h 
--       450 7 version1(0) message-waiting-operations(0)};

-- H323CallCompletionOperations OPERATION ::=
--   {ccbsRequest | ccnrRequest | ccCancel | ccExecPossible | ccRingout |
--    ccSuspend | ccResume}

-- ccbsRequest OPERATION ::= {
--   ARGUMENT  CcRequestArg
--   RESULT    CcRequestRes
--   ERRORS
--     {shortTermRejection | longTermRejection | undefined |
--       supplementaryServiceInteractionNotAllowed}
--   CODE      local:40
-- }

-- ccnrRequest OPERATION ::= {
--   ARGUMENT  CcRequestArg
--   RESULT    CcRequestRes
--   ERRORS
--     {shortTermRejection | longTermRejection | undefined |
--       supplementaryServiceInteractionNotAllowed}
--   CODE      local:27
-- }

-- ccCancel OPERATION ::= {
--   ARGUMENT         CcArg
--   OPTIONAL         TRUE
--   RETURN RESULT    FALSE
--   ALWAYS RESPONDS  FALSE
--   CODE             local:28
-- }

-- ccExecPossible OPERATION ::= {
--   ARGUMENT         CcArg
--   OPTIONAL         TRUE
--   RETURN RESULT    FALSE
--   ALWAYS RESPONDS  FALSE
--   CODE             local:29
-- }

-- ccRingout OPERATION ::= {
--   ARGUMENT       CcShortArg
--   OPTIONAL       TRUE
--   RETURN RESULT  FALSE
--   ERRORS         {remoteUserBusyAgain | failureToMatch | undefined}
--   CODE           local:31
-- }

-- ccSuspend OPERATION ::= {
--   ARGUMENT         CcShortArg
--   OPTIONAL         TRUE
--   RETURN RESULT    FALSE
--   ALWAYS RESPONDS  FALSE
--   CODE             local:32
-- }

-- ccResume OPERATION ::= {
--   ARGUMENT         CcArg
--   OPTIONAL         TRUE
--   RETURN RESULT    FALSE
--   ALWAYS RESPONDS  FALSE
--   CODE             local:33
-- }

CcRequestArg ::= SEQUENCE {
  numberA                EndpointAddress,
  numberB                EndpointAddress,
  ccIdentifier           CallIdentifier OPTIONAL,
  -- If present, it shall be used as the prime mechanism for associating 
  -- the unsuccessful call, the CC Request and the CC Call.
  service                BasicService,
  can-retain-service     BOOLEAN,
  retain-sig-connection  BOOLEAN OPTIONAL,
  extension              SEQUENCE SIZE (0..255) OF MixedExtension OPTIONAL,
  ...
}

CcRequestRes ::= SEQUENCE {
  retain-service  BOOLEAN,
  extension       SEQUENCE SIZE (0..255) OF MixedExtension OPTIONAL,
  ...
}

CcArg ::= CHOICE {
  shortArg  CcShortArg, -- if signalling conection is retained
  longArg   CcLongArg, -- if connection release option applies
  ...
}

CcShortArg ::= SEQUENCE {
  ccIdentifier  CallIdentifier OPTIONAL,
  extension     SEQUENCE SIZE (0..255) OF MixedExtension OPTIONAL,
  ...
}

CcLongArg ::= SEQUENCE {
  numberA       EndpointAddress OPTIONAL,
  numberB       EndpointAddress OPTIONAL,
  ccIdentifier  CallIdentifier OPTIONAL,
  service       BasicService OPTIONAL,
  -- these elements are used to identify the proper CC Request. 
  -- The ccIdentifier if present shall be the prime mechanism for this purpose.
  extension     SEQUENCE SIZE (0..255) OF MixedExtension OPTIONAL,
  ...
}

-- shortTermRejection ERROR ::= {CODE  local:1010
-- }

-- longTermRejection ERROR ::= {CODE  local:1011
-- }

-- remoteUserBusyAgain ERROR ::= {CODE  local:1012
-- }

-- failureToMatch ERROR ::= {CODE  local:1013
-- }

-- END 
-- of Call-Completion-Operations

-- Module Call-Offer-Operations (H.450.10:03/2001)
-- Call-Offer-Operations {itu-t recommendation h 450 10 version1(0)
--   call-offer-operations(0)} DEFINITIONS AUTOMATIC TAGS ::=
-- BEGIN
-- 
-- IMPORTS
--   OPERATION, ERROR
--     FROM Remote-Operations-Information-Objects {joint-iso-itu-t
--       remote-operations(4) informationObjects(5) version1(0)}
--   MixedExtension
--     FROM Call-Hold-Operations {itu-t recommendation h 450 4 version1(0)
--       call-hold-operations(0)}
--   callWaiting
--     FROM Call-Waiting-Operations {itu-t recommendation h 450 6 version1(0)
--       call-waiting-operations(0)};

-- H323CallOfferOperations OPERATION ::=
--   {callOfferRequest | callWaiting | remoteUserAlerting | cfbOverride}

-- callOfferRequest OPERATION ::= sent from calling to called endpoint
--    {
--   ARGUMENT         CoReqOptArg
--   OPTIONAL         TRUE
--   RETURN RESULT    FALSE
--   ALWAYS RESPONDS  FALSE
--   CODE             local:34
-- }

-- remoteUserAlerting OPERATION ::=  sent from called to calling endpoint
--    {
--   ARGUMENT         RUAlertOptArg
--   OPTIONAL         TRUE
--   RETURN RESULT    FALSE
--   ALWAYS RESPONDS  FALSE
--   CODE             local:115
-- }

-- cfbOverride OPERATION ::=  sent from calling to called endpoint
--    {
--   ARGUMENT         CfbOvrOptArg
--   OPTIONAL         TRUE
--   RETURN RESULT    FALSE
--   ALWAYS RESPONDS  FALSE
--   CODE             local:49
-- }

CoReqOptArg ::= SEQUENCE {
  extension  SEQUENCE SIZE (0..255) OF MixedExtension OPTIONAL,
  ...
}

RUAlertOptArg ::= SEQUENCE {
  extension  SEQUENCE SIZE (0..255) OF MixedExtension OPTIONAL,
  ...
}

CfbOvrOptArg ::= SEQUENCE {
  extension  SEQUENCE SIZE (0..255) OF MixedExtension OPTIONAL,
  ...
}

-- END 
-- of Call-Offer-Operations
-- Module Call-Intrusion-Operations (H.450.11:03/2001)
-- Call-Intrusion-Operations {itu-t recommendation h 450 11 version1(0)
--   call-intrusion-operations(0)} DEFINITIONS AUTOMATIC TAGS ::=
-- BEGIN

-- IMPORTS
--   OPERATION, ERROR
--     FROM Remote-Operations-Information-Objects {joint-iso-itu-t
--       remote-operations(4) informationObjects(5) version1(0)}
--   CallIdentifier
--     FROM H323-MESSAGES  see H.225.0
      
--   MixedExtension, undefined
--     FROM Call-Hold-Operations {itu-t recommendation h 450 4 version1(0)
--       call-hold-operations(0)}
--   notAvailable, supplementaryServiceInteractionNotAllowed
--     FROM H4501-General-Error-List {itu-t recommendation h 450 1 version1(0)
--       general-error-list(1)}
--   callWaiting
--     FROM Call-Waiting-Operations {itu-t recommendation h 450 6 version1(0)
--       call-waiting-operations(0)}
--   cfbOverride, remoteUserAlerting
--     FROM Call-Offer-Operations {itu-t recommendation h 450 10 version1(0)
--       call-offer-operations(0)};

-- H323CallIntrusionOperations OPERATION ::=
--   {callIntrusionRequest | callIntrusionGetCIPL | callIntrusionIsolate |
--    callIntrusionForcedRelease | callIntrusionWOBRequest |
--    callIntrusionSilentMonitor | callIntrusionNotification | cfbOverride |
--    remoteUserAlerting | callWaiting}

-- callWaiting is only used for interaction with Call Transfer 
-- callIntrusionRequest OPERATION ::= {
--   ARGUMENT  CIRequestArg
--   RESULT    CIRequestRes
--   ERRORS
--     {notAvailable | notBusy | temporarilyUnavailable | notAuthorized |
--       undefined | supplementaryServiceInteractionNotAllowed}
--   CODE      local:43
-- }

-- callIntrusionGetCIPL OPERATION ::= {
--   ARGUMENT         CIGetCIPLOptArg
--   OPTIONAL         TRUE
--   RESULT           CIGetCIPLRes
--   ALWAYS RESPONDS  FALSE
--   CODE             local:44
-- }

-- callIntrusionIsolate OPERATION ::= {
--   ARGUMENT  CIIsOptArg
--   OPTIONAL  TRUE
--   RESULT    CIIsOptRes
--   OPTIONAL  TRUE
--   ERRORS
--     {notAvailable | undefined | supplementaryServiceInteractionNotAllowed}
--   CODE      local:45
-- }

-- callIntrusionForcedRelease OPERATION ::= {
--   ARGUMENT  CIFrcRelArg
--   OPTIONAL  TRUE
--   RESULT    CIFrcRelOptRes
--   OPTIONAL  TRUE
--   ERRORS
--     {notAvailable | notBusy | temporarilyUnavailable | notAuthorized |
--       undefined | supplementaryServiceInteractionNotAllowed}
--   CODE      local:46
-- }

-- callIntrusionWOBRequest OPERATION ::= {
--   ARGUMENT  CIWobOptArg
--   OPTIONAL  TRUE
--   RESULT    CIWobOptRes
--   OPTIONAL  TRUE
--   ERRORS
--     {notAvailable | undefined | supplementaryServiceInteractionNotAllowed}
--   CODE      local:47
-- }

-- callIntrusionSilentMonitor OPERATION ::= {
--   ARGUMENT  CISilentArg
--   RESULT    CISilentOptRes
--   OPTIONAL  TRUE
--   ERRORS
--     {notAvailable | notBusy | temporarilyUnavailable | notAuthorized |
--       undefined | supplementaryServiceInteractionNotAllowed}
--   CODE      local:116
-- }

-- callIntrusionNotification OPERATION ::= {
--   ARGUMENT         CINotificationArg
--   RETURN RESULT    FALSE
--   ALWAYS RESPONDS  FALSE
--   CODE             local:117
-- }

CIRequestArg ::= SEQUENCE {
  ciCapabilityLevel  CICapabilityLevel,
  argumentExtension  SEQUENCE SIZE (0..255) OF MixedExtension OPTIONAL,
  ...
}

CIRequestRes ::= SEQUENCE {
  ciStatusInformation  CIStatusInformation,
  resultExtension      SEQUENCE SIZE (0..255) OF MixedExtension OPTIONAL,
  ...
}

CIGetCIPLOptArg ::= SEQUENCE {
  argumentExtension  SEQUENCE SIZE (0..255) OF MixedExtension OPTIONAL,
  ...
}

CIGetCIPLRes ::= SEQUENCE {
  ciProtectionLevel          CIProtectionLevel,
  silentMonitoringPermitted  NULL OPTIONAL,
  resultExtension            SEQUENCE SIZE (0..255) OF MixedExtension OPTIONAL,
  ...
}

CIIsOptArg ::= SEQUENCE {
  argumentExtension  SEQUENCE SIZE (0..255) OF MixedExtension OPTIONAL,
  ...
}

CIIsOptRes ::= SEQUENCE {
  resultExtension  SEQUENCE SIZE (0..255) OF MixedExtension OPTIONAL,
  ...
}

CIFrcRelArg ::= SEQUENCE {
  ciCapabilityLevel  CICapabilityLevel,
  argumentExtension  SEQUENCE SIZE (0..255) OF MixedExtension OPTIONAL,
  ...
}

CIFrcRelOptRes ::= SEQUENCE {
  resultExtension  SEQUENCE SIZE (0..255) OF MixedExtension OPTIONAL,
  ...
}

CIWobOptArg ::= SEQUENCE {
  argumentExtension  SEQUENCE SIZE (0..255) OF MixedExtension OPTIONAL,
  ...
}

CIWobOptRes ::= SEQUENCE {
  resultExtension  SEQUENCE SIZE (0..255) OF MixedExtension OPTIONAL,
  ...
}

CISilentArg ::= SEQUENCE {
  ciCapabilityLevel  CICapabilityLevel,
  specificCall       CallIdentifier OPTIONAL,
  argumentExtension  SEQUENCE SIZE (0..255) OF MixedExtension OPTIONAL,
  ...
}

CISilentOptRes ::= SEQUENCE {
  resultExtension  SEQUENCE SIZE (0..255) OF MixedExtension OPTIONAL,
  ...
}

CINotificationArg ::= SEQUENCE {
  ciStatusInformation  CIStatusInformation,
  argumentExtension    SEQUENCE SIZE (0..255) OF MixedExtension OPTIONAL,
  ...
}

CICapabilityLevel ::= INTEGER {
  intrusionLowCap(1), intrusionMediumCap(2), intrusionHighCap(3)}(1..3)

CIProtectionLevel ::= INTEGER {
  lowProtection(0), mediumProtection(1), highProtection(2), fullProtection(3)
}(0..3)

CIStatusInformation ::= CHOICE {
  callIntrusionImpending  NULL,
  callIntruded            NULL,
  callIsolated            NULL,
  callForceReleased       NULL,
  callIntrusionComplete   NULL,
  callIntrusionEnd        NULL,
  ...
}

-- notBusy ERROR ::= {CODE  local:1009
-- }  used when the called user is not busy

-- temporarilyUnavailable ERROR ::= {CODE  local:1000
-- }  used when conditions for invocation of SS-CI

-- are momentarily not met
-- notAuthorized ERROR ::= {CODE  local:1007
-- } used when a SS-CI request is rejected

-- because of insufficient CICL or if silent
-- monitoring is not permitted
-- END 
-- of Call-Intrusion-Operations

-- Module Common-Information-Operations (H.450.12:07/2001)
-- Common-Information-Operations {itu-t recommendation h 450 12 version1(0)
--   common-information-operations(0)} DEFINITIONS AUTOMATIC TAGS ::=
-- BEGIN

-- IMPORTS
--   OPERATION, ERROR
--     FROM Remote-Operations-Information-Objects {joint-iso-itu-t
--       remote-operations(4) informationObjects(5) version1(0)}
--   EXTENSION, Extension{}
--     FROM Manufacturer-specific-service-extension-definition {itu-t
--       recommendation h 450 1 version1(0) msi-definition(18)}
--   MixedExtension, undefined
--     FROM Call-Hold-Operations {itu-t recommendation h 450 4 version1(0)
--       call-hold-operations(0)};

-- H323CommonInformationOperations OPERATION ::= {cmnRequest | cmnInform}

-- cmnRequest OPERATION ::= {
--   ARGUMENT  DummyArg  used as CmnRequestArg ( Wireshark )
--   OPTIONAL  TRUE
--   RESULT    CmnArg
--   ERRORS    {undefined}
--   CODE      local:84
-- }

-- cmnInform OPERATION ::= {
--   ARGUMENT         CmnArg
--   RETURN RESULT    FALSE
--   ALWAYS RESPONDS  FALSE
--   CODE             local:85
-- }

CmnArg ::= SEQUENCE {
  featureList     FeatureList OPTIONAL,
  featureValues   FeatureValues OPTIONAL,
  featureControl  FeatureControl OPTIONAL,
  extension       SEQUENCE SIZE (0..255) OF MixedExtension OPTIONAL,
  ...
}

CmnRequestArg ::= SEQUENCE {
  extensionArg  SEQUENCE SIZE (0..255) OF MixedExtension OPTIONAL
}

FeatureList ::= SEQUENCE {
  -- indicates capabilities of the endpoint sending the FeatureList
  ssCFreRoutingSupported         NULL OPTIONAL, -- Call Forwarding rerouting
  
  -- supported meaningful only in
  -- forward direction during call
  -- establishment 
  ssCTreRoutingSupported         NULL OPTIONAL, -- Call Transfer rerouting
  
  -- supported meaningful both in
  -- forward & backward direction
  -- during call establishment 
  ssCCBSPossible                 NULL OPTIONAL, -- CCBS possible meaningful only
  
  -- in backward direction before
  -- receipt of ALERTING/CONNECT 
  ssCCNRPossible                 NULL OPTIONAL, -- CCNR possible meaningful only
  
  -- in backward direction before
  -- receipt of CONNECT 
  ssCOSupported                  NULL OPTIONAL, -- Call Offer supported
  
  -- meaningful only in backward
  -- direction during call
  -- establishment 
  -- Call Intrusion
  ssCIForcedReleaseSupported     NULL OPTIONAL, -- meaningful only in
  
  -- backward direction 
  ssCIIsolationSupported         NULL OPTIONAL, -- meaningful only in
  
  -- backward direction 
  ssCIWaitOnBusySupported        NULL OPTIONAL, -- meaningful only in
  
  -- backward direction 
  ssCISilentMonitoringSupported  NULL OPTIONAL, -- meaningful only in
  
  -- backward direction 
  ssCIConferenceSupported        NULL OPTIONAL, -- meaningful only in
  
  -- backward direction 
  -- Call Hold
  ssCHFarHoldSupported           NULL OPTIONAL, -- meaningful in both
  
  -- directions
  -- Message Waiting Callback
  ssMWICallbackSupported         NULL OPTIONAL, -- meaningful in backward
  
  -- direction
  -- meaningful both in
  -- forward & backward
  -- direction during call
  -- establishment
  -- Call Park
  ssCPCallParkSupported          NULL OPTIONAL, -- meaningful in both
  
  -- directions
  ...
}

FeatureValues ::= SEQUENCE {
  partyCategory        PartyCategory OPTIONAL,
  ssCIprotectionLevel  SSCIProtectionLevel OPTIONAL,
  -- Supplementary Service Call Intrusion Protection level
  -- meaningful both in forward and backward direction; inclusion
  -- indicates support of SS-CI as an unwanted endpoint (forward 
  -- direction) or as a Terminating  Endpoint (backward direction),
  -- as well as the applicable protection level.
  ...
}

PartyCategory ::= ENUMERATED {unknown, extension, attendant, emergExt, ...
                              }

SSCIProtectionLevel ::= INTEGER(0..3)

FeatureControl ::= SEQUENCE {
  ssCHDoNotHold               NULL OPTIONAL, -- meaningful in both directions
  
  -- Sending endpoint shall not be held
  ssCTDoNotTransfer           NULL OPTIONAL, -- meaningful in both directions
  
  -- sending endpoint shall not be transferred
  ssMWICallbackCall           NULL OPTIONAL, -- meaningful only in SETUP 
  
  -- indicating a callback call
  ssCISilentMonitorPermitted  NULL OPTIONAL, -- unwanted endpoint
  
  -- allows for 
  -- silent monitoring
  -- meaningful in forward and backward direction
  ...
}

-- END 
-- of Common-Information-Operations




--
-- Module Manufacturer-specific-service-extension-definition (H.450.1:02/1998)
-- Manufacturer-specific-service-extension-definition {itu-t recommendation 
--  h 450 1 version1(0) msi-definition(18)} DEFINITIONS AUTOMATIC TAGS ::=
-- BEGIN

-- Actual values defined by individual manufacturers
Unspecified ::= 
    CHOICE {extension    Extension,
            nonStandard  NonStandardParameter}

-- invalidReroutingNumber ERROR ::= {
  -- used when establishment of the new connection fails
  -- because the reroutingNumber is not a valid alias address
--  CODE  local:1004
-- }

-- UnrecognizedCallIdentity ERROR ::= {
  -- used when establishment of the new connection fails because it
  -- could not be associated with a SS-CT entity at the 
  -- transferred-to endpoint
--  CODE  local:1005
--}

--establishmentFailure ERROR ::= {
  -- used when establishment of the new connection fails and
  -- no other error applies
--  CODE  local:1006
--}

-- END 
-- of Call-Transfer-Operations
-- Module H225-generic-parameters-definition (H.450.1:02/1998)
-- H225-generic-parameters-definition {itu-t recommendation h 450 1 version1(0)
--  h225-generic-parameters(6)} DEFINITIONS AUTOMATIC TAGS ::=

H225InformationElement ::= OCTET STRING

--END 
-- of H225 Generic parameters definition
-- Module Manufacturer-specific-service-extension-definition (H.450.1:02/1998)


-- Manufacturer-specific-service-extension-definition {itu-t recommendation 
--   h 450 1 version1(0) msi-definition(18)} DEFINITIONS AUTOMATIC TAGS ::=
-- BEGIN

-- EXTENSION ::= CLASS {&ArgumentType  ,
--                     &extensionId   OBJECT IDENTIFIER
-- }WITH SYNTAX {ARGUMENT &ArgumentType
--              IDENTIFIER &extensionId
-- }

-- Extension{EXTENSION:ExtensionSet} ::= SEQUENCE {
--  extensionId        EXTENSION.&extensionId({ExtensionSet}),
--  extensionArgument  EXTENSION.&ArgumentType({ExtensionSet}{@extensionId})
--}
-- Wireshark adaptation NEEDS VERIFICATION !
 Extension ::= SEQUENCE {
  extensionId        OBJECT IDENTIFIER,
  extensionArgument  ExtensionArgument
  }
ExtensionArgument ::= OCTET STRING

-- ExtensionSet is a set of objects of class EXTENSION.
-- Actual values of ExtensionSet are defined by the individual manufacturers. 
-- Element extensionId is constrained to be the identifier of an object from that set.
-- Element extensionArgument is constrained to be the argument type for that particular
-- object.
-- END 
-- of Manufacturer-specific-service-extension-definition

END -- of H4501- Supplementary-ServiceAPDU-Structure 

-- Generated by Asnp, the ASN.1 pretty-printer of France Telecom R&D

-- $Id$
-- Module IN-CS-1-Datatypes-appendix (Q.1218:10/1995)
IN-CS-1-DataTypes-appendix {itu-t recommendation q 1218 modules(0)
  cs-1-datatypes-app(6) version1(0)}
--  This module contains additional type definitions for the IN CS-1 data types.
DEFINITIONS IMPLICIT TAGS ::=
BEGIN

IMPORTS
  LegID, CorrelationID
    FROM IN-CS-1-Datatypes {itu-t recommendation q 1218 modules(0)
      cs-1-datatypes(2) version1(0)};

--  TYPE DEFINITION FOR ADDITIONAL	IN CS-1	DATA TYPES
--  Argument Data Types
AddPartyArg ::= SEQUENCE {
  originalCallID     [0]  CallID OPTIONAL,
  destinationCallID  [1]  CallID OPTIONAL
}

--  OPTIONAL denotes network operator specific use.
AttachArg ::= SEQUENCE {
  newLegID               [0]  LegID OPTIONAL,
  correlationidentifier  [1]  CorrelationID OPTIONAL
}

--  OPTIONAL denotes network operator specific use.
CallPartyHandlingResultsArg ::= SEQUENCE OF LegInformation

ChangePartiesArg ::= SEQUENCE {
  callID              [0]  CallID OPTIONAL,
  targetCallID        [1]  CallID,
  legToBeConnectedID  [2]  LegID
}

--  OPTIONAL denotes network operator specific use.
DetachArg ::= SEQUENCE {
  legToBeDetached        [0]  LegID OPTIONAL,
  correlationidentifier  [1]  CorrelationID OPTIONAL
}

--  OPTIONAL denotes network operator specific use.
HoldCallPartyConnectionArg ::= SEQUENCE {
  callID  [0]  CallID OPTIONAL,
  legID   [1]  LegID
}

--  OPTIONAL denotes network operator specific use.
ReconnectArg ::= SEQUENCE {
  callID     [0]  CallID OPTIONAL,
  heldLegID  [1]  LegID
}

--  OPTIONAL denotes network operator specific use.
ReleaseCallPartyConnectionArg ::= SEQUENCE {
  legToBeReleased  [0]  LegID,
  callID           [1]  CallID OPTIONAL,
  releaseCause     [2]  CauseQ763 OPTIONAL
}

--  OPTIONAL denotes network operator specific use. Common Data Types
CallID ::= INTEGER

--  Indicates an identifier to reference an instance of a Call accessible to the SCF. Refer to
--  4.2.2.1/Q.1214 for a description of Call Segment.
CauseQ763 ::= OCTET STRING
-- WS adaptation
--  Indicates the cause for interface related information. Refer to the Q.763 Cause parameter 
--  for encoding.
LegInformation ::= SEQUENCE {legID      [0]  LegID,
                             legStatus  [1]  LegStatus
}

--  Indicates call party information, as defined by a Leg object. This includes a LegID to reference 
--  each call party, and a LegStatus to indicate whether the call party is connected or not.
LegStatus ::= ENUMERATED {
  connected(0), unconnected(1), pending(2), interacting(3)
 --  user connected to a resource--}

--  Indicates the state of the call party.
END

-- Generated by Asnp, the ASN.1 pretty-printer of France Telecom R&D

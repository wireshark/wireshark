--         Expanded ASN1 Module 'SS-Operations'          
--SIEMENS ASN.1 Compiler       R5.70  (Production_5.70)    
--            Date: 2004-03-19 Time: 12:34:55            

SS-Operations{ 0 identified-organization (4) etsi (0) mobileDomain (0) gsm-Access (2) modules (3) ss-Operations (0) version9 (9) }

DEFINITIONS

IMPLICIT TAGS ::=

BEGIN

EXPORTS
   processUnstructuredSS-Data, 
   notifySS, 
   forwardChargeAdvice, 
   forwardCUG-Info, 
   buildMPTY, 
   holdMPTY, 
   retrieveMPTY, 
   splitMPTY, 
   explicitCT, 
   accessRegisterCCEntry, 
   callDeflection, 
   userUserService, 
   lcs-LocationNotification, 
   lcs-MOLR, 
   lcs-AreaEventRequest, 
   lcs-AreaEventReport, 
   lcs-AreaEventCancellation;

IMPORTS

	SS-Code,
	SS-Status,
	CUG-Index,
	CCBS-Feature,
	AlertingPattern,
	USSD-DataCodingScheme,
	USSD-String,
	ISDN-AddressString,
	ISDN-SubaddressString,
	AddressString,
	NotificationToMSUser,
	LocationType,
	LCSClientExternalID,
	LCSClientName,
	LCSRequestorID,
	LCSCodeword,
	LCSServiceTypeID,
	LCS-QoS,
	SupportedGADShapes,
	AgeOfLocationInformation,
	Ext-GeographicalInformation,
	Add-GeographicalInformation,
	LCS-ReferenceNumber,
	GSN-Address,
	DeferredLocationEventType,
	AreaEventInfo

	FROM MAP-Protocol{ 0 identified-organization (4) etsi (0) mobileDomain (0) gsm-Network (1) modules (3) map-Protocol (4) version5 (5) }
	;


DummySS-operationsArg::= CHOICE {
	notifySS						NotifySS-Arg,
	processUnstructuredSS-Data		SS-UserData,
	forwardCUG-Info					ForwardCUG-InfoArg,
	accessRegisterCCEntry			AccessRegisterCCEntryArg,
	forwardChargeAdvice				ForwardChargeAdviceArg,
	callDeflection					CallDeflectionArg,
	lcs-LocationNotification		LocationNotificationArg,
	lcs-MOLR						LCS-MOLRArg,
	lcs-AreaEventRequest			LCS-AreaEventRequestArg,
	lcs-AreaEventReport				LCS-AreaEventReportArg,
	lcs-AreaEventCancellation		LCS-AreaEventCancellationArg,
	...
	}


DummySS-operationsRes::= CHOICE {
	registerCC-EntryRes				RegisterCC-EntryRes,
	lcs-LocationNotification-res	LocationNotificationRes,
	lcs-MOLR-res					LCS-MOLRRes,
	...
	}
-- processUnstructuredSS-Data OPERATION  ::=  {
--   ARGUMENT     IA5String  ( SIZE( 1 .. 200 ) )
--   RESULT     IA5String  ( SIZE( 1 .. 200 ) )
--   ERRORS     {
--      systemFailure | 
--      unexpectedDataValue }
--   CODE     local      : 19
--   }
SS-UserData ::= IA5String (SIZE (1.. 200))

-- notifySS   OPERATION  ::=  {
--   ARGUMENT     SEQUENCE {
NotifySS-Arg ::= SEQUENCE{
	ss-Code 				[1] SS-Code OPTIONAL,
	ss-Status 				[4] SS-Status OPTIONAL,
	ss-Notification 		[5] SS-Notification OPTIONAL,
	callIsWaiting-Indicator [14] NULL OPTIONAL,
	callOnHold-Indicator 	[15] CallOnHold-Indicator OPTIONAL,
	mpty-Indicator 			[16] NULL OPTIONAL,
	cug-Index 				[17] CUG-Index OPTIONAL,
	clirSuppressionRejected [18] NULL OPTIONAL,
	... ,
	ect-Indicator 			[19] ECT-Indicator OPTIONAL,
	nameIndicator 			[20] NameIndicator OPTIONAL,
	ccbs-Feature 			[21] CCBS-Feature OPTIONAL,
	alertingPattern 		[22] AlertingPattern OPTIONAL,
	multicall-Indicator 	[23] Multicall-Indicator OPTIONAL}
--   CODE     local      : 16
--   }
-- The nameIndicator is defined because of CNAP.

Multicall-Indicator ::= ENUMERATED {
	nbr-SNexceeded (0),
	nbr-Userexceeded (1)}

--forwardChargeAdvice OPERATION  ::=  {
--   ARGUMENT     SEQUENCE {
ForwardChargeAdviceArg ::= SEQUENCE{
	ss-Code 		[0] SS-Code,
	chargingInformation 	[1] ChargingInformation,
	...}

--   RETURN  RESULT     TRUE
--   CODE     local      : 125
--   }

SS-Notification ::= OCTET STRING (SIZE (1))
-- Bit 8 7 6 5 4 00000 (Unused)
-- Bit 3 Call is forwarded indication to A-subscriber
-- (calling subscriber)
-- 0 No information content
-- 1 Outgoing call has been forwarded to C
-- Bit 2 Call is forwarded indication to B-subscriber
-- (forwarding subscriber)
-- 0 No information content
-- 1 Incoming call has been forwarded to C
-- Bit 1 Call is forwarded indication to C-subscriber
-- (forwarded-to subscriber)
-- 0 No information content
-- 1 Incoming call is a forwarded call

ChargingInformation ::= SEQUENCE{
	e1 [1] E1 OPTIONAL,
	e2 [2] E2 OPTIONAL,
	e3 [3] E3 OPTIONAL,
	e4 [4] E4 OPTIONAL,
	e5 [5] E5 OPTIONAL,
	e6 [6] E6 OPTIONAL,
	e7 [7] E7 OPTIONAL,
...}

E1 ::= INTEGER (0..max10TimesUnitsPerTime)

max10TimesUnitsPerTime INTEGER ::= 8191

E2 ::= INTEGER (0..max10TimesTimeInterval)

max10TimesTimeInterval INTEGER ::= 8191

E3 ::= INTEGER (0..max100TimesScalingFactor)

max100TimesScalingFactor INTEGER ::= 8191

E4 ::= INTEGER (0..max10TimesIncrement)

max10TimesIncrement INTEGER ::= 8191

E5 ::= INTEGER (0..max10TimesIncrementPerDataInterval)

max10TimesIncrementPerDataInterval INTEGER ::= 8191

E6 ::= INTEGER (0..maxNumberOfSegmentsPerDataInterval)

maxNumberOfSegmentsPerDataInterval INTEGER ::= 8191

E7 ::= INTEGER (0..max10TimesInitialTime)

max10TimesInitialTime INTEGER ::= 8191

CallOnHold-Indicator ::= ENUMERATED {
	callRetrieved (0),
	callOnHold (1)}

-- forwardCUG-Info OPERATION  ::=  {
--   ARGUMENT     SEQUENCE {
ForwardCUG-InfoArg ::= SEQUENCE {
	cug-Index 		[0] CUG-Index OPTIONAL,
	suppressPrefCUG 	[1] NULL OPTIONAL,
	suppressOA 		[2] NULL OPTIONAL,
...}
--   CODE     local      : 120
--   }	


ECT-Indicator ::= SEQUENCE {
	ect-CallState 		[0] ECT-CallState,
	rdn 				[1] RDN OPTIONAL,
	...}

ECT-CallState ::= ENUMERATED {
	alerting (0),
	active (1)}

NameIndicator ::= SEQUENCE {
	callingName 		[0] Name OPTIONAL,
	...
	}

Name ::= CHOICE {
	namePresentationAllowed 	[0] NameSet,
	presentationRestricted 		[1] NULL,
	nameUnavailable 			[2] NULL,
	namePresentationRestricted 	[3] NameSet}

NameSet ::= SEQUENCE {
	dataCodingScheme 		[0] USSD-DataCodingScheme,
	lengthInCharacters 		[1] INTEGER,
	nameString 				[2] USSD-String,
...}

-- NameIndicator, Name and NameSet are defined because of CNAP.
-- The USSD-DataCodingScheme shall indicate use of the default alphabet through the
-- following encoding:
-- bit 7 6 5 4 3 2 1 0
-- | 0 0 0 0 | 1 1 1 1|

RDN ::= CHOICE {
	presentationAllowedAddress 				[0] RemotePartyNumber,
	presentationRestricted 					[1] NULL,
	numberNotAvailableDueToInterworking 	[2] NULL,
	presentationRestrictedAddress 			[3] RemotePartyNumber}

RemotePartyNumber ::= SEQUENCE {
	partyNumber 					[0] ISDN-AddressString,
	partyNumberSubaddress 			[1] ISDN-SubaddressString OPTIONAL,
...}

-- accessRegisterCCEntry OPERATION  ::=  {
--   ARGUMENT     SEQUENCE {
--      ... }

AccessRegisterCCEntryArg ::= SEQUENCE {
	...}

RegisterCC-EntryRes ::= 
--   RESULT     SEQUENCE {
		SEQUENCE {
      ccbs-Feature   [0] IMPLICIT SEQUENCE {
         ccbs-Index               [0] IMPLICIT INTEGER ( 1 .. 5 ) OPTIONAL, 
         b-subscriberNumber       [1] IMPLICIT OCTET STRING ( SIZE( 1 .. 20 ) ) ( SIZE( 1 .. 9 ) ) OPTIONAL, 
         b-subscriberSubaddress   [2] IMPLICIT OCTET STRING ( SIZE( 1 .. 21 ) ) OPTIONAL, 
         basicServiceGroup        [3] CHOICE {
            bearerService			[2] IMPLICIT OCTET STRING ( SIZE( 1 ) ), 
            teleservice			[3] IMPLICIT OCTET STRING ( SIZE( 1 ) )} OPTIONAL, 
         ... } OPTIONAL, 
      ... }
--   ERRORS     {
--      systemFailure | 
--      dataMissing | 
--      unexpectedDataValue | 
--      callBarred | 
--      illegalSS-Operation | 
--      ss-ErrorStatus | 
--      ss-Incompatibility | 
--      shortTermDenial | 
--      longTermDenial | 
--      facilityNotSupported }
--   CODE     local      : 119
--   }

-- callDeflection OPERATION  ::=  {
--   ARGUMENT     SEQUENCE {

CallDeflectionArg ::= SEQUENCE {
	deflectedToNumber 			[0] AddressString,
	deflectedToSubaddress 		[1] ISDN-SubaddressString OPTIONAL,
...}

--   RETURN  RESULT     TRUE
--   ERRORS     {
--      illegalSS-Operation | 
--      ss-ErrorStatus | 
--      ss-NotAvailable | 
--      ss-Incompatibility | 
--      facilityNotSupported | 
--      systemFailure | 
--      resourcesNotAvailable | 
--      forwardingViolation | 
--      callBarred | 
--      deflectionToServedSubscriber | 
--      invalidDeflectedToNumber | 
--      specialServiceCode | 
--      forwardingFailed }
--   CODE     local      : 117
--   }


--userUserService OPERATION  ::=  {
--   ARGUMENT     SEQUENCE {

UserUserServiceArg ::= SEQUENCE {
	uUS-Service 	[0] UUS-Service,
	uUS-Required 	[1] BOOLEAN,
... }

--   RETURN  RESULT     TRUE
--   ERRORS     {
--      illegalSS-Operation | 
--      ss-ErrorStatus | 
--      ss-NotAvailable | 
--      ss-Incompatibility | 
--     facilityNotSupported | 
--      systemFailure | 
--      resourcesNotAvailable | 
--      rejectedByNetwork | 
--      rejectedByUser }
--   CODE     local      : 118
--   }


UUS-Service ::= ENUMERATED {
	uUS1 (1),
	uUS2 (2),
	uUS3 (3),
... }

-- exception handling:
-- In case of UUS-Service with any other value, indicated as "UUS required",
-- but not understood by the MS, the call will be cleared.

-- lcs-LocationNotification OPERATION  ::=  {
--   ARGUMENT     SEQUENCE {
LocationNotificationArg ::= SEQUENCE {
	notificationType 		[0] NotificationToMSUser,
	locationType 			[1] LocationType,
	lcsClientExternalID 	[2] LCSClientExternalID OPTIONAL,
	lcsClientName 			[3] LCSClientName OPTIONAL,
	... ,
	lcsRequestorID 			[4] LCSRequestorID OPTIONAL,
	lcsCodeword 			[5] LCSCodeword OPTIONAL,
	lcsServiceTypeID 		[6] LCSServiceTypeID OPTIONAL }

-- exception handling:
-- At reception of an unrecognised notificationType value the receiver shall reject the
-- operation with a return error cause of unexpected data value.
-- At reception of an unrecognised locationType value the receiver shall reject the
-- operation with a return error cause of unexpected data value.

--   RESULT     SEQUENCE {
LocationNotificationRes ::= SEQUENCE {
	verificationResponse [0] VerificationResponse OPTIONAL,
	...}
--   ERRORS     {
--      systemFailure | 
--      unexpectedDataValue }
--   CODE     local      : 116
--   }

VerificationResponse::= ENUMERATED {
	permissionDenied (0),
	permissionGranted (1),
... }
-- exception handling:
-- an unrecognized value shall be treated the same as value 0 (permissionDenied)


-- lcs-MOLR   OPERATION  ::=  {
--   ARGUMENT     SEQUENCE {
--   RESULT     SEQUENCE {

LCS-MOLRArg ::= SEQUENCE {
	molr-Type 				[0] MOLR-Type,
	locationMethod 			[1] LocationMethod OPTIONAL,
	lcs-QoS 				[2] LCS-QoS OPTIONAL,
	lcsClientExternalID 	[3] LCSClientExternalID OPTIONAL,
	mlc-Number 				[4] ISDN-AddressString OPTIONAL,
	gpsAssistanceData 		[5] GPSAssistanceData OPTIONAL,
	...,
	supportedGADShapes 		[6] SupportedGADShapes OPTIONAL,
	lcsServiceTypeID 		[7] LCSServiceTypeID OPTIONAL,
	ageOfLocationInfo 		[8] AgeOfLocationInformation OPTIONAL,
	locationType 			[9] LocationType OPTIONAL,
	pseudonymIndicator 		[10] NULL OPTIONAL }
-- The parameter locationMethod shall be included if and only if the molr-Type is set to value
-- deCipheringKeys or assistanceData.
-- The parameter gpsAssistanceData shall be included if and only if the molr-Type is set to value
-- assistanceData and locationMethod is set to value assistedGPS.

MOLR-Type::= ENUMERATED {
	locationEstimate (0),
	assistanceData (1),
	deCipheringKeys (2),
... }
-- exception handling:
-- an unrecognized value shall be rejected by the receiver with a return error cause of
-- unexpected data value.

LocationMethod::= ENUMERATED {
	msBasedEOTD (0),
	msAssistedEOTD (1),
	assistedGPS (2),
	...,
	msBasedOTDOA (3)
}
-- exception handling:
-- When this parameter is received with value msBasedEOTD or msAssistedEOTD and the MS
-- is camped on an UMTS Service Area then the receiver shall reject it
-- with a return error cause of unexpected data value.
-- When this parameter is received with value msBasedOTDOA and the MS
-- is camped on a GSM Cell then the receiver shall reject it with a return error cause of
-- unexpected data value.
-- an unrecognized value shall be rejected by the receiver with a return error cause of
-- unexpected data value.

GPSAssistanceData::= OCTET STRING (SIZE (1..38))

-- Octets 1 to 38 are coded in the same way as the octets 3 to 7+2n of Requested GPS Data IE
-- in 3GPP TS 49.031.

LCS-MOLRRes::= SEQUENCE {
	locationEstimate 		[0] Ext-GeographicalInformation OPTIONAL,
	decipheringKeys 		[1] DecipheringKeys OPTIONAL,
	...,
	add-LocationEstimate 	[2] Add-GeographicalInformation OPTIONAL}

--   ERRORS     {
--      systemFailure | 
--      unexpectedDataValue | 
--      dataMissing | 
--      facilityNotSupported | 
--      ss-SubscriptionViolation | 
--      positionMethodFailure }
--   CODE     local      : 115
--   }

-- Parameters locationEstimate or add-LocationEstimate (one but not both)
-- shall be included if and only if the
-- molr-Type in LocationRequestArg was set to value locationEstimate.
-- Parameter add-LocationEstimate shall not be included if the supportedGADShapes
-- parameter was not received in the LCS-MOLRArg.
-- The locationEstimate and the add-locationEstimate parameters shall not be sent if
-- the supportedGADShapes parameter has been received in LCS-MOLRArg
-- and the shape encoded in locationEstimate or add-LocationEstimate is not marked
-- as supported in supportedGADShapes. In such a case LCS-MOLRArg
-- shall be rejected with error FacilityNotSupported with additional indication
-- shapeOfLocationEstimateNotSupported.
-- Parameter decipheringKeys shall be included if and only if the molr-Type
-- in LocationRequestArg was set to value deCipheringKeys.

DecipheringKeys::= OCTET STRING (SIZE (15))

-- Octets in DecipheringKeys are coded in the same way as the octets 3 to 17 of Deciphering Key IE
-- in 3GPP TS 49.031. I.e. these octets contain Current Deciphering Key, Next Deciphering Key and
-- Ciphering Key Flag.

-- lcs-AreaEventRequest OPERATION  ::=  {
--   ARGUMENT     SEQUENCE {

LCS-AreaEventRequestArg ::= SEQUENCE {
	referenceNumber 			[0] LCS-ReferenceNumber,
	h-gmlc-address 				[1] GSN-Address,
	deferredLocationEventType 	[3] DeferredLocationEventType,
	areaEventInfo 				[4] AreaEventInfo,
... }
--   RETURN  RESULT     TRUE
--   ERRORS     {
--      systemFailure | 
--      facilityNotSupported | 
--      unexpectedDataValue }
--   CODE     local      : 114
--   }

-- the msAvailableValue in the DeferredLocationEventType is not applicable for this procedure

-- lcs-AreaEventReport OPERATION  ::=  {
--   ARGUMENT     SEQUENCE {

LCS-AreaEventReportArg ::= SEQUENCE {
	referenceNumber 	[0] LCS-ReferenceNumber,
	h-gmlc-address 		[1] GSN-Address,
... }
--   RETURN  RESULT     TRUE
--   ERRORS     {
--      systemFailure | 
--      unexpectedDataValue | 
--      facilityNotSupported }
--   CODE     local      : 113
--   }

-- lcs-AreaEventCancellation OPERATION  ::=  {
--   ARGUMENT     SEQUENCE {
LCS-AreaEventCancellationArg ::= SEQUENCE {
	referenceNumber 	[0] LCS-ReferenceNumber,
	h-gmlc-address 		[1] GSN-Address,
... }
--   CODE     local      : 112
--   }


--buildMPTY  OPERATION  ::=  {
--   RETURN  RESULT     TRUE
--   ERRORS     {
--      illegalSS-Operation | 
--      ss-ErrorStatus | 
--      ss-NotAvailable | 
--      ss-Incompatibility | 
--      systemFailure | 
--      resourcesNotAvailable | 
--      maxNumberOfMPTY-ParticipantsExceeded }
--   CODE     local      : 124
--   }

--holdMPTY   OPERATION  ::=  {
--   RETURN  RESULT     TRUE
--   ERRORS     {
--      illegalSS-Operation | 
--      ss-ErrorStatus | 
--      ss-Incompatibility | 
--      facilityNotSupported | 
--      systemFailure }
--   CODE     local      : 123
--   }

--retrieveMPTY OPERATION  ::=  {
--   RETURN  RESULT     TRUE
--  ERRORS     {
--      illegalSS-Operation | 
--      ss-ErrorStatus | 
--      ss-Incompatibility | 
--      facilityNotSupported | 
--      systemFailure }
--   CODE     local      : 122
--   }

--splitMPTY  OPERATION  ::=  {
--   RETURN  RESULT     TRUE
--   ERRORS     {
--      illegalSS-Operation | 
--      ss-ErrorStatus | 
--      ss-Incompatibility | 
--      facilityNotSupported | 
--      systemFailure }
--   CODE     local      : 121
--   }

--explicitCT OPERATION  ::=  {
--   RETURN  RESULT     TRUE
--   ERRORS     {
--      illegalSS-Operation | 
--      ss-ErrorStatus | 
--      ss-NotAvailable | 
--      ss-Incompatibility | 
--      facilityNotSupported | 
--      systemFailure | 
--      resourcesNotAvailable | 
--      callBarred }
--   CODE     local      : 126
--   }

END

-- $Id$
-- Module CMIP-A-ASSOCIATE-Information (X.711:10/1997)
CMIP-A-ASSOCIATE-Information {joint-iso-itu-t ms(9) cmip(1) modules(0)
  aAssociateUserInfo(1)} DEFINITIONS ::=
BEGIN

FunctionalUnits ::= BIT STRING {
  multipleObjectSelection(0), filter(1), multipleReply(2), extendedService(3),
  cancelGet(4)}

--	Functional unit i is supported if and only if bit i is one
--	Information carried in user-information parameter of A-ASSOCIATE
CMIPUserInfo ::= SEQUENCE {
  protocolVersion  [0] IMPLICIT ProtocolVersion DEFAULT {version1},
  functionalUnits  [1] IMPLICIT FunctionalUnits DEFAULT {},
  accessControl    [2]  EXTERNAL OPTIONAL,
  userInfo         [3]  EXTERNAL OPTIONAL
}

ProtocolVersion ::= BIT STRING {version1(0), version2(1)}

END

-- Generated by Asnp, the ASN.1 pretty-printer of France Telecom R&D

--
-- EN 300 130-1 Ver. 1.2.4
--

MCID-Operations {ccitt identified-organization etsi (0) 130 operations-and-errors (1)}

DEFINITIONS ::=
BEGIN

EXPORTS				MCIDRequest;


IMPORTS				
                    --OPERATION
					--FROM Remote-Operation-Notation 
					--	{joint-iso-ccitt remote-operations(4) notation (0)}
					notAvailable,
					notSubscribed,
					invalidCallState,
					notIncomingCall,
					supplementaryServiceInteractionNotAllowed
					FROM General-Errors
						{ccitt identified-organization etsi (0) 196 general errors};



	mCIDRequest OPERATION ::= {
	   RETURN RESULT     FALSE 
       ERRORS {
            notAvailable |
            invalidCallState |
            notIncomingCall |
            supplementaryServiceInteractionNotAllowed}
	   CODE        local:  3} 

-- mCIDRequest MCIDRequest ::= 3

END -- of MCID-Operations

--
-- EN 301 002-1 Ver. 1.3.1
--
Set-Operations-and-Errors {ITU-T identified-organization etsi(0) 1002 operations-and-errors(1)}

DEFINITIONS EXPLICIT TAGS ::=

BEGIN

EXPORTS
        ModifyPin,
        Pin,
		Tan,
        InvalidPin,
		InvalidTan,
        PinNotProvided,
        InvalidNewPin,
        ChangeOfPinRequired,
        PrimitivePin,
        NewPinIsOldPin,
        UserControlBlocked;

IMPORTS
        OPERATION, ERROR
        FROM Remote-Operations-Information-Objects 
    {joint-iso-itu-t (2) remote-operations (4) informationObjects(5) version1(0)}

        PartyNumber
        FROM Addressing-Data-Elements
            {itu-t(0) identified-organization(4) etsi(0) 196 addressing-data-elements(6)}

        invalidServedUserNr
        FROM General-Errors
            {itu-t(0) identified-organization(4) etsi(0) 196 general-errors(2)};

ModifyPin				::= OPERATION
								ARGUMENT	ModifyPinArgument
								RESULT
								ERRORS     {InvalidPin,
											PinNotProvided,
											InvalidNewPin,
											invalidServedUserNr,
											PrimitivePin,
											NewPinIsOldPin,
											UserControlBlocked}

PossibleFraudulentPinUse	::= OPERATION
PossibleFraudulentTanUse	::= OPERATION
ModifyPinArgument		::= SEQUENCE {
								oldPin			Pin,
								newPin			Pin,
								servedUserNr	PartyNumber}

Pin						::= IA5String (SIZE(4..12)) (FROM ("0"|"1"|"2"|"3"|"4"|"5"|"6"|"7"|"8"|"9"
                                                          |"A"|"B"|"C"|"D"|"E"|"F"|"G"|"H"|"I"|"J"
                                                          |"K"|"L"|"M"|"N"|"O"|"P"|"Q"|"R"|"S"|"T"
                                                          |"U"|"V"|"W"|"X"|"Y"|"Z"
                                                          |"a"|"b"|"c"|"d"|"e"|"f"|"g"|"h"|"i"|"j"
                                                          |"k"|"l"|"m"|"n"|"o"|"p"|"q"|"r"|"s"|"t"
                                                          |"u"|"v"|"w"|"x"|"y"|"z"))

Tan						::= IA5String (SIZE(6..12)) (FROM ("0"|"1"|"2"|"3"|"4"|"5"|"6"|"7"|"8"|"9"
                                                          |"A"|"B"|"C"|"D"|"E"|"F"|"G"|"H"|"I"|"J"
                                                          |"K"|"L"|"M"|"N"|"O"|"P"|"Q"|"R"|"S"|"T"
                                                          |"U"|"V"|"W"|"X"|"Y"|"Z"
                                                          |"a"|"b"|"c"|"d"|"e"|"f"|"g"|"h"|"i"|"j"
                                                          |"k"|"l"|"m"|"n"|"o"|"p"|"q"|"r"|"s"|"t"
                                                          |"u"|"v"|"w"|"x"|"y"|"z"))


invalidPin            ERROR ::= {CODE global:{sETOID 10}}
invalidTan            ERROR ::= {CODE global:{sETOID 11}}
pinNotProvided        ERROR ::= {CODE global:{sETOID 17}}
invalidNewPin         ERROR ::= {CODE global:{sETOID 12}}
userControlBlocked    ERROR ::= {CODE global:{sETOID 13}}
changeOfPinRequired   ERROR ::= {CODE global:{sETOID 14}}
primitivePin          ERROR ::= {CODE global:{sETOID 15}}
newPinIsOldPin        ERROR ::= {CODE global:{sETOID 16}}


sETOID OBJECT IDENTIFIER ::= {itu-t(0) identified-organization(4) etsi(0) 1002 operations-and-errors(1)}

modifyPin				ModifyPin 				::= globalValue {sETOID  1}
possibleFraudulentPinUse	PossibleFraudulentPinUse	::= globalValue {sETOID  2}
possibleFraudulentTanUse	PossibleFraudulentTanUse	::= globalValue {sETOID  3}

invalidPin				InvalidPin 				::= globalValue {sETOID 10}
pinNotProvided			PinNotProvided 			::= globalValue {sETOID 11}
invalidNewPin			InvalidNewPin        	::= globalValue {sETOID 12}
userControlBlocked		UserControlBlocked   	::= globalValue {sETOID 13}
changeOfPinRequired		ChangeOfPinRequired 	::= globalValue {sETOID 14}
primitivePin			PrimitivePin			::= globalValue {sETOID 15}
newPinIsOldPin			NewPinIsOldPin			::= globalValue {sETOID 16}
invalidTan				InvalidTan 				::= globalValue {sETOID 17}


END -- of Set-Function-Operations-and-Errors

--
-- $Id$
--
-- ETSI EN 300 207-1 V3.1.1 (2001-06)
--

Diversion-Operations {etsi(0) xx(207) operations-and-errors(1)}

DEFINITIONS EXPLICIT TAGS ::=

BEGIN

EXPORTS             ActivationDiversion, 
                    DeactivationDiversion,
                    ActivationStatusNotificationDiv,
                    DeactivationStatusNotificationDiv,
                    InterrogationDiversion,
                    InterrogateServedUserNumbers,
                    DiversionInformation,
                    CallDeflection,
                    CallRerouteing,
                    DivertingLegInformation1,
                    DivertingLegInformation2,
                    DivertingLegInformation3,
                    InvalidDivertedToNr,
                    SpecialServiceNr,
                    DiversionToServedUserNr,
                    IncomingCallAccepted,
                    NumberOfDiversionsExceeded,
                    NotActivated,
                    RequestAlreadyAccepted,
                    invalidDivertedToNr,
                    specialServiceNr,
                    diversionToServedUserNr,
                    incomingCallAccepted,
                    numberOfDiversionsExceeded,
                    notActivated,
                    requestAlreadyAccepted,
ServedUserNr;

IMPORTS  OPERATION, ERROR FROM Remote-Operations-Information-Objects 
    {joint-iso-itu-t (2) remote-operations (4) informationObjects(5) version1(0)} 

                    notSubscribed,
                    notAvailable,
                    invalidServedUserNr,
                    basicServiceNotProvided,
                    supplementaryServiceInteractionNotAllowed,
                    resourceUnavailable
                    FROM General-Errors
                        {itu-t(0) identified-organization(4) etsi(0) 196 general-errors(2)}

                    PresentedAddressScreened,
                    PresentedNumberUnscreened,
                    Address,
                    PartyNumber,
                    PartySubaddress,
                    PresentationAllowedIndicator

                    FROM Addressing-Data-Elements
                        {itu-t(0) identified-organization(4) etsi(0) 196 addressing-data-elements(6)}

                    BasicService
                    FROM Basic-Service-Elements
                        {itu-t(0) identified-organization(4) etsi(0) 196 basic-service-elements(8)}

                    Q931InformationElement
                    FROM Embedded-Q931-Types
                        {itu-t(0) identified-organization(4) etsi(0) 196 embedded-q931-types(7)};


	activationDiversion OPERATION ::= {
	   ARGUMENT       ActivationDiversionArg 
	   RETURN RESULT     FALSE 
	   ALWAYS RESPONDS  FALSE 
	   ERRORS {
			notSubscribed,
			notAvailable,
			invalidServedUserNr,
			supplementaryServiceInteractionNotAllowed,
			basicServiceNotProvided,
			resourceUnavailable,
			invalidDivertedToNr,
			specialServiceNr,
			diversionToServedUserNr,
			invalidNoReplyTimerValue}
	   CODE        local:  7} 

    ActivationDiversionArg ::= SEQUENCE {
        procedure               Procedure,
        basicService            BasicService,
        forwardedToAddress      Address,
        servedUserNr            ServedUserNr,
		noReplyTimer		    NoReplyTimer OPTIONAL
	}




-- End of ActivationDiversion operation definition

	deactivationDiversion OPERATION ::= {
	   ARGUMENT       DeactivationDiversionArg 
	   RETURN RESULT     FALSE 
	   ALWAYS RESPONDS  FALSE 
       ERRORS {
        notSubscribed |
        notAvailable |
        invalidServedUserNr |
        NotActivated}
	   CODE        local:  8} 

	DeactivationDiversionArg   ::=  SEQUENCE {   
		procedure               Procedure,
        basicService            BasicService,
        servedUserNr            ServedUserNr
	}


-- End of DeactivationDiversion operation definition

	activationStatusNotificationDiv OPERATION ::= {
	   ARGUMENT      ActivationStatusNotificationDivArg 
	   RETURN RESULT     FALSE 
	   ALWAYS RESPONDS  FALSE 
	   CODE        local:  9} 

    ActivationStatusNotificationDivArg ::= SEQUENCE {
        procedure               Procedure,
        basicService            BasicService,
        forwardedToAddresss     Address,
        servedUserNr            ServedUserNr}

-- End of ActivationStatusNotificationDiv operation definition

	deactivationStatusNotificationDiv OPERATION ::= {
	   ARGUMENT      DeactivationStatusNotificationDivArg 
	   RETURN RESULT     FALSE 
	   ALWAYS RESPONDS  FALSE 
	   CODE        local:  10} 

    DeactivationStatusNotificationDivArg ::= SEQUENCE {
        procedure               Procedure,
        basicService            BasicService,
        servedUserNr            ServedUserNr}

-- End of DeactivationStatusNotificationDiv operation definition

	interrogationDiversion  OPERATION ::= {
	   ARGUMENT      InterrogationDiversionArg 
	   RESULT		 InterrogationDiversionRes 
        ERRORS {
            notSubscribed |
            notAvailable |
            invalidServedUserNr}
	   CODE        local:  11} 

    InterrogationDiversionArg ::= SEQUENCE {
        procedure               Procedure,
        basicService            BasicService DEFAULT allServices,
        servedUserNr            ServedUserNr}

        InterrogationDiversionRes ::=  IntResultList


-- End of InterrogationDiversion operation definition

	interrogateServedUserNumbers  OPERATION ::= {
	   RESULT     InterrogateServedUserNumbersRes 
        ERRORS {
            notSubscribed |
            notAvailable}
	   CODE        local:  17} 

	InterrogateServedUserNumbersRes ::= ServedUserNumberList

-- End of InterrogateServedUserNumbers operation definition

	diversionInformation    OPERATION ::= {
	   ARGUMENT      DiversionInformationArg 
	   RETURN RESULT     FALSE 
	   ALWAYS RESPONDS  FALSE 
	   CODE        local:  12} 

		DiversionInformationArg ::= SEQUENCE {
			diversionReason         DiversionReason,
			basicService            BasicService,
			servedUserSubaddress    PartySubaddress OPTIONAL,
			callingAddress          [0] PresentedAddressScreened OPTIONAL,
			originalCalledNr        [1] PresentedNumberUnscreened OPTIONAL,
			lastDivertingNr         [2] PresentedNumberUnscreened OPTIONAL,
			lastDivertingReason     [3] DiversionReason OPTIONAL,
			userInfo                Q931InformationElement OPTIONAL}

-- The User-user information element, as specified in EN 300 286-1 [19]  clause 7.3.3 , shall be 
--embedded in the userInfo parameter.

-- End of DiversionInformation operation definition

	callDeflection    OPERATION ::= {
	   ARGUMENT      CallDeflectionArg 
	   RETURN RESULT     FALSE 
	   ERRORS {
			notSubscribed |
			notAvailable |
			invalidDivertedToNr |
			specialServiceNr |
			diversionToServedUserNr |
			incomingCallAccepted |
			numberOfDiversionsExceeded |
			supplementaryServiceInteractionNotAllowed |
			requestAlreadyAccepted}
	   CODE        local:  13} 

    CallDeflectionArg ::= SEQUENCE {
        deflectionAddress                   Address,
        presentationAllowedDivertedToUser   PresentationAllowedIndicator
                                            OPTIONAL}

-- End of CallDeflection operation definition

	callRerouteing    OPERATION ::= {
	   ARGUMENT      CallRerouteingArg 
	   RETURN RESULT     FALSE 
	   ALWAYS RESPONDS  FALSE 
       ERRORS {
        notSubscribed |
        notAvailable |
        supplementaryServiceInteractionNotAllowed |
        resourceUnavailable |
        invalidDivertedToNr |
        specialServiceNr |
        diversionToServedUserNr |
        numberOfDiversionsExceeded}
	   CODE        local:  14} 

    CallRerouteingArg ::= SEQUENCE {
        rerouteingReason        DiversionReason,
        calledAddress           Address,
        rerouteingCounter       DiversionCounter,
        q931InfoElement         Q931InformationElement,
        lastRerouteingNr        [1] PresentedNumberUnscreened,
        subscriptionOption      [2] SubscriptionOption
                                    DEFAULT noNotification,
        callingPartySubaddress  [3] PartySubaddress OPTIONAL}

-- The User-user information element (optional), High layer compatibility information element
-- (optional), Bearer capability information element and Low layer compatibility information 
-- element (optional) as specified in EN 300 403-1 [11] clause 4.5 shall be embedded in the 
-- q931InfoElement.


-- End of CallRerouteing operation definition

	divertingLegInformation1    OPERATION ::= {
	   ARGUMENT      DivertingLegInformation1Arg 
	   RETURN RESULT     FALSE 
	   ALWAYS RESPONDS  FALSE 
	   CODE        local:  18} 

	DivertingLegInformation1Arg ::= SEQUENCE {
		diversionReason         DiversionReason,
		subscriptionOption      SubscriptionOption,
		divertedToNumber        PresentedNumberUnscreened OPTIONAL}

-- End of DivertingLegInformation1 operation definition


	divertingLegInformation2    OPERATION ::= {
	   ARGUMENT      DivertingLegInformation2Arg 
	   RETURN RESULT     FALSE 
	   ALWAYS RESPONDS  FALSE 
	   CODE        local:  15} 

    DivertingLegInformation2Arg ::= SEQUENCE {
        diversionCounter        DiversionCounter,
        diversionReason         DiversionReason,
        divertingNr             [1] PresentedNumberUnscreened OPTIONAL,
        originalCalledNr        [2] PresentedNumberUnscreened OPTIONAL}

-- End of DivertingLegInformation2 operation definition
	divertingLegInformation3    OPERATION ::= {
	   ARGUMENT      DivertingLegInformation3Arg 
	   RETURN RESULT     FALSE 
	   ALWAYS RESPONDS  FALSE 
	   CODE        local:  19} 

    DivertingLegInformation3Arg ::=      PresentationAllowedIndicator

-- End of DivertingLegInformation3 operation definition

IntResultList               ::= SET SIZE (0..29) OF IntResult

IntResult                   ::= SEQUENCE   {servedUserNr          ServedUserNr,
                                            basicService          BasicService,
                                            procedure             Procedure,
                                            forwardedToAddress    Address}

ServedUserNr                ::= CHOICE     {individualNumber      PartyNumber,
                                            allNumbers            NULL}

DiversionCounter            ::= INTEGER (1..5)

SubscriptionOption          ::= ENUMERATED {noNotification                    (0),
                                            notificationWithoutDivertedToNr   (1),
                                            notificationWithDivertedToNr      (2)}

Procedure                   ::= ENUMERATED {cfu         (0),
                                            cfb         (1),
                                            cfnr        (2)}

ServedUserNumberList        ::= SET SIZE (0..99) OF PartyNumber

DiversionReason             ::= ENUMERATED {unknown     (0),
                                            cfu         (1),
                                            cfb         (2),
                                            cfnr        (3),
                                            cdAlerting  (4),
                                            cdImmediate (5)}

NoReplyTimer						::= INTEGER (1..180)

InvalidDivertedToNr         ::= ERROR
invalidDivertedToNr  ERROR ::= { CODE  local: 12}

SpecialServiceNr            ::= ERROR
specialServiceNr  ERROR ::= { CODE  local: 14}

DiversionToServedUserNr     ::= ERROR
diversionToServedUserNr  ERROR ::= { CODE  local: 15}

IncomingCallAccepted        ::= ERROR
incomingCallAccepted  ERROR ::= { CODE  local: 23}

NumberOfDiversionsExceeded  ::= ERROR
numberOfDiversionsExceeded  ERROR ::= { CODE  local: 24}

NotActivated                ::= ERROR
notActivated  ERROR ::= { CODE  local: 46}

RequestAlreadyAccepted      ::= ERROR
requestAlreadyAccepted  ERROR ::= { CODE  local: 48}

InvalidNoReplyTimerValue    ::= ERROR
--invalidNoReplyTimerValue  ERROR ::= { CODE  local: xx}

--deactivationDiversion               DeactivationDiversion               ::= localValue  8
--activationStatusNotificationDiv     ActivationStatusNotificationDiv     ::= localValue  9
--deactivationStatusNotificationDiv   DeactivationStatusNotificationDiv   ::= localValue 10
--interrogationDiversion              InterrogationDiversion              ::= localValue 11
--interrogateServedUserNumbers        InterrogateServedUserNumbers        ::= localValue 17
--diversionInformation                DiversionInformation                ::= localValue 12
--callDeflection                      CallDeflection                      ::= localValue 13
--callRerouteing                      CallRerouteing                      ::= localValue 14
--divertingLegInformation1            DivertingLegInformation1            ::= localValue 18
--divertingLegInformation3            DivertingLegInformation3            ::= localValue 19
--divertingLegInformation2            DivertingLegInformation2            ::= localValue 15
--invalidDivertedToNr                 InvalidDivertedToNr                 ::= localValue 12
--specialServiceNr                    SpecialServiceNr                    ::= localValue 14
--diversionToServedUserNr             DiversionToServedUserNr             ::= localValue 15
--incomingCallAccepted                IncomingCallAccepted                ::= localValue 23
--numberOfDiversionsExceeded          NumberOfDiversionsExceeded          ::= localValue 24
--notActivated                        NotActivated                        ::= localValue 46
--requestAlreadyAccepted              RequestAlreadyAccepted              ::= localValue 48

END -- of Diversion-Operations

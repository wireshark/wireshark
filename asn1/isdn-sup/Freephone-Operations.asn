--
-- EN 300 210-1 Ver. 1.2.4
--
Freephone-Operations {ccitt identified-organization etsi(0) 210 operations-and-errors(1)}

DEFINITIONS EXPLICIT TAGS ::=

BEGIN

EXPORTS         CallFPH, Monitor-T-FPH, Free-T-FPH, Call-T-FPH;

IMPORTS         OPERATION, ERROR
                FROM Remote-Operations-Information-Objects 
					{joint-iso-itu-t remote-operations (4) notation (0)}    

                notAvailable, notImplemented
                FROM General-Errors
                    {itu-t(0) identified-organization(4) etsi(0) 196 general-errors(2)}

                PartyNumber
                FROM Addressing-Data-Elements
                    {itu-t(0) identified-organization(4) etsi(0) 196 addressing-data-elements(6)}

                Q931InformationElement
                FROM Embedded-Q931-Types
                    {itu-t(0) identified-organization(4) etsi(0) 196 embedded-q931-types(7)};

--CallFPH         ::= OPERATION
--                    ARGUMENT    calledFreephoneNr       CalledFreephoneNr - - optional

  callFPH OPERATION ::=
    {
        ARGUMENT CalledFreephoneNrArg -- optional    
        
        CODE global:{fPHOID callFPH-operation (1)}   
    }

CalledFreephoneNrArg ::= CalledFreephoneNr

--Monitor-T-FPH   ::= OPERATION
--                    ARGUMENT SEQUENCE {
--                                q931InfoElement         Q931InformationElement,
--                                servedUserDestination   PartyNumber,
--                                queueIdentity           QueueIdentity OPTIONAL}
--                    RESULT
--                    ERRORS {    notAvailable, 
--                                notImplemented}

-- the Bearer capability, High layer compatibility (optional) and Low layer compatibility 
-- (optional) information elements shall be embedded in q931InfoElement.

  monitor-T-FPH OPERATION ::=
    {
        ARGUMENT Monitor-T-FPHArg     

        ERRORS {    notAvailable|
                    notImplemented}
        
        CODE global:{fPHOID monitor-T-FPH-operation(2)}   
    }

Monitor-T-FPHArg ::= SEQUENCE {
                                q931InfoElement         Q931InformationElement,
                                servedUserDestination   PartyNumber,
                                queueIdentity           QueueIdentity OPTIONAL}

--Free-T-FPH      ::= OPERATION
--                    ARGUMENT SEQUENCE {
--                                servedUserDestination   PartyNumber,
--                                fPHReference            FPHReference}
--
  free-T-FPH OPERATION ::=
    {
        ARGUMENT Free-T-FPHArg     
        
        CODE global:{fPHOID free-T-FPH-operation(3)}   
    }

    Free-T-FPHArg ::= SEQUENCE {
        servedUserDestination   PartyNumber,
       fPHReference            FPHReference}

--Call-T-FPH      ::= OPERATION
--                    ARGUMENT SEQUENCE {
--                                fPHReference            FPHReference,
--                                calledFreephoneNr       CalledFreephoneNr OPTIONAL}

   call-T-FPH OPERATION ::=
    {
        ARGUMENT Call-T-FPHArg     
        
        CODE global:{fPHOID call-T-FPH-operation(4)}   
    }

    Call-T-FPHArg ::= SEQUENCE {
        fPHReference            FPHReference,
        calledFreephoneNr       CalledFreephoneNr OPTIONAL}

FPHReference		::= INTEGER (0..127)
CalledFreephoneNr	::= PartyNumber
QueueIdentity		::= INTEGER (0..127)

fPHOID	OBJECT IDENTIFIER		::= {itu-t(0) identified-organization(4) etsi(0) 210
								     freephone-operations(1)}

--callFPH			CallFPH			::= globalValue {fPHOID callFPH-operation(1)}
--monitor-T-FPH	Monitor-T-FPH	::= globalValue {fPHOID monitor-T-FPH-operation(2)}
--free-T-FPH		Free-T-FPH		::= globalValue {fPHOID free-T-FPH-operation(3)}
--call-T-FPH		Call-T-FPH		::= globalValue {fPHOID call-T-FPH-operation(4)}

END -- Freephone-Operations

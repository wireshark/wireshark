--
-- $Id$
--
-- EN 300 286-1 Ver. 1.2.4
--

User-To-User-Signalling-Operations {ccitt identified-organization etsi(0) 286
                                    operations-and-errors(1)}

DEFINITIONS ::=
BEGIN

EXPORTS                 UserUserService, RejectedByUser, RejectedByNetwork, Service, Preferred;

IMPORTS                 OPERATION, ERROR 
                        FROM Remote-Operations-Information-Objects 
    {joint-iso-itu-t (2) remote-operations (4) informationObjects(5) version1(0)};

  userUserService OPERATION ::=
    {
      ARGUMENT UserUserServiceArg 
      ERRORS {
        rejectedByTheUser |
        rejectedByTheNetwork }   
        
      CODE local:1       
    }

UserUserServiceArg ::= SEQUENCE {
          service   [1] IMPLICIT Service,
          preferred [2] IMPLICIT Preferred }

Service                 ::= INTEGER {
                                service1 (1), 
                                service2 (2), 
                                service3 (3)}
                                (1..3)

Preferred               ::= BOOLEAN     -- True  = preferred request
                                        -- False = required request
rejectedByTheNetwork ERROR ::= {CODE local:1}
rejectedByTheUser    ERROR ::= {CODE local:2}


--userUserService UserUserService     ::= 1
--rejectedByNetwork RejectedByNetwork ::= 1
--rejectedByUser RejectedByUser       ::= 2

END -- of User-To-User-Signalling-Operations

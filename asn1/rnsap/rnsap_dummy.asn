RNSAP-Dummy
DEFINITIONS AUTOMATIC TAGS ::= 
BEGIN

DummyInitiatingValue::= CHOICE {
	id-commonTransportChannelResourcesInitialisation		CommonTransportChannelResourcesRequest,		--	( 0),
	id-commonTransportChannelResourcesRelease				CommonTransportChannelResourcesReleaseRequest,	--	( 1),
	id-compressedModeCommand								CompressedModeCommand,						--	( 2),
	id-downlinkPowerControl									DL-PowerControlRequest,						--	( 3),
	id-downlinkPowerTimeslotControl							DL-PowerTimeslotControlRequest,				--	( 4),
	id-downlinkSignallingTransfer							DownlinkSignallingTransferRequest,			--	( 5),
	id-errorIndication										ErrorIndication,							--	( 6),
	id-dedicatedMeasurementFailure							DedicatedMeasurementFailureIndication,		--	( 7),
	id-dedicatedMeasurementInitiation						DedicatedMeasurementInitiationRequest,		--	( 8),
	id-dedicatedMeasurementReporting						DedicatedMeasurementReport,					--	( 9),
	id-dedicatedMeasurementTermination						DedicatedMeasurementTerminationRequest,		--	( 10),
	id-paging												PagingRequest,								--	( 11),
	id-physicalChannelReconfiguration						PhysicalChannelReconfigurationRequestTDD,	--	( 12),
	id-privateMessage										PrivateMessage,								--	( 13),
	id-radioLinkAddition									RadioLinkAdditionRequestFDD,				--	( 14),
	id-radioLinkAddition-TDD								RadioLinkAdditionRequestTDD,				--	( 14),
	id-radioLinkCongestion									RadioLinkCongestionIndication,				--	( 34),
	id-radioLinkDeletion									RadioLinkDeletionRequest,					--	( 15),
	id-radioLinkFailure										RadioLinkFailureIndication,					--	( 16),
	id-radioLinkPreemption									RadioLinkPreemptionRequiredIndication,		--	( 17),
	id-radioLinkRestoration									RadioLinkRestoreIndication,					--	( 18),
	id-radioLinkSetup										RadioLinkSetupRequestFDD,					--	( 19),
	id-radioLinkSetupTdd									RadioLinkSetupRequestTDD,					--	( 19),
	id-relocationCommit										RelocationCommit,							--	( 20),
	id-synchronisedRadioLinkReconfigurationCancellation		RadioLinkReconfigurationCancel,				--	( 21),
	id-synchronisedRadioLinkReconfigurationCommit			RadioLinkReconfigurationCommit,				--	( 22),
	id-synchronisedRadioLinkReconfigurationPreparation		RadioLinkReconfigurationPrepareFDD,			--	( 23),
	id-synchronisedRadioLinkReconfigurationPreparation-TDD	RadioLinkReconfigurationReadyTDD,			--	( 23),
	id-unSynchronisedRadioLinkReconfiguration				RadioLinkReconfigurationRequestFDD,			--	( 24),
	id-unSynchronisedRadioLinkReconfiguration-TDD			RadioLinkReconfigurationRequestTDD,			--	( 24),
	id-uplinkSignallingTransfer								UplinkSignallingTransferIndicationFDD,		--	( 25),
	id-uplinkSignallingTransfer-TDD							UplinkSignallingTransferIndicationTDD,		--	( 25),
	id-commonMeasurementFailure								CommonMeasurementFailureIndication,			--	( 26),
	id-commonMeasurementInitiation							CommonMeasurementInitiationRequest,			--	( 27),
	id-commonMeasurementReporting							CommonMeasurementReport,					--	( 28),
	id-commonMeasurementTermination							CommonMeasurementTerminationRequest,		--	( 29),
	id-informationExchangeFailure							InformationExchangeFailureIndication,		--	( 30),
	id-informationExchangeInitiation						InformationExchangeInitiationRequest,		--	( 31),
	id-informationReporting									InformationReport,							--	( 32),
	id-informationExchangeTermination						InformationExchangeTerminationRequest,		--	( 33),
	id-reset												ResetRequest,								--	( 35),
	id-radioLinkActivation 									RadioLinkActivationCommandFDD,				--	( 36),
	id-radioLinkActivation-TDD								RadioLinkActivationCommandTDD,				--	( 36),
	id-gERANuplinkSignallingTransfer						GERANUplinkSignallingTransferIndication,	--	( 37),
	id-radioLinkParameterUpdate								RadioLinkParameterUpdateIndicationFDD,		--	( 38),
	id-radioLinkParameterUpdate-TDD							RadioLinkParameterUpdateIndicationTDD,		--	( 38),
	id-uEMeasurementFailure									UEMeasurementFailureIndication,				--	( 39),
	id-uEMeasurementInitiation								UEMeasurementInitiationRequest,				--	( 40),
	id-uEMeasurementReporting								UEMeasurementReport,						--	( 41),
	id-uEMeasurementTermination								UEMeasurementTerminationRequest,			--	( 42),
	id-iurDeactivateTrace									IurDeactivateTrace,							--	( 43),
	id-iurInvokeTrace										IurInvokeTrace,								--	( 44),
	id-mBMSAttach											MBMSAttachCommand,							--	( 45),
	id-mBMSDetach											MBMSDetachCommand,							--	( 46),
	id-directInformationTransfer							DirectInformationTransfer,					--	( 48),
	...
}

DummySuccessfulOutcomeValue::= CHOICE {
	id-commonTransportChannelResourcesInitialisation		CommonTransportChannelResourcesResponseFDD,		--	( 0),
	id-commonTransportChannelResourcesInitialisation-TDD	CommonTransportChannelResourcesResponseTDD,		--	( 0),
	id-dedicatedMeasurementInitiation						DedicatedMeasurementInitiationResponse,			--	( 8),
	id-physicalChannelReconfiguration						PhysicalChannelReconfigurationCommand,			--	( 12),
	id-radioLinkAddition									RadioLinkAdditionResponseFDD,					--	( 14),
	id-radioLinkAddition-TDD								RadioLinkAdditionResponseTDD,					--	( 14),
	id-radioLinkDeletion									RadioLinkDeletionResponse,						--	( 15),
	id-radioLinkSetup										RadioLinkSetupResponseFDD,						--	( 19),
	id-radioLinkSetupTdd									RadioLinkSetupResponseTDD,						--	( 19),
	id-synchronisedRadioLinkReconfigurationPreparation		RadioLinkReconfigurationReadyFDD,				--	( 23),
	id-synchronisedRadioLinkReconfigurationPreparation-TDD	RadioLinkReconfigurationReadyTDD,				--	( 23),
	id-unSynchronisedRadioLinkReconfiguration				RadioLinkReconfigurationResponseFDD,			--	( 24),
	id-unSynchronisedRadioLinkReconfiguration-TDD			RadioLinkReconfigurationResponseTDD,			--	( 24),
	id-commonMeasurementInitiation							CommonMeasurementInitiationResponse,			--	( 27),
	id-informationExchangeInitiation						InformationExchangeInitiationResponse,			--	( 31),
	id-reset												ResetResponse,									--	( 35),
	id-uEMeasurementInitiation								UEMeasurementInitiationResponse,				--	( 40),
	...
}
DummyUnSuccessfulOutcomeValue::= CHOICE {
	id-commonTransportChannelResourcesInitialisation		CommonTransportChannelResourcesFailure,			--	( 0),
	id-dedicatedMeasurementInitiation						DedicatedMeasurementInitiationFailure,			--	( 8),
	id-physicalChannelReconfiguration						PhysicalChannelReconfigurationFailure,			--	( 12),
	id-radioLinkAddition									RadioLinkAdditionFailureFDD,					--	( 14),
	id-radioLinkAddition-TDD								RadioLinkAdditionFailureTDD,					--	( 14),
	id-radioLinkSetup										RadioLinkSetupFailureFDD,						--	( 19),
	id-radioLinkSetupTdd									RadioLinkSetupFailureTDD,						--	( 19),
	id-synchronisedRadioLinkReconfigurationPreparation		RadioLinkReconfigurationFailure,				--	( 23),
	id-unSynchronisedRadioLinkReconfiguration				RadioLinkReconfigurationFailure,				--	( 24),
	id-unSynchronisedRadioLinkReconfiguration-TDD			RadioLinkReconfigurationFailure,				--	( 24),
	id-commonMeasurementInitiation							CommonMeasurementInitiationFailure,				--	( 27),
	id-informationExchangeInitiation						InformationExchangeInitiationFailure,			--	( 31),
	id-uEMeasurementInitiation								UEMeasurementInitiationFailure,					--	( 40),
	...
}

END

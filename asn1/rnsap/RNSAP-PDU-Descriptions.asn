-- RNSAP-PDU-Descriptions.asn
--
-- Taken from 3GPP TS 25.423 V9.4.0 (2010-09)
-- http://www.3gpp.org/ftp/Specs/archive/25_series/25.423/25423-790.zip/25423-790.DOC
--
-- 9.3.2	Elementary Procedure Definitions
--

-- **************************************************************
--
-- Elementary Procedure definitions
--
-- **************************************************************

RNSAP-PDU-Descriptions {
itu-t (0) identified-organization (4) etsi (0) mobileDomain (0) 
umts-Access (20) modules (3) rnsap (1) version1 (1) rnsap-PDU-Descriptions (0) }

DEFINITIONS AUTOMATIC TAGS ::= 

BEGIN

-- **************************************************************
--
-- IE parameter types from other modules.
--
-- **************************************************************

IMPORTS
	Criticality,
	ProcedureID,
	TransactionID
FROM RNSAP-CommonDataTypes

	CommonMeasurementFailureIndication,
	CommonMeasurementInitiationFailure,
	CommonMeasurementInitiationRequest,
	CommonMeasurementInitiationResponse,
	CommonMeasurementReport,
	CommonMeasurementTerminationRequest,
	CommonTransportChannelResourcesFailure,
	CommonTransportChannelResourcesRequest,
	CommonTransportChannelResourcesReleaseRequest,
	CommonTransportChannelResourcesResponseFDD,
	CommonTransportChannelResourcesResponseTDD,
	CompressedModeCommand,
	DedicatedMeasurementFailureIndication,
	DedicatedMeasurementInitiationFailure,
	DedicatedMeasurementInitiationRequest,
	DedicatedMeasurementInitiationResponse,
	DedicatedMeasurementReport,
	DedicatedMeasurementTerminationRequest,
	DirectInformationTransfer,
	DL-PowerControlRequest,
	DL-PowerTimeslotControlRequest,
	DownlinkSignallingTransferRequest,
	ErrorIndication,
	EnhancedRelocationCancel,
	EnhancedRelocationFailure,
	EnhancedRelocationRequest,
	EnhancedRelocationResponse,
	EnhancedRelocationSignallingTransfer,
	EnhancedRelocationRelease,
	InformationExchangeFailureIndication,
	InformationExchangeInitiationFailure,
	InformationExchangeInitiationRequest,
	InformationExchangeInitiationResponse,
	InformationExchangeTerminationRequest,
	InformationReport,
	IurDeactivateTrace,
	IurInvokeTrace,
	MBMSAttachCommand,
	MBMSDetachCommand,
	MBSFNMCCHInformation,
	PagingRequest,
	PhysicalChannelReconfigurationCommand,
	PhysicalChannelReconfigurationFailure,
	PhysicalChannelReconfigurationRequestFDD,
	PhysicalChannelReconfigurationRequestTDD,
	PrivateMessage,
	RadioLinkActivationCommandFDD,
	RadioLinkActivationCommandTDD,
	RadioLinkAdditionFailureFDD,
	RadioLinkAdditionFailureTDD,
	RadioLinkAdditionRequestFDD,
	RadioLinkAdditionRequestTDD,
	RadioLinkAdditionResponseFDD,
	RadioLinkAdditionResponseTDD,
	RadioLinkCongestionIndication,
	RadioLinkDeletionRequest,
	RadioLinkDeletionResponse,
	RadioLinkFailureIndication,
	RadioLinkParameterUpdateIndicationFDD,
	RadioLinkParameterUpdateIndicationTDD,
	RadioLinkPreemptionRequiredIndication,
	RadioLinkReconfigurationCancel,
	RadioLinkReconfigurationCommit,
	RadioLinkReconfigurationFailure,
	RadioLinkReconfigurationPrepareFDD,
	RadioLinkReconfigurationPrepareTDD,
	RadioLinkReconfigurationReadyFDD,
	RadioLinkReconfigurationReadyTDD,
	RadioLinkReconfigurationRequestFDD,
	RadioLinkReconfigurationRequestTDD,
	RadioLinkReconfigurationResponseFDD,
	RadioLinkReconfigurationResponseTDD,
	RadioLinkRestoreIndication,
	RadioLinkSetupFailureFDD,
	RadioLinkSetupFailureTDD,
	RadioLinkSetupRequestFDD,
	RadioLinkSetupRequestTDD,
	RadioLinkSetupResponseFDD,
	RadioLinkSetupResponseTDD,
	RelocationCommit,
	ResetRequest,
	ResetResponse,
	UEMeasurementFailureIndication,
	UEMeasurementInitiationFailure,
	UEMeasurementInitiationRequest,
	UEMeasurementInitiationResponse,
	UEMeasurementReport,
	UEMeasurementTerminationRequest,
	SecondaryULFrequencyReport,
	SecondaryULFrequencyUpdateIndication,
	UplinkSignallingTransferIndicationFDD,
	UplinkSignallingTransferIndicationTDD,
	GERANUplinkSignallingTransferIndication
FROM RNSAP-PDU-Contents

	id-commonMeasurementFailure,
	id-commonMeasurementInitiation,
	id-commonMeasurementReporting,
	id-commonMeasurementTermination,
	id-commonTransportChannelResourcesInitialisation,
	id-commonTransportChannelResourcesRelease,
	id-compressedModeCommand,
	id-downlinkPowerControl,
	id-downlinkSignallingTransfer,
	id-downlinkPowerTimeslotControl,
	id-enhancedRelocation,
	id-enhancedRelocationCancel,
	id-enhancedRelocationSignallingTransfer,
	id-enhancedRelocationRelease,
	id-errorIndication,
	id-informationExchangeFailure,
	id-informationExchangeInitiation,
	id-informationReporting,
	id-informationExchangeTermination,
	id-iurDeactivateTrace,
	id-iurInvokeTrace,
	id-dedicatedMeasurementFailure,
	id-dedicatedMeasurementInitiation,
	id-dedicatedMeasurementReporting,
	id-dedicatedMeasurementTermination,
	id-directInformationTransfer,
	id-mBMSAttach,
	id-mBMSDetach,
	id-mBSFNMCCHInformation,
	id-paging,
	id-physicalChannelReconfiguration,
	id-privateMessage,
	id-radioLinkActivation,
	id-radioLinkAddition,
	id-radioLinkCongestion,
	id-radioLinkDeletion,
	id-radioLinkFailure,
	id-radioLinkParameterUpdate,
	id-radioLinkPreemption,
	id-radioLinkRestoration,
	id-radioLinkSetup,
	id-relocationCommit,
	id-reset,
	id-synchronisedRadioLinkReconfigurationCancellation,
	id-synchronisedRadioLinkReconfigurationCommit,
	id-synchronisedRadioLinkReconfigurationPreparation,
	id-uEMeasurementFailure,
	id-uEMeasurementInitiation,
	id-uEMeasurementReporting,
	id-uEMeasurementTermination, 
	id-secondaryULFrequencyReporting,
	id-secondaryULFrequencyUpdate,
	id-unSynchronisedRadioLinkReconfiguration,
	id-uplinkSignallingTransfer,
	id-gERANuplinkSignallingTransfer
FROM RNSAP-Constants;

-- **************************************************************
--
-- Interface Elementary Procedure Class
--
-- **************************************************************

RNSAP-ELEMENTARY-PROCEDURE ::= CLASS {
	&InitiatingMessage				,
	&SuccessfulOutcome				OPTIONAL,
	&UnsuccessfulOutcome				OPTIONAL,
	&Outcome					OPTIONAL,
	&procedureID			ProcedureID 	UNIQUE,
	&criticality			Criticality 	DEFAULT ignore
}
WITH SYNTAX {
	INITIATING MESSAGE		&InitiatingMessage
	[SUCCESSFUL OUTCOME		&SuccessfulOutcome]
	[UNSUCCESSFUL OUTCOME		&UnsuccessfulOutcome]
	[OUTCOME			&Outcome]
	PROCEDURE ID			&procedureID
	[CRITICALITY			&criticality]
}

-- **************************************************************
--
-- Interface PDU Definition
--
-- **************************************************************

RNSAP-PDU ::= CHOICE {
	initiatingMessage	InitiatingMessage,
	successfulOutcome	SuccessfulOutcome,
	unsuccessfulOutcome	UnsuccessfulOutcome,
	outcome			Outcome,
	...
}

InitiatingMessage ::= SEQUENCE {
	procedureID	RNSAP-ELEMENTARY-PROCEDURE.&procedureID		({RNSAP-ELEMENTARY-PROCEDURES}),
	criticality	RNSAP-ELEMENTARY-PROCEDURE.&criticality		({RNSAP-ELEMENTARY-PROCEDURES}{@procedureID}),
	transactionID	TransactionID,
	value		RNSAP-ELEMENTARY-PROCEDURE.&InitiatingMessage	({RNSAP-ELEMENTARY-PROCEDURES}{@procedureID})
}

SuccessfulOutcome ::= SEQUENCE {
	procedureID	RNSAP-ELEMENTARY-PROCEDURE.&procedureID		({RNSAP-ELEMENTARY-PROCEDURES}),
	criticality	RNSAP-ELEMENTARY-PROCEDURE.&criticality		({RNSAP-ELEMENTARY-PROCEDURES}{@procedureID}),
	transactionID	TransactionID,
	value		RNSAP-ELEMENTARY-PROCEDURE.&SuccessfulOutcome	({RNSAP-ELEMENTARY-PROCEDURES}{@procedureID})
}

UnsuccessfulOutcome ::= SEQUENCE {
	procedureID	RNSAP-ELEMENTARY-PROCEDURE.&procedureID		({RNSAP-ELEMENTARY-PROCEDURES}),
	criticality	RNSAP-ELEMENTARY-PROCEDURE.&criticality		({RNSAP-ELEMENTARY-PROCEDURES}{@procedureID}),
	transactionID	TransactionID,
	value		RNSAP-ELEMENTARY-PROCEDURE.&UnsuccessfulOutcome	({RNSAP-ELEMENTARY-PROCEDURES}{@procedureID})
}

Outcome ::= SEQUENCE {
	procedureID	RNSAP-ELEMENTARY-PROCEDURE.&procedureID		({RNSAP-ELEMENTARY-PROCEDURES}),
	criticality	RNSAP-ELEMENTARY-PROCEDURE.&criticality		({RNSAP-ELEMENTARY-PROCEDURES}{@procedureID}),
	transactionID	TransactionID,
	value		RNSAP-ELEMENTARY-PROCEDURE.&Outcome		({RNSAP-ELEMENTARY-PROCEDURES}{@procedureID})
}

-- **************************************************************
--
-- Interface Elementary Procedure List
--
-- **************************************************************

RNSAP-ELEMENTARY-PROCEDURES RNSAP-ELEMENTARY-PROCEDURE ::= {
	RNSAP-ELEMENTARY-PROCEDURES-CLASS-1			|
	RNSAP-ELEMENTARY-PROCEDURES-CLASS-2			|
	RNSAP-ELEMENTARY-PROCEDURES-CLASS-3			,
	...
}

RNSAP-ELEMENTARY-PROCEDURES-CLASS-1 RNSAP-ELEMENTARY-PROCEDURE ::= {
	radioLinkSetupFDD										|
	radioLinkSetupTDD										|
	radioLinkAdditionFDD									|
	radioLinkAdditionTDD									|
	radioLinkDeletion										|
	synchronisedRadioLinkReconfigurationPreparationFDD		|
	synchronisedRadioLinkReconfigurationPreparationTDD		|
	unSynchronisedRadioLinkReconfigurationFDD				|
	unSynchronisedRadioLinkReconfigurationTDD				|
	physicalChannelReconfigurationFDD						|
	physicalChannelReconfigurationTDD						|
	dedicatedMeasurementInitiation							|
	commonTransportChannelResourcesInitialisationFDD		|
	commonTransportChannelResourcesInitialisationTDD		,
	...,
	commonMeasurementInitiation								|
	informationExchangeInitiation							|
	reset													|
	uEMeasurementInitiation									|
	enhancedRelocation
}

RNSAP-ELEMENTARY-PROCEDURES-CLASS-2 RNSAP-ELEMENTARY-PROCEDURE ::= {
	uplinkSignallingTransferFDD							|
	uplinkSignallingTransferTDD							|
	downlinkSignallingTransfer							|
	relocationCommit									|
	paging												|
	synchronisedRadioLinkReconfigurationCommit			|
	synchronisedRadioLinkReconfigurationCancellation	|
	radioLinkFailure									|
	radioLinkPreemption									|
	radioLinkRestoration								|
	dedicatedMeasurementReporting						|
	dedicatedMeasurementTermination						|
	dedicatedMeasurementFailure							|
	downlinkPowerControlFDD								|
	downlinkPowerTimeslotControl						|
	compressedModeCommandFDD							|
	commonTransportChannelResourcesRelease				|
	errorIndication										|
	privateMessage										,
	...,
	radioLinkCongestion									|
	commonMeasurementFailure							|
	commonMeasurementReporting							|
	commonMeasurementTermination						|
	informationExchangeFailure							|
	informationExchangeTermination						|
	informationReporting								|
	radioLinkActivationFDD								|
	radioLinkActivationTDD								|
	gERANuplinkSignallingTransfer						|
	radioLinkParameterUpdateFDD							|
	radioLinkParameterUpdateTDD							|
	uEMeasurementReporting								|
	uEMeasurementTermination							|
	uEMeasurementFailure								|
	iurInvokeTrace										|
	iurDeactivateTrace									|
	mBMSAttach											|
	mBMSDetach											|
	directInformationTransfer							|
	enhancedRelocationCancel							|
	enhancedRelocationSignallingTransfer				|
	enhancedRelocationRelease							|
	mBSFNMCCHInformation								|
	secondaryULFrequencyReportingFDD					|
	secondaryULFrequencyUpdateFDD
								



}

RNSAP-ELEMENTARY-PROCEDURES-CLASS-3 RNSAP-ELEMENTARY-PROCEDURE ::= {
	...
}

-- **************************************************************
--
-- Interface Elementary Procedures
--
-- **************************************************************

radioLinkSetupFDD RNSAP-ELEMENTARY-PROCEDURE ::= {
	INITIATING MESSAGE	RadioLinkSetupRequestFDD
	SUCCESSFUL OUTCOME	RadioLinkSetupResponseFDD
	UNSUCCESSFUL OUTCOME	RadioLinkSetupFailureFDD
	PROCEDURE ID		{ procedureCode id-radioLinkSetup, ddMode fdd }
	CRITICALITY		reject
}

radioLinkSetupTDD RNSAP-ELEMENTARY-PROCEDURE ::= {
	INITIATING MESSAGE	RadioLinkSetupRequestTDD
	SUCCESSFUL OUTCOME	RadioLinkSetupResponseTDD
	UNSUCCESSFUL OUTCOME	RadioLinkSetupFailureTDD
	PROCEDURE ID		{ procedureCode id-radioLinkSetup, ddMode tdd }
	CRITICALITY		reject
}

radioLinkAdditionFDD RNSAP-ELEMENTARY-PROCEDURE ::= {
	INITIATING MESSAGE	RadioLinkAdditionRequestFDD
	SUCCESSFUL OUTCOME	RadioLinkAdditionResponseFDD
	UNSUCCESSFUL OUTCOME	RadioLinkAdditionFailureFDD
	PROCEDURE ID		{ procedureCode id-radioLinkAddition , ddMode fdd }
	CRITICALITY		reject
}

radioLinkAdditionTDD RNSAP-ELEMENTARY-PROCEDURE ::= {
	INITIATING MESSAGE	RadioLinkAdditionRequestTDD
	SUCCESSFUL OUTCOME	RadioLinkAdditionResponseTDD
	UNSUCCESSFUL OUTCOME	RadioLinkAdditionFailureTDD
	PROCEDURE ID		{ procedureCode id-radioLinkAddition , ddMode tdd }
	CRITICALITY		reject
}

radioLinkDeletion RNSAP-ELEMENTARY-PROCEDURE ::= {
	INITIATING MESSAGE	RadioLinkDeletionRequest
	SUCCESSFUL OUTCOME	RadioLinkDeletionResponse
	PROCEDURE ID		{ procedureCode id-radioLinkDeletion, ddMode common }
	CRITICALITY		reject
}

synchronisedRadioLinkReconfigurationPreparationFDD RNSAP-ELEMENTARY-PROCEDURE ::= {
	INITIATING MESSAGE	RadioLinkReconfigurationPrepareFDD
	SUCCESSFUL OUTCOME	RadioLinkReconfigurationReadyFDD
	UNSUCCESSFUL OUTCOME	RadioLinkReconfigurationFailure
	PROCEDURE ID		{ procedureCode id-synchronisedRadioLinkReconfigurationPreparation, ddMode fdd }
	CRITICALITY		reject
}

synchronisedRadioLinkReconfigurationPreparationTDD RNSAP-ELEMENTARY-PROCEDURE ::= {
	INITIATING MESSAGE	RadioLinkReconfigurationPrepareTDD
	SUCCESSFUL OUTCOME	RadioLinkReconfigurationReadyTDD
	UNSUCCESSFUL OUTCOME	RadioLinkReconfigurationFailure
	PROCEDURE ID		{ procedureCode id-synchronisedRadioLinkReconfigurationPreparation, ddMode tdd }
	CRITICALITY		reject
}

unSynchronisedRadioLinkReconfigurationFDD RNSAP-ELEMENTARY-PROCEDURE ::= {
	INITIATING MESSAGE	RadioLinkReconfigurationRequestFDD
	SUCCESSFUL OUTCOME	RadioLinkReconfigurationResponseFDD
	UNSUCCESSFUL OUTCOME	RadioLinkReconfigurationFailure
	PROCEDURE ID		{ procedureCode id-unSynchronisedRadioLinkReconfiguration, ddMode fdd }
	CRITICALITY		reject
}

unSynchronisedRadioLinkReconfigurationTDD RNSAP-ELEMENTARY-PROCEDURE ::= {
	INITIATING MESSAGE	RadioLinkReconfigurationRequestTDD
	SUCCESSFUL OUTCOME	RadioLinkReconfigurationResponseTDD
	UNSUCCESSFUL OUTCOME	RadioLinkReconfigurationFailure
	PROCEDURE ID		{ procedureCode id-unSynchronisedRadioLinkReconfiguration, ddMode tdd }
	CRITICALITY		reject
}

physicalChannelReconfigurationFDD RNSAP-ELEMENTARY-PROCEDURE ::= {
	INITIATING MESSAGE	PhysicalChannelReconfigurationRequestFDD
	SUCCESSFUL OUTCOME	PhysicalChannelReconfigurationCommand
	UNSUCCESSFUL OUTCOME	PhysicalChannelReconfigurationFailure
	PROCEDURE ID		{ procedureCode id-physicalChannelReconfiguration, ddMode fdd }
	CRITICALITY		reject
}

physicalChannelReconfigurationTDD RNSAP-ELEMENTARY-PROCEDURE ::= {
	INITIATING MESSAGE	PhysicalChannelReconfigurationRequestTDD
	SUCCESSFUL OUTCOME	PhysicalChannelReconfigurationCommand
	UNSUCCESSFUL OUTCOME	PhysicalChannelReconfigurationFailure
	PROCEDURE ID		{ procedureCode id-physicalChannelReconfiguration, ddMode tdd }
	CRITICALITY		reject
}

dedicatedMeasurementInitiation RNSAP-ELEMENTARY-PROCEDURE ::= {
	INITIATING MESSAGE	DedicatedMeasurementInitiationRequest
	SUCCESSFUL OUTCOME	DedicatedMeasurementInitiationResponse
	UNSUCCESSFUL OUTCOME	DedicatedMeasurementInitiationFailure
	PROCEDURE ID		{ procedureCode id-dedicatedMeasurementInitiation, ddMode common }
	CRITICALITY		reject
}

commonTransportChannelResourcesInitialisationFDD RNSAP-ELEMENTARY-PROCEDURE ::= {
	INITIATING MESSAGE	CommonTransportChannelResourcesRequest
	SUCCESSFUL OUTCOME	CommonTransportChannelResourcesResponseFDD
	UNSUCCESSFUL OUTCOME	CommonTransportChannelResourcesFailure
	PROCEDURE ID		{ procedureCode id-commonTransportChannelResourcesInitialisation, ddMode fdd }
	CRITICALITY		reject
}

commonTransportChannelResourcesInitialisationTDD RNSAP-ELEMENTARY-PROCEDURE ::= {
	INITIATING MESSAGE	CommonTransportChannelResourcesRequest
	SUCCESSFUL OUTCOME	CommonTransportChannelResourcesResponseTDD
	UNSUCCESSFUL OUTCOME	CommonTransportChannelResourcesFailure
	PROCEDURE ID		{ procedureCode id-commonTransportChannelResourcesInitialisation, ddMode tdd }
	CRITICALITY		reject
}

uplinkSignallingTransferFDD RNSAP-ELEMENTARY-PROCEDURE ::= {
	INITIATING MESSAGE	UplinkSignallingTransferIndicationFDD
	PROCEDURE ID		{ procedureCode id-uplinkSignallingTransfer, ddMode fdd }
	CRITICALITY		ignore
}

uplinkSignallingTransferTDD RNSAP-ELEMENTARY-PROCEDURE ::= {
	INITIATING MESSAGE	UplinkSignallingTransferIndicationTDD
	PROCEDURE ID		{ procedureCode id-uplinkSignallingTransfer, ddMode tdd }
	CRITICALITY		ignore
}

downlinkSignallingTransfer RNSAP-ELEMENTARY-PROCEDURE ::= {
	INITIATING MESSAGE	DownlinkSignallingTransferRequest
	PROCEDURE ID		{ procedureCode id-downlinkSignallingTransfer, ddMode common }
	CRITICALITY		ignore
}

relocationCommit RNSAP-ELEMENTARY-PROCEDURE ::= {
	INITIATING MESSAGE	RelocationCommit
	PROCEDURE ID		{ procedureCode id-relocationCommit, ddMode common }
	CRITICALITY		ignore
}

paging RNSAP-ELEMENTARY-PROCEDURE ::= {
	INITIATING MESSAGE	PagingRequest
	PROCEDURE ID		{ procedureCode id-paging, ddMode common }
	CRITICALITY		ignore
}

synchronisedRadioLinkReconfigurationCommit RNSAP-ELEMENTARY-PROCEDURE ::= {
	INITIATING MESSAGE	RadioLinkReconfigurationCommit
	PROCEDURE ID		{ procedureCode id-synchronisedRadioLinkReconfigurationCommit, ddMode common }
	CRITICALITY		ignore
}

synchronisedRadioLinkReconfigurationCancellation RNSAP-ELEMENTARY-PROCEDURE ::= {
	INITIATING MESSAGE	RadioLinkReconfigurationCancel
	PROCEDURE ID		{ procedureCode id-synchronisedRadioLinkReconfigurationCancellation, ddMode common }
	CRITICALITY		ignore
}

radioLinkFailure RNSAP-ELEMENTARY-PROCEDURE ::= {
	INITIATING MESSAGE	RadioLinkFailureIndication
	PROCEDURE ID		{ procedureCode id-radioLinkFailure, ddMode common }
	CRITICALITY		ignore
}

radioLinkPreemption RNSAP-ELEMENTARY-PROCEDURE ::= {
	INITIATING MESSAGE	RadioLinkPreemptionRequiredIndication
	PROCEDURE ID		{ procedureCode id-radioLinkPreemption, ddMode common }
	CRITICALITY		ignore
}

radioLinkRestoration RNSAP-ELEMENTARY-PROCEDURE ::= {
	INITIATING MESSAGE	RadioLinkRestoreIndication
	PROCEDURE ID		{ procedureCode id-radioLinkRestoration, ddMode common }
	CRITICALITY		ignore
}

dedicatedMeasurementReporting RNSAP-ELEMENTARY-PROCEDURE ::= {
	INITIATING MESSAGE	DedicatedMeasurementReport
	PROCEDURE ID		{ procedureCode id-dedicatedMeasurementReporting, ddMode common }
	CRITICALITY		ignore
}

dedicatedMeasurementTermination RNSAP-ELEMENTARY-PROCEDURE ::= {
	INITIATING MESSAGE	DedicatedMeasurementTerminationRequest
	PROCEDURE ID		{ procedureCode id-dedicatedMeasurementTermination, ddMode common }
	CRITICALITY		ignore
}

dedicatedMeasurementFailure RNSAP-ELEMENTARY-PROCEDURE ::= {
	INITIATING MESSAGE	DedicatedMeasurementFailureIndication
	PROCEDURE ID		{ procedureCode id-dedicatedMeasurementFailure, ddMode common }
	CRITICALITY		ignore
}

radioLinkCongestion RNSAP-ELEMENTARY-PROCEDURE ::= {
	INITIATING MESSAGE	RadioLinkCongestionIndication
	PROCEDURE ID		{ procedureCode id-radioLinkCongestion, ddMode common }
	CRITICALITY		ignore
}

downlinkPowerControlFDD RNSAP-ELEMENTARY-PROCEDURE ::= {
	INITIATING MESSAGE	DL-PowerControlRequest
	PROCEDURE ID		{ procedureCode id-downlinkPowerControl, ddMode fdd }
	CRITICALITY		ignore
}

downlinkPowerTimeslotControl RNSAP-ELEMENTARY-PROCEDURE ::= {
	INITIATING MESSAGE	DL-PowerTimeslotControlRequest
	PROCEDURE ID		{ procedureCode id-downlinkPowerTimeslotControl, ddMode tdd }
	CRITICALITY		ignore
}

compressedModeCommandFDD RNSAP-ELEMENTARY-PROCEDURE ::= {
	INITIATING MESSAGE	CompressedModeCommand
	PROCEDURE ID		{ procedureCode id-compressedModeCommand, ddMode fdd }
	CRITICALITY		ignore
}

commonTransportChannelResourcesRelease RNSAP-ELEMENTARY-PROCEDURE ::= {
	INITIATING MESSAGE	CommonTransportChannelResourcesReleaseRequest
	PROCEDURE ID		{ procedureCode id-commonTransportChannelResourcesRelease, ddMode common }
	CRITICALITY		ignore
}

errorIndication RNSAP-ELEMENTARY-PROCEDURE ::= {
	INITIATING MESSAGE	ErrorIndication
	PROCEDURE ID		{ procedureCode id-errorIndication, ddMode common }
	CRITICALITY		ignore
}

commonMeasurementInitiation RNSAP-ELEMENTARY-PROCEDURE ::= {
	INITIATING MESSAGE		CommonMeasurementInitiationRequest
	SUCCESSFUL OUTCOME		CommonMeasurementInitiationResponse
	UNSUCCESSFUL OUTCOME	CommonMeasurementInitiationFailure
	PROCEDURE ID			{ procedureCode id-commonMeasurementInitiation, ddMode common }
	CRITICALITY				reject
}

commonMeasurementReporting RNSAP-ELEMENTARY-PROCEDURE ::= {
	INITIATING MESSAGE	CommonMeasurementReport
	PROCEDURE ID		{ procedureCode id-commonMeasurementReporting, ddMode common }
	CRITICALITY			ignore
}

commonMeasurementTermination RNSAP-ELEMENTARY-PROCEDURE ::= {
	INITIATING MESSAGE	CommonMeasurementTerminationRequest
	PROCEDURE ID		{ procedureCode id-commonMeasurementTermination, ddMode common }
	CRITICALITY		ignore
}

commonMeasurementFailure RNSAP-ELEMENTARY-PROCEDURE ::= {
	INITIATING MESSAGE	CommonMeasurementFailureIndication
	PROCEDURE ID		{ procedureCode id-commonMeasurementFailure, ddMode common }
	CRITICALITY		ignore
}

informationExchangeInitiation RNSAP-ELEMENTARY-PROCEDURE ::= {
	INITIATING MESSAGE		InformationExchangeInitiationRequest
	SUCCESSFUL OUTCOME		InformationExchangeInitiationResponse
	UNSUCCESSFUL OUTCOME	InformationExchangeInitiationFailure
	PROCEDURE ID			{ procedureCode id-informationExchangeInitiation, ddMode common }
	CRITICALITY				reject
}

informationReporting RNSAP-ELEMENTARY-PROCEDURE ::= {
	INITIATING MESSAGE		InformationReport
	PROCEDURE ID			{ procedureCode id-informationReporting, ddMode common }
	CRITICALITY				ignore
}

informationExchangeTermination RNSAP-ELEMENTARY-PROCEDURE ::= {
	INITIATING MESSAGE		InformationExchangeTerminationRequest
	PROCEDURE ID			{ procedureCode id-informationExchangeTermination, ddMode common }
	CRITICALITY				ignore
}

informationExchangeFailure RNSAP-ELEMENTARY-PROCEDURE ::= {
	INITIATING MESSAGE		InformationExchangeFailureIndication
	PROCEDURE ID			{ procedureCode id-informationExchangeFailure, ddMode common }
	CRITICALITY				ignore
}

privateMessage RNSAP-ELEMENTARY-PROCEDURE ::= {
	INITIATING MESSAGE	PrivateMessage
	PROCEDURE ID		{ procedureCode id-privateMessage, ddMode common }
	CRITICALITY		ignore
}

reset RNSAP-ELEMENTARY-PROCEDURE ::= {
	INITIATING MESSAGE		ResetRequest
	SUCCESSFUL OUTCOME		ResetResponse
	PROCEDURE ID 			{ procedureCode id-reset, ddMode common } 
	CRITICALITY 			reject
}

radioLinkActivationFDD RNSAP-ELEMENTARY-PROCEDURE ::= {
	INITIATING MESSAGE		RadioLinkActivationCommandFDD
	PROCEDURE ID			{ procedureCode id-radioLinkActivation, ddMode fdd }
	CRITICALITY				ignore
}

radioLinkActivationTDD RNSAP-ELEMENTARY-PROCEDURE ::= {
	INITIATING MESSAGE		RadioLinkActivationCommandTDD
	PROCEDURE ID			{ procedureCode id-radioLinkActivation, ddMode tdd }
	CRITICALITY				ignore
}

gERANuplinkSignallingTransfer RNSAP-ELEMENTARY-PROCEDURE ::= {
	INITIATING MESSAGE	GERANUplinkSignallingTransferIndication
	PROCEDURE ID		{ procedureCode id-gERANuplinkSignallingTransfer, ddMode common }
	CRITICALITY		ignore
}

radioLinkParameterUpdateFDD RNSAP-ELEMENTARY-PROCEDURE ::= {
	INITIATING MESSAGE		RadioLinkParameterUpdateIndicationFDD
	PROCEDURE ID 			{ procedureCode id-radioLinkParameterUpdate, ddMode fdd }
	CRITICALITY 			ignore
}

radioLinkParameterUpdateTDD RNSAP-ELEMENTARY-PROCEDURE ::= {
	INITIATING MESSAGE		RadioLinkParameterUpdateIndicationTDD
	PROCEDURE ID 			{ procedureCode id-radioLinkParameterUpdate, ddMode tdd }
	CRITICALITY 			ignore
}

uEMeasurementInitiation RNSAP-ELEMENTARY-PROCEDURE ::= {
	INITIATING MESSAGE	UEMeasurementInitiationRequest
	SUCCESSFUL OUTCOME	UEMeasurementInitiationResponse
	UNSUCCESSFUL OUTCOME	UEMeasurementInitiationFailure
	PROCEDURE ID		{ procedureCode id-uEMeasurementInitiation, ddMode tdd }
	CRITICALITY		reject
}

uEMeasurementReporting RNSAP-ELEMENTARY-PROCEDURE ::= {
	INITIATING MESSAGE	UEMeasurementReport
	PROCEDURE ID		{ procedureCode id-uEMeasurementReporting, ddMode tdd }
	CRITICALITY		ignore
}

uEMeasurementTermination RNSAP-ELEMENTARY-PROCEDURE ::= {
	INITIATING MESSAGE	UEMeasurementTerminationRequest
	PROCEDURE ID		{ procedureCode id-uEMeasurementTermination, ddMode tdd }
	CRITICALITY		ignore
}

uEMeasurementFailure RNSAP-ELEMENTARY-PROCEDURE ::= {
	INITIATING MESSAGE	UEMeasurementFailureIndication
	PROCEDURE ID		{ procedureCode id-uEMeasurementFailure, ddMode tdd }
	CRITICALITY		ignore
}

iurInvokeTrace RNSAP-ELEMENTARY-PROCEDURE ::= {
	INITIATING MESSAGE	IurInvokeTrace
	PROCEDURE ID		{ procedureCode id-iurInvokeTrace, ddMode common }
	CRITICALITY			ignore
}

iurDeactivateTrace RNSAP-ELEMENTARY-PROCEDURE ::= {
	INITIATING MESSAGE	IurDeactivateTrace
	PROCEDURE ID		{ procedureCode id-iurDeactivateTrace, ddMode common }
	CRITICALITY			ignore
}

mBMSAttach RNSAP-ELEMENTARY-PROCEDURE ::= {
	INITIATING MESSAGE		MBMSAttachCommand
	PROCEDURE ID			{ procedureCode id-mBMSAttach, ddMode common }
	CRITICALITY				ignore
}

mBMSDetach RNSAP-ELEMENTARY-PROCEDURE ::= {
	INITIATING MESSAGE		MBMSDetachCommand
	PROCEDURE ID			{ procedureCode id-mBMSDetach, ddMode common }
	CRITICALITY				ignore
}

directInformationTransfer RNSAP-ELEMENTARY-PROCEDURE ::= {
	INITIATING MESSAGE		DirectInformationTransfer
	PROCEDURE ID			{ procedureCode id-directInformationTransfer, ddMode common }
	CRITICALITY				ignore
}

enhancedRelocation RNSAP-ELEMENTARY-PROCEDURE ::= {
	INITIATING MESSAGE	EnhancedRelocationRequest
	SUCCESSFUL OUTCOME	EnhancedRelocationResponse
	UNSUCCESSFUL OUTCOME	EnhancedRelocationFailure
	PROCEDURE ID		{ procedureCode id-enhancedRelocation, ddMode common }
	CRITICALITY		reject
}

enhancedRelocationCancel RNSAP-ELEMENTARY-PROCEDURE ::= {
	INITIATING MESSAGE		EnhancedRelocationCancel
	PROCEDURE ID			{ procedureCode id-enhancedRelocationCancel, ddMode common }
	CRITICALITY				ignore
}

enhancedRelocationSignallingTransfer RNSAP-ELEMENTARY-PROCEDURE ::= {
	INITIATING MESSAGE		EnhancedRelocationSignallingTransfer
	PROCEDURE ID			{ procedureCode id-enhancedRelocationSignallingTransfer, ddMode common }
	CRITICALITY				ignore
}

enhancedRelocationRelease RNSAP-ELEMENTARY-PROCEDURE ::= {
	INITIATING MESSAGE		EnhancedRelocationRelease
	PROCEDURE ID			{ procedureCode id-enhancedRelocationRelease, ddMode common }
	CRITICALITY				ignore
}

mBSFNMCCHInformation RNSAP-ELEMENTARY-PROCEDURE ::= {
	INITIATING MESSAGE		MBSFNMCCHInformation
	PROCEDURE ID			{ procedureCode id-mBSFNMCCHInformation, ddMode common }
	CRITICALITY				reject
}

secondaryULFrequencyReportingFDD RNSAP-ELEMENTARY-PROCEDURE ::= {
	INITIATING MESSAGE		SecondaryULFrequencyReport
	PROCEDURE ID			{ procedureCode id-secondaryULFrequencyReporting, ddMode fdd }
	CRITICALITY				ignore
}

secondaryULFrequencyUpdateFDD RNSAP-ELEMENTARY-PROCEDURE ::= {
	INITIATING MESSAGE		SecondaryULFrequencyUpdateIndication
	PROCEDURE ID 			{ procedureCode id-secondaryULFrequencyUpdate, ddMode fdd }
	CRITICALITY 			ignore
}

END

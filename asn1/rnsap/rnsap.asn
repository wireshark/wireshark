--9.3.2	Elementary Procedure Definitions
-- **************************************************************
--
-- Elementary Procedure definitions
--
-- **************************************************************

RNSAP-PDU-Descriptions {
itu-t (0) identified-organization (4) etsi (0) mobileDomain (0) 
umts-Access (20) modules (3) rnsap (1) version1 (1) rnsap-PDU-Descriptions (0) }

DEFINITIONS AUTOMATIC TAGS ::= 

BEGIN

-- **************************************************************
--
-- IE parameter types from other modules.
--
-- **************************************************************

--IMPORTS
--	Criticality,
--	ProcedureID,
--	TransactionID
--FROM RNSAP-CommonDataTypes

--	CommonMeasurementFailureIndication,
--	CommonMeasurementInitiationFailure,
--	CommonMeasurementInitiationRequest,
--	CommonMeasurementInitiationResponse,
--	CommonMeasurementReport,
--	CommonMeasurementTerminationRequest,
--	CommonTransportChannelResourcesFailure,
--	CommonTransportChannelResourcesRequest,
--	CommonTransportChannelResourcesReleaseRequest,
--	CommonTransportChannelResourcesResponseFDD,
--	CommonTransportChannelResourcesResponseTDD,
--	CompressedModeCommand,
--	DedicatedMeasurementFailureIndication,
--	DedicatedMeasurementInitiationFailure,
--	DedicatedMeasurementInitiationRequest,
--	DedicatedMeasurementInitiationResponse,
--	DedicatedMeasurementReport,
--	DedicatedMeasurementTerminationRequest,
--	DirectInformationTransfer,
--	DL-PowerControlRequest,
--	DL-PowerTimeslotControlRequest,
--	DownlinkSignallingTransferRequest,
--	ErrorIndication,
--	InformationExchangeFailureIndication,
--	InformationExchangeInitiationFailure,
--	InformationExchangeInitiationRequest,
--	InformationExchangeInitiationResponse,
--	InformationExchangeTerminationRequest,
--	InformationReport,
--	IurDeactivateTrace,
--	IurInvokeTrace,
--	MBMSAttachCommand,
--	MBMSDetachCommand,
--	PagingRequest,
--	PhysicalChannelReconfigurationCommand,
--	PhysicalChannelReconfigurationFailure,
--	PhysicalChannelReconfigurationRequestFDD,
--	PhysicalChannelReconfigurationRequestTDD,
--	PrivateMessage,
--	RadioLinkActivationCommandFDD,
--	RadioLinkActivationCommandTDD,
--	RadioLinkAdditionFailureFDD,
--	RadioLinkAdditionFailureTDD,
--	RadioLinkAdditionRequestFDD,
--	RadioLinkAdditionRequestTDD,
--	RadioLinkAdditionResponseFDD,
--	RadioLinkAdditionResponseTDD,
--	RadioLinkCongestionIndication,
--	RadioLinkDeletionRequest,
--	RadioLinkDeletionResponse,
--	RadioLinkFailureIndication,
--	RadioLinkParameterUpdateIndicationFDD,
--	RadioLinkParameterUpdateIndicationTDD,
--	RadioLinkPreemptionRequiredIndication,
--	RadioLinkReconfigurationCancel,
--	RadioLinkReconfigurationCommit,
--	RadioLinkReconfigurationFailure,
--	RadioLinkReconfigurationPrepareFDD,
--	RadioLinkReconfigurationPrepareTDD,
--	RadioLinkReconfigurationReadyFDD,
--	RadioLinkReconfigurationReadyTDD,
--	RadioLinkReconfigurationRequestFDD,
--	RadioLinkReconfigurationRequestTDD,
--	RadioLinkReconfigurationResponseFDD,
--	RadioLinkReconfigurationResponseTDD,
--	RadioLinkRestoreIndication,
--	RadioLinkSetupFailureFDD,
--	RadioLinkSetupFailureTDD,
--	RadioLinkSetupRequestFDD,
--	RadioLinkSetupRequestTDD,
--	RadioLinkSetupResponseFDD,
--	RadioLinkSetupResponseTDD,
--	RelocationCommit,
--	ResetRequest,
--	ResetResponse,
--	UEMeasurementFailureIndication,
--	UEMeasurementInitiationFailure,
--	UEMeasurementInitiationRequest,
--	UEMeasurementInitiationResponse,
--	UEMeasurementReport,
--	UEMeasurementTerminationRequest,
--	UplinkSignallingTransferIndicationFDD,
--	UplinkSignallingTransferIndicationTDD,
--	GERANUplinkSignallingTransferIndication
--FROM RNSAP-PDU-Contents

--	id-commonMeasurementFailure,
--	id-commonMeasurementInitiation,
--	id-commonMeasurementReporting,
--	id-commonMeasurementTermination,
--	id-commonTransportChannelResourcesInitialisation,
--	id-commonTransportChannelResourcesRelease,
--	id-compressedModeCommand,
--	id-downlinkPowerControl,
--	id-downlinkSignallingTransfer,
--	id-downlinkPowerTimeslotControl,
--	id-errorIndication,
--	id-informationExchangeFailure,
--	id-informationExchangeInitiation,
--	id-informationReporting,
--	id-informationExchangeTermination,
--	id-iurDeactivateTrace,
--	id-iurInvokeTrace,
--	id-dedicatedMeasurementFailure,
--	id-dedicatedMeasurementInitiation,
--	id-dedicatedMeasurementReporting,
--	id-dedicatedMeasurementTermination,
--	id-directInformationTransfer,
--	id-mBMSAttach,
--	id-mBMSDetach,
--	id-paging,
--	id-physicalChannelReconfiguration,
--	id-privateMessage,
--	id-radioLinkActivation,
--	id-radioLinkAddition,
--	id-radioLinkCongestion,
--	id-radioLinkDeletion,
--	id-radioLinkFailure,
--	id-radioLinkParameterUpdate,
--	id-radioLinkPreemption,
--	id-radioLinkRestoration,
--	id-radioLinkSetup,
--	id-relocationCommit,
--	id-reset,
--	id-synchronisedRadioLinkReconfigurationCancellation,
--	id-synchronisedRadioLinkReconfigurationCommit,
--	id-synchronisedRadioLinkReconfigurationPreparation,
--	id-uEMeasurementFailure,
--	id-uEMeasurementInitiation,
--	id-uEMeasurementReporting,
--	id-uEMeasurementTermination,
--	id-unSynchronisedRadioLinkReconfiguration,
--	id-uplinkSignallingTransfer,
--	id-gERANuplinkSignallingTransfer
--FROM RNSAP-Constants;

-- **************************************************************
--
-- Interface Elementary Procedure Class
--
-- **************************************************************

--RNSAP-ELEMENTARY-PROCEDURE ::= CLASS {
--	&InitiatingMessage				,
--	&SuccessfulOutcome				OPTIONAL,
--	&UnsuccessfulOutcome				OPTIONAL,
--	&Outcome					OPTIONAL,
--	&procedureID			ProcedureID 	UNIQUE,
--	&criticality			Criticality 	DEFAULT ignore
--}
--WITH SYNTAX {
--	INITIATING MESSAGE		&InitiatingMessage
--	[SUCCESSFUL OUTCOME		&SuccessfulOutcome]
--	[UNSUCCESSFUL OUTCOME		&UnsuccessfulOutcome]
--	[OUTCOME			&Outcome]
--	PROCEDURE ID			&procedureID
--	[CRITICALITY			&criticality]
--}

-- **************************************************************
--
-- Interface PDU Definition
--
-- **************************************************************

RNSAP-PDU ::= CHOICE {
	initiatingMessage	InitiatingMessage,
	successfulOutcome	SuccessfulOutcome,
	unsuccessfulOutcome	UnsuccessfulOutcome,
	outcome				Outcome,
	...
}

--InitiatingMessage ::= SEQUENCE {
--	procedureID	RNSAP-ELEMENTARY-PROCEDURE.&procedureID		({RNSAP-ELEMENTARY-PROCEDURES}),
--	criticality	RNSAP-ELEMENTARY-PROCEDURE.&criticality		({RNSAP-ELEMENTARY-PROCEDURES}{@procedureID}),
--	transactionID	TransactionID,
--	value		RNSAP-ELEMENTARY-PROCEDURE.&InitiatingMessage	({RNSAP-ELEMENTARY-PROCEDURES}{@procedureID})
--}

InitiatingMessage ::= SEQUENCE {
	procedureID				ProcedureID,
	criticality				Criticality,
	transactionID 			TransactionID,
	initiatingMessageValue	InitiatingMessageValue
}

InitiatingMessageValue ::= ANY

--SuccessfulOutcome ::= SEQUENCE {
--	procedureID	RNSAP-ELEMENTARY-PROCEDURE.&procedureID		({RNSAP-ELEMENTARY-PROCEDURES}),
--	criticality	RNSAP-ELEMENTARY-PROCEDURE.&criticality		({RNSAP-ELEMENTARY-PROCEDURES}{@procedureID}),
--	transactionID	TransactionID,
--	value		RNSAP-ELEMENTARY-PROCEDURE.&SuccessfulOutcome	({RNSAP-ELEMENTARY-PROCEDURES}{@procedureID})
--}

SuccessfulOutcome ::= SEQUENCE {
	procedureID				ProcedureID,
	criticality				Criticality,
 	transactionID 			TransactionID,
	successfulOutcomeValue	SuccessfulOutcomeValue
}

SuccessfulOutcomeValue ::= ANY

--UnsuccessfulOutcome ::= SEQUENCE {
--	procedureID	RNSAP-ELEMENTARY-PROCEDURE.&procedureID		({RNSAP-ELEMENTARY-PROCEDURES}),
--	criticality	RNSAP-ELEMENTARY-PROCEDURE.&criticality		({RNSAP-ELEMENTARY-PROCEDURES}{@procedureID}),
--	transactionID	TransactionID,
--	value		RNSAP-ELEMENTARY-PROCEDURE.&UnsuccessfulOutcome	({RNSAP-ELEMENTARY-PROCEDURES}{@procedureID})
--}

UnsuccessfulOutcome ::= SEQUENCE {
	procedureID					ProcedureID,
	criticality					Criticality,
 	transactionID 				TransactionID,
	unsuccessfulOutcomeValue	UnsuccessfulOutcomeValue
}

UnsuccessfulOutcomeValue ::= ANY


--Outcome ::= SEQUENCE {
--	procedureID	RNSAP-ELEMENTARY-PROCEDURE.&procedureID		({RNSAP-ELEMENTARY-PROCEDURES}),
--	criticality	RNSAP-ELEMENTARY-PROCEDURE.&criticality		({RNSAP-ELEMENTARY-PROCEDURES}{@procedureID}),
--	transactionID	TransactionID,
--	value		RNSAP-ELEMENTARY-PROCEDURE.&Outcome		({RNSAP-ELEMENTARY-PROCEDURES}{@procedureID})
--}

Outcome ::= SEQUENCE {
	procedureID				ProcedureID,
	criticality				Criticality,
 	transactionID 			TransactionID,
	outcomeValue			OutcomeValue
}

OutcomeValue ::= ANY
-- **************************************************************
--
-- Interface Elementary Procedure List
--
-- **************************************************************

--RNSAP-ELEMENTARY-PROCEDURES RNSAP-ELEMENTARY-PROCEDURE ::= {
--	RNSAP-ELEMENTARY-PROCEDURES-CLASS-1			|
--	RNSAP-ELEMENTARY-PROCEDURES-CLASS-2			|
--	RNSAP-ELEMENTARY-PROCEDURES-CLASS-3			,
--	...
--}

--RNSAP-ELEMENTARY-PROCEDURES-CLASS-1 RNSAP-ELEMENTARY-PROCEDURE ::= {
--	radioLinkSetupFDD										|
--	radioLinkSetupTDD										|
--	radioLinkAdditionFDD									|
--	radioLinkAdditionTDD									|
--	radioLinkDeletion										|
--	synchronisedRadioLinkReconfigurationPreparationFDD		|
--	synchronisedRadioLinkReconfigurationPreparationTDD		|
--	unSynchronisedRadioLinkReconfigurationFDD				|
--	unSynchronisedRadioLinkReconfigurationTDD				|
--	physicalChannelReconfigurationFDD						|
--	physicalChannelReconfigurationTDD						|
--	dedicatedMeasurementInitiation							|
--	commonTransportChannelResourcesInitialisationFDD		|
--	commonTransportChannelResourcesInitialisationTDD		,
--	...,
--	commonMeasurementInitiation								|
--	informationExchangeInitiation							|
--	reset													|
--	uEMeasurementInitiation
--}

--RNSAP-ELEMENTARY-PROCEDURES-CLASS-2 RNSAP-ELEMENTARY-PROCEDURE ::= {
--	uplinkSignallingTransferFDD							|
--	uplinkSignallingTransferTDD							|
--	downlinkSignallingTransfer							|
--	relocationCommit									|
--	paging												|
--	synchronisedRadioLinkReconfigurationCommit			|
--	synchronisedRadioLinkReconfigurationCancellation	|
--	radioLinkFailure									|
--	radioLinkPreemption									|
--	radioLinkRestoration								|
--	dedicatedMeasurementReporting						|
--	dedicatedMeasurementTermination						|
--	dedicatedMeasurementFailure							|
--	downlinkPowerControlFDD								|
--	downlinkPowerTimeslotControl						|
--	compressedModeCommandFDD							|
--	commonTransportChannelResourcesRelease				|
--	errorIndication										|
--	privateMessage										,
--	...,
--	radioLinkCongestion									|
--	commonMeasurementFailure							|
--	commonMeasurementReporting							|
--	commonMeasurementTermination						|
--	informationExchangeFailure							|
--	informationExchangeTermination						|
--	informationReporting								|
--	radioLinkActivationFDD								|
--	radioLinkActivationTDD								|
--	gERANuplinkSignallingTransfer						|
--	radioLinkParameterUpdateFDD							|
--	radioLinkParameterUpdateTDD							|
--	uEMeasurementReporting								|
--	uEMeasurementTermination							|
--	uEMeasurementFailure								|
--	iurInvokeTrace										|
--	iurDeactivateTrace									|
--	mBMSAttach											|
--	mBMSDetach											|
--	directInformationTransfer
--
--}

--RNSAP-ELEMENTARY-PROCEDURES-CLASS-3 RNSAP-ELEMENTARY-PROCEDURE ::= {
--	...
--}
-- **************************************************************
--
-- Interface Elementary Procedures
--
-- **************************************************************
-- **************************************************************
--
-- Interface Elementary Procedures
--
-- **************************************************************

--radioLinkSetupFDD RNSAP-ELEMENTARY-PROCEDURE ::= {
--	INITIATING MESSAGE	RadioLinkSetupRequestFDD
--	SUCCESSFUL OUTCOME	RadioLinkSetupResponseFDD
--	UNSUCCESSFUL OUTCOME	RadioLinkSetupFailureFDD
--	PROCEDURE ID		{ procedureCode id-radioLinkSetup, ddMode fdd }
--	CRITICALITY		reject
--}
--radioLinkSetupTDD RNSAP-ELEMENTARY-PROCEDURE ::= {
--	INITIATING MESSAGE	RadioLinkSetupRequestTDD
--	SUCCESSFUL OUTCOME	RadioLinkSetupResponseTDD
--	UNSUCCESSFUL OUTCOME	RadioLinkSetupFailureTDD
--	PROCEDURE ID		{ procedureCode id-radioLinkSetup, ddMode tdd }
--	CRITICALITY		reject
--}
--downlinkSignallingTransfer RNSAP-ELEMENTARY-PROCEDURE ::= {
--	INITIATING MESSAGE	DownlinkSignallingTransferRequest
--	PROCEDURE ID		{ procedureCode id-downlinkSignallingTransfer, ddMode common }
--	CRITICALITY		ignore
--}
--radioLinkAdditionFDD RNSAP-ELEMENTARY-PROCEDURE ::= {
--	INITIATING MESSAGE	RadioLinkAdditionRequestFDD
--	SUCCESSFUL OUTCOME	RadioLinkAdditionResponseFDD
--	UNSUCCESSFUL OUTCOME	RadioLinkAdditionFailureFDD
--	PROCEDURE ID		{ procedureCode id-radioLinkAddition , ddMode fdd }
--	CRITICALITY		reject
--}

--radioLinkAdditionTDD RNSAP-ELEMENTARY-PROCEDURE ::= {
--	INITIATING MESSAGE	RadioLinkAdditionRequestTDD
--	SUCCESSFUL OUTCOME	RadioLinkAdditionResponseTDD
--	UNSUCCESSFUL OUTCOME	RadioLinkAdditionFailureTDD
--	PROCEDURE ID		{ procedureCode id-radioLinkAddition , ddMode tdd }
--	CRITICALITY		reject
--}

--radioLinkDeletion RNSAP-ELEMENTARY-PROCEDURE ::= {
--	INITIATING MESSAGE	RadioLinkDeletionRequest
--	SUCCESSFUL OUTCOME	RadioLinkDeletionResponse
--	PROCEDURE ID		{ procedureCode id-radioLinkDeletion, ddMode common }
--	CRITICALITY		reject
--}

--synchronisedRadioLinkReconfigurationPreparationFDD RNSAP-ELEMENTARY-PROCEDURE ::= {
--	INITIATING MESSAGE	RadioLinkReconfigurationPrepareFDD
--	SUCCESSFUL OUTCOME	RadioLinkReconfigurationReadyFDD
--	UNSUCCESSFUL OUTCOME	RadioLinkReconfigurationFailure
--	PROCEDURE ID		{ procedureCode id-synchronisedRadioLinkReconfigurationPreparation, ddMode fdd }
--	CRITICALITY		reject
--}

--synchronisedRadioLinkReconfigurationPreparationTDD RNSAP-ELEMENTARY-PROCEDURE ::= {
--	INITIATING MESSAGE	RadioLinkReconfigurationPrepareTDD
--	SUCCESSFUL OUTCOME	RadioLinkReconfigurationReadyTDD
--	UNSUCCESSFUL OUTCOME	RadioLinkReconfigurationFailure
--	PROCEDURE ID		{ procedureCode id-synchronisedRadioLinkReconfigurationPreparation, ddMode tdd }
--	CRITICALITY		reject
--}

--unSynchronisedRadioLinkReconfigurationFDD RNSAP-ELEMENTARY-PROCEDURE ::= {
--	INITIATING MESSAGE	RadioLinkReconfigurationRequestFDD
--	SUCCESSFUL OUTCOME	RadioLinkReconfigurationResponseFDD
--	UNSUCCESSFUL OUTCOME	RadioLinkReconfigurationFailure
--	PROCEDURE ID		{ procedureCode id-unSynchronisedRadioLinkReconfiguration, ddMode fdd }
--	CRITICALITY		reject
--}

--unSynchronisedRadioLinkReconfigurationTDD RNSAP-ELEMENTARY-PROCEDURE ::= {
--	INITIATING MESSAGE	RadioLinkReconfigurationRequestTDD
--	SUCCESSFUL OUTCOME	RadioLinkReconfigurationResponseTDD
--	UNSUCCESSFUL OUTCOME	RadioLinkReconfigurationFailure
--	PROCEDURE ID		{ procedureCode id-unSynchronisedRadioLinkReconfiguration, ddMode tdd }
--	CRITICALITY		reject
--}

--physicalChannelReconfigurationTDD RNSAP-ELEMENTARY-PROCEDURE ::= {
--	INITIATING MESSAGE	PhysicalChannelReconfigurationRequestTDD
--	SUCCESSFUL OUTCOME	PhysicalChannelReconfigurationCommand
--	UNSUCCESSFUL OUTCOME	PhysicalChannelReconfigurationFailure
--	PROCEDURE ID		{ procedureCode id-physicalChannelReconfiguration, ddMode tdd }
--	CRITICALITY		reject
--}

--dedicatedMeasurementInitiation RNSAP-ELEMENTARY-PROCEDURE ::= {
--	INITIATING MESSAGE	DedicatedMeasurementInitiationRequest
--	SUCCESSFUL OUTCOME	DedicatedMeasurementInitiationResponse
--	UNSUCCESSFUL OUTCOME	DedicatedMeasurementInitiationFailure
--	PROCEDURE ID		{ procedureCode id-dedicatedMeasurementInitiation, ddMode common }
--	CRITICALITY		reject
--}

--commonTransportChannelResourcesInitialisationFDD RNSAP-ELEMENTARY-PROCEDURE ::= {
--	INITIATING MESSAGE	CommonTransportChannelResourcesRequest
--	SUCCESSFUL OUTCOME	CommonTransportChannelResourcesResponseFDD
--	UNSUCCESSFUL OUTCOME	CommonTransportChannelResourcesFailure
--	PROCEDURE ID		{ procedureCode id-commonTransportChannelResourcesInitialisation, ddMode fdd }
--	CRITICALITY		reject
--}

--commonTransportChannelResourcesInitialisationTDD RNSAP-ELEMENTARY-PROCEDURE ::= {
--	INITIATING MESSAGE	CommonTransportChannelResourcesRequest
--	SUCCESSFUL OUTCOME	CommonTransportChannelResourcesResponseTDD
--	UNSUCCESSFUL OUTCOME	CommonTransportChannelResourcesFailure
--	PROCEDURE ID		{ procedureCode id-commonTransportChannelResourcesInitialisation, ddMode tdd }
--	CRITICALITY		reject
--}

--uplinkSignallingTransferFDD RNSAP-ELEMENTARY-PROCEDURE ::= {
--	INITIATING MESSAGE	UplinkSignallingTransferIndicationFDD
--	PROCEDURE ID		{ procedureCode id-uplinkSignallingTransfer, ddMode fdd }
--	CRITICALITY		ignore
--}

--uplinkSignallingTransferTDD RNSAP-ELEMENTARY-PROCEDURE ::= {
--	INITIATING MESSAGE	UplinkSignallingTransferIndicationTDD
--	PROCEDURE ID		{ procedureCode id-uplinkSignallingTransfer, ddMode tdd }
--	CRITICALITY		ignore
--}

--downlinkSignallingTransfer RNSAP-ELEMENTARY-PROCEDURE ::= {
--	INITIATING MESSAGE	DownlinkSignallingTransferRequest
--	PROCEDURE ID		{ procedureCode id-downlinkSignallingTransfer, ddMode common }
--	CRITICALITY		ignore
--}

--relocationCommit RNSAP-ELEMENTARY-PROCEDURE ::= {
--	INITIATING MESSAGE	RelocationCommit
--	PROCEDURE ID		{ procedureCode id-relocationCommit, ddMode common }
--	CRITICALITY		ignore
--}

--paging RNSAP-ELEMENTARY-PROCEDURE ::= {
--	INITIATING MESSAGE	PagingRequest
--	PROCEDURE ID		{ procedureCode id-paging, ddMode common }
--	CRITICALITY		ignore
--}

--synchronisedRadioLinkReconfigurationCommit RNSAP-ELEMENTARY-PROCEDURE ::= {
--	INITIATING MESSAGE	RadioLinkReconfigurationCommit
--	PROCEDURE ID		{ procedureCode id-synchronisedRadioLinkReconfigurationCommit, ddMode common }
--	CRITICALITY		ignore
--}

--synchronisedRadioLinkReconfigurationCancellation RNSAP-ELEMENTARY-PROCEDURE ::= {
--	INITIATING MESSAGE	RadioLinkReconfigurationCancel
--	PROCEDURE ID		{ procedureCode id-synchronisedRadioLinkReconfigurationCancellation, ddMode common }
--	CRITICALITY		ignore
--}

--radioLinkFailure RNSAP-ELEMENTARY-PROCEDURE ::= {
--	INITIATING MESSAGE	RadioLinkFailureIndication
--	PROCEDURE ID		{ procedureCode id-radioLinkFailure, ddMode common }
--	CRITICALITY		ignore
--}

--radioLinkPreemption RNSAP-ELEMENTARY-PROCEDURE ::= {
--	INITIATING MESSAGE	RadioLinkPreemptionRequiredIndication
--	PROCEDURE ID		{ procedureCode id-radioLinkPreemption, ddMode common }
--	CRITICALITY		ignore
--}

--radioLinkRestoration RNSAP-ELEMENTARY-PROCEDURE ::= {
--	INITIATING MESSAGE	RadioLinkRestoreIndication
--	PROCEDURE ID		{ procedureCode id-radioLinkRestoration, ddMode common }
--	CRITICALITY		ignore
--}

--dedicatedMeasurementReporting RNSAP-ELEMENTARY-PROCEDURE ::= {
--	INITIATING MESSAGE	DedicatedMeasurementReport
--	PROCEDURE ID		{ procedureCode id-dedicatedMeasurementReporting, ddMode common }
--	CRITICALITY		ignore
--}

--dedicatedMeasurementTermination RNSAP-ELEMENTARY-PROCEDURE ::= {
--	INITIATING MESSAGE	DedicatedMeasurementTerminationRequest
--	PROCEDURE ID		{ procedureCode id-dedicatedMeasurementTermination, ddMode common }
--	CRITICALITY		ignore
--}

--dedicatedMeasurementFailure RNSAP-ELEMENTARY-PROCEDURE ::= {
--	INITIATING MESSAGE	DedicatedMeasurementFailureIndication
--	PROCEDURE ID		{ procedureCode id-dedicatedMeasurementFailure, ddMode common }
--	CRITICALITY		ignore
--}

--radioLinkCongestion RNSAP-ELEMENTARY-PROCEDURE ::= {
--	INITIATING MESSAGE	RadioLinkCongestionIndication
--	PROCEDURE ID		{ procedureCode id-radioLinkCongestion, ddMode common }
--	CRITICALITY		ignore
--}

--downlinkPowerControlFDD RNSAP-ELEMENTARY-PROCEDURE ::= {
--	INITIATING MESSAGE	DL-PowerControlRequest
--	PROCEDURE ID		{ procedureCode id-downlinkPowerControl, ddMode fdd }
--	CRITICALITY		ignore
--}

--downlinkPowerTimeslotControl RNSAP-ELEMENTARY-PROCEDURE ::= {
--	INITIATING MESSAGE	DL-PowerTimeslotControlRequest
--	PROCEDURE ID		{ procedureCode id-downlinkPowerTimeslotControl, ddMode tdd }
--	CRITICALITY		ignore
--}

--compressedModeCommandFDD RNSAP-ELEMENTARY-PROCEDURE ::= {
--	INITIATING MESSAGE	CompressedModeCommand
--	PROCEDURE ID		{ procedureCode id-compressedModeCommand, ddMode fdd }
--	CRITICALITY		ignore
--}

--commonTransportChannelResourcesRelease RNSAP-ELEMENTARY-PROCEDURE ::= {
--	INITIATING MESSAGE	CommonTransportChannelResourcesReleaseRequest
--	PROCEDURE ID		{ procedureCode id-commonTransportChannelResourcesRelease, ddMode common }
--	CRITICALITY		ignore
--}

--errorIndication RNSAP-ELEMENTARY-PROCEDURE ::= {
--	INITIATING MESSAGE	ErrorIndication
--	PROCEDURE ID		{ procedureCode id-errorIndication, ddMode common }
--	CRITICALITY		ignore
--}

--commonMeasurementInitiation RNSAP-ELEMENTARY-PROCEDURE ::= {
--	INITIATING MESSAGE		CommonMeasurementInitiationRequest
--	SUCCESSFUL OUTCOME		CommonMeasurementInitiationResponse
--	UNSUCCESSFUL OUTCOME	CommonMeasurementInitiationFailure
--	PROCEDURE ID			{ procedureCode id-commonMeasurementInitiation, ddMode common }
--	CRITICALITY				reject
--}

--commonMeasurementReporting RNSAP-ELEMENTARY-PROCEDURE ::= {
--	INITIATING MESSAGE	CommonMeasurementReport
--	PROCEDURE ID		{ procedureCode id-commonMeasurementReporting, ddMode common }
--	CRITICALITY			ignore
--}

--commonMeasurementTermination RNSAP-ELEMENTARY-PROCEDURE ::= {
--	INITIATING MESSAGE	CommonMeasurementTerminationRequest
--	PROCEDURE ID		{ procedureCode id-commonMeasurementTermination, ddMode common }
--	CRITICALITY		ignore
--}

--commonMeasurementFailure RNSAP-ELEMENTARY-PROCEDURE ::= {
--	INITIATING MESSAGE	CommonMeasurementFailureIndication
--	PROCEDURE ID		{ procedureCode id-commonMeasurementFailure, ddMode common }
--	CRITICALITY		ignore
--}

--informationExchangeInitiation RNSAP-ELEMENTARY-PROCEDURE ::= {
--	INITIATING MESSAGE		InformationExchangeInitiationRequest
--	SUCCESSFUL OUTCOME		InformationExchangeInitiationResponse
--	UNSUCCESSFUL OUTCOME	InformationExchangeInitiationFailure
--	PROCEDURE ID			{ procedureCode id-informationExchangeInitiation, ddMode common }
--	CRITICALITY				reject
--}

--informationReporting RNSAP-ELEMENTARY-PROCEDURE ::= {
--	INITIATING MESSAGE		InformationReport
--	PROCEDURE ID			{ procedureCode id-informationReporting, ddMode common }
--	CRITICALITY				ignore
--}

--informationExchangeTermination RNSAP-ELEMENTARY-PROCEDURE ::= {
--	INITIATING MESSAGE		InformationExchangeTerminationRequest
--	PROCEDURE ID			{ procedureCode id-informationExchangeTermination, ddMode common }
--	CRITICALITY				ignore
--}

--informationExchangeFailure RNSAP-ELEMENTARY-PROCEDURE ::= {
--	INITIATING MESSAGE		InformationExchangeFailureIndication
--	PROCEDURE ID			{ procedureCode id-informationExchangeFailure, ddMode common }
--	CRITICALITY				ignore
--}

--privateMessage RNSAP-ELEMENTARY-PROCEDURE ::= {
--	INITIATING MESSAGE	PrivateMessage
--	PROCEDURE ID		{ procedureCode id-privateMessage, ddMode common }
--	CRITICALITY		ignore
--}

--reset RNSAP-ELEMENTARY-PROCEDURE ::= {
--	INITIATING MESSAGE		ResetRequest
--	SUCCESSFUL OUTCOME		ResetResponse
--	PROCEDURE ID 			{ procedureCode id-reset, ddMode common } 
--	CRITICALITY 			reject
--}

--radioLinkActivationFDD RNSAP-ELEMENTARY-PROCEDURE ::= {
--	INITIATING MESSAGE		RadioLinkActivationCommandFDD
--	PROCEDURE ID			{ procedureCode id-radioLinkActivation, ddMode fdd }
--	CRITICALITY				ignore
--}

--radioLinkActivationTDD RNSAP-ELEMENTARY-PROCEDURE ::= {
--	INITIATING MESSAGE		RadioLinkActivationCommandTDD
--	PROCEDURE ID			{ procedureCode id-radioLinkActivation, ddMode tdd }
--	CRITICALITY				ignore
--}

--gERANuplinkSignallingTransfer RNSAP-ELEMENTARY-PROCEDURE ::= {
--	INITIATING MESSAGE	GERANUplinkSignallingTransferIndication
--	PROCEDURE ID		{ procedureCode id-gERANuplinkSignallingTransfer, ddMode common }
--	CRITICALITY		ignore
--}

--radioLinkParameterUpdateFDD RNSAP-ELEMENTARY-PROCEDURE ::= {
--	INITIATING MESSAGE		RadioLinkParameterUpdateIndicationFDD
--	PROCEDURE ID 			{ procedureCode id-radioLinkParameterUpdate, ddMode fdd }
--	CRITICALITY 			ignore
--}

--radioLinkParameterUpdateTDD RNSAP-ELEMENTARY-PROCEDURE ::= {
--	INITIATING MESSAGE		RadioLinkParameterUpdateIndicationTDD
--	PROCEDURE ID 			{ procedureCode id-radioLinkParameterUpdate, ddMode tdd }
--	CRITICALITY 			ignore
--}

--uEMeasurementInitiation RNSAP-ELEMENTARY-PROCEDURE ::= {
--	INITIATING MESSAGE	UEMeasurementInitiationRequest
--	SUCCESSFUL OUTCOME	UEMeasurementInitiationResponse
--	UNSUCCESSFUL OUTCOME	UEMeasurementInitiationFailure
--	PROCEDURE ID		{ procedureCode id-uEMeasurementInitiation, ddMode tdd }
--	CRITICALITY		reject
--}

--uEMeasurementReporting RNSAP-ELEMENTARY-PROCEDURE ::= {
--	INITIATING MESSAGE	UEMeasurementReport
--	PROCEDURE ID		{ procedureCode id-uEMeasurementReporting, ddMode tdd }
--	CRITICALITY		ignore
--}

--uEMeasurementTermination RNSAP-ELEMENTARY-PROCEDURE ::= {
--	INITIATING MESSAGE	UEMeasurementTerminationRequest
--	PROCEDURE ID		{ procedureCode id-uEMeasurementTermination, ddMode tdd }
--	CRITICALITY		ignore
--}

--uEMeasurementFailure RNSAP-ELEMENTARY-PROCEDURE ::= {
--	INITIATING MESSAGE	UEMeasurementFailureIndication
--	PROCEDURE ID		{ procedureCode id-uEMeasurementFailure, ddMode tdd }
--	CRITICALITY		ignore
--}

--iurInvokeTrace RNSAP-ELEMENTARY-PROCEDURE ::= {
--	INITIATING MESSAGE	IurInvokeTrace
--	PROCEDURE ID		{ procedureCode id-iurInvokeTrace, ddMode common }
--	CRITICALITY			ignore
--}

--iurDeactivateTrace RNSAP-ELEMENTARY-PROCEDURE ::= {
--	INITIATING MESSAGE	IurDeactivateTrace
--	PROCEDURE ID		{ procedureCode id-iurDeactivateTrace, ddMode common }
--	CRITICALITY			ignore
--}

--mBMSAttach RNSAP-ELEMENTARY-PROCEDURE ::= {
--	INITIATING MESSAGE		MBMSAttachCommand
--	PROCEDURE ID			{ procedureCode id-mBMSAttach, ddMode common }
--	CRITICALITY				ignore
--}

--mBMSDetach RNSAP-ELEMENTARY-PROCEDURE ::= {
--	INITIATING MESSAGE		MBMSDetachCommand
--	PROCEDURE ID			{ procedureCode id-mBMSDetach, ddMode common }
--	CRITICALITY				ignore
--}

--directInformationTransfer RNSAP-ELEMENTARY-PROCEDURE ::= {
--	INITIATING MESSAGE		DirectInformationTransfer
--	PROCEDURE ID			{ procedureCode id-directInformationTransfer, ddMode common }
--	CRITICALITY				ignore
--}

DummyInitiatingValue::= CHOICE {
	id-commonTransportChannelResourcesInitialisation		CommonTransportChannelResourcesRequest,		--	( 0),
	id-commonTransportChannelResourcesRelease				CommonTransportChannelResourcesReleaseRequest,	--	( 1),
	id-compressedModeCommand								CompressedModeCommand,						--	( 2),
	id-downlinkPowerControl									DL-PowerControlRequest,						--	( 3),
	id-downlinkPowerTimeslotControl							DL-PowerTimeslotControlRequest,				--	( 4),
	id-downlinkSignallingTransfer							DownlinkSignallingTransferRequest,			--	( 5),
	id-errorIndication										ErrorIndication,							--	( 6),
	id-dedicatedMeasurementFailure							DedicatedMeasurementFailureIndication,		--	( 7),
	id-dedicatedMeasurementInitiation						DedicatedMeasurementInitiationRequest,		--	( 8),
	id-dedicatedMeasurementReporting						DedicatedMeasurementReport,					--	( 9),
	id-dedicatedMeasurementTermination						DedicatedMeasurementTerminationRequest,		--	( 10),
	id-paging												PagingRequest,								--	( 11),
	id-physicalChannelReconfiguration						PhysicalChannelReconfigurationRequestTDD,	--	( 12),
	id-privateMessage										PrivateMessage,								--	( 13),
	id-radioLinkAddition									RadioLinkAdditionRequestFDD,				--	( 14),
	id-radioLinkAddition-TDD								RadioLinkAdditionRequestTDD,				--	( 14),
	id-radioLinkCongestion									RadioLinkCongestionIndication,				--	( 34),
	id-radioLinkDeletion									RadioLinkDeletionRequest,					--	( 15),
	id-radioLinkFailure										RadioLinkFailureIndication,					--	( 16),
	id-radioLinkPreemption									RadioLinkPreemptionRequiredIndication,		--	( 17),
	id-radioLinkRestoration									RadioLinkRestoreIndication,					--	( 18),
	id-radioLinkSetup										RadioLinkSetupRequestFDD,					--	( 19),
	id-radioLinkSetupTdd									RadioLinkSetupRequestTDD,					--	( 19),
	id-relocationCommit										RelocationCommit,							--	( 20),
	id-synchronisedRadioLinkReconfigurationCancellation		RadioLinkReconfigurationCancel,				--	( 21),
	id-synchronisedRadioLinkReconfigurationCommit			RadioLinkReconfigurationCommit,				--	( 22),
	id-synchronisedRadioLinkReconfigurationPreparation		RadioLinkReconfigurationPrepareFDD,			--	( 23),
	id-synchronisedRadioLinkReconfigurationPreparation-TDD	RadioLinkReconfigurationReadyTDD,			--	( 23),
	id-unSynchronisedRadioLinkReconfiguration				RadioLinkReconfigurationRequestFDD,			--	( 24),
	id-unSynchronisedRadioLinkReconfiguration-TDD			RadioLinkReconfigurationRequestTDD,			--	( 24),
	id-uplinkSignallingTransfer								UplinkSignallingTransferIndicationFDD,		--	( 25),
	id-uplinkSignallingTransfer-TDD							UplinkSignallingTransferIndicationTDD,		--	( 25),
	id-commonMeasurementFailure								CommonMeasurementFailureIndication,			--	( 26),
	id-commonMeasurementInitiation							CommonMeasurementInitiationRequest,			--	( 27),
	id-commonMeasurementReporting							CommonMeasurementReport,					--	( 28),
	id-commonMeasurementTermination							CommonMeasurementTerminationRequest,		--	( 29),
	id-informationExchangeFailure							InformationExchangeFailureIndication,		--	( 30),
	id-informationExchangeInitiation						InformationExchangeInitiationRequest,		--	( 31),
	id-informationReporting									InformationReport,							--	( 32),
	id-informationExchangeTermination						InformationExchangeTerminationRequest,		--	( 33),
	id-reset												ResetRequest,								--	( 35),
	id-radioLinkActivation 									RadioLinkActivationCommandFDD,				--	( 36),
	id-radioLinkActivation-TDD								RadioLinkActivationCommandTDD,				--	( 36),
	id-gERANuplinkSignallingTransfer						GERANUplinkSignallingTransferIndication,	--	( 37),
	id-radioLinkParameterUpdate								RadioLinkParameterUpdateIndicationFDD,		--	( 38),
	id-radioLinkParameterUpdate-TDD							RadioLinkParameterUpdateIndicationTDD,		--	( 38),
	id-uEMeasurementFailure									UEMeasurementFailureIndication,				--	( 39),
	id-uEMeasurementInitiation								UEMeasurementInitiationRequest,				--	( 40),
	id-uEMeasurementReporting								UEMeasurementReport,						--	( 41),
	id-uEMeasurementTermination								UEMeasurementTerminationRequest,			--	( 42),
	id-iurDeactivateTrace									IurDeactivateTrace,							--	( 43),
	id-iurInvokeTrace										IurInvokeTrace,								--	( 44),
	id-mBMSAttach											MBMSAttachCommand,							--	( 45),
	id-mBMSDetach											MBMSDetachCommand,							--	( 46),
	id-directInformationTransfer							DirectInformationTransfer,					--	( 48),
	...
}

DummySuccessfulOutcomeValue::= CHOICE {
	id-commonTransportChannelResourcesInitialisation		CommonTransportChannelResourcesResponseFDD,		--	( 0),
	id-commonTransportChannelResourcesInitialisation-TDD	CommonTransportChannelResourcesResponseTDD,		--	( 0),
	id-dedicatedMeasurementInitiation						DedicatedMeasurementInitiationResponse,			--	( 8),
	id-physicalChannelReconfiguration						PhysicalChannelReconfigurationCommand,			--	( 12),
	id-radioLinkAddition									RadioLinkAdditionResponseFDD,					--	( 14),
	id-radioLinkAddition-TDD								RadioLinkAdditionResponseTDD,					--	( 14),
	id-radioLinkDeletion									RadioLinkDeletionResponse,						--	( 15),
	id-radioLinkSetup										RadioLinkSetupResponseFDD,						--	( 19),
	id-radioLinkSetupTdd									RadioLinkSetupResponseTDD,						--	( 19),
	id-synchronisedRadioLinkReconfigurationPreparation		RadioLinkReconfigurationReadyFDD,				--	( 23),
	id-synchronisedRadioLinkReconfigurationPreparation-TDD	RadioLinkReconfigurationReadyTDD,				--	( 23),
	id-unSynchronisedRadioLinkReconfiguration				RadioLinkReconfigurationResponseFDD,			--	( 24),
	id-unSynchronisedRadioLinkReconfiguration-TDD			RadioLinkReconfigurationResponseTDD,			--	( 24),
	id-commonMeasurementInitiation							CommonMeasurementInitiationResponse,			--	( 27),
	id-informationExchangeInitiation						InformationExchangeInitiationResponse,			--	( 31),
	id-reset												ResetResponse,									--	( 35),
	id-uEMeasurementInitiation								UEMeasurementInitiationResponse,				--	( 40),
	...
}
DummyUnSuccessfulOutcomeValue::= CHOICE {
	id-commonTransportChannelResourcesInitialisation		CommonTransportChannelResourcesFailure,			--	( 0),
	id-dedicatedMeasurementInitiation						DedicatedMeasurementInitiationFailure,			--	( 8),
	id-physicalChannelReconfiguration						PhysicalChannelReconfigurationFailure,			--	( 12),
	id-radioLinkAddition									RadioLinkAdditionFailureFDD,					--	( 14),
	id-radioLinkAddition-TDD								RadioLinkAdditionFailureTDD,					--	( 14),
	id-radioLinkSetup										RadioLinkSetupFailureFDD,						--	( 19),
	id-radioLinkSetupTdd									RadioLinkSetupFailureTDD,						--	( 19),
	id-synchronisedRadioLinkReconfigurationPreparation		RadioLinkReconfigurationFailure,				--	( 23),
	id-unSynchronisedRadioLinkReconfiguration				RadioLinkReconfigurationFailure,				--	( 24),
	id-unSynchronisedRadioLinkReconfiguration-TDD			RadioLinkReconfigurationFailure,				--	( 24),
	id-commonMeasurementInitiation							CommonMeasurementInitiationFailure,				--	( 27),
	id-informationExchangeInitiation						InformationExchangeInitiationFailure,			--	( 31),
	id-uEMeasurementInitiation								UEMeasurementInitiationFailure,					--	( 40),
	...
}

DummyProtocolIE ::= CHOICE {
	id-AllowedQueuingTime												AllowedQueuingTime,					--	( 4),
	id-Allowed-Rate-Information											Allowed-Rate-Information,			--	( 42),
	id-AntennaColocationIndicator										AntennaColocationIndicator,			--	( 309),
	id-BindingID														BindingID,							--	( 5),
	id-C-ID																C-ID,								--	( 6),
	id-C-RNTI															C-RNTI,								--	( 7),
	id-Cell-Capacity-Class-Value										Cell-Capacity-Class-Value,			--	( 303),
	id-CFN																CFN,								--	( 8),
	id-CN-CS-DomainIdentifier											CN-CS-DomainIdentifier,				--	( 9),
	id-CN-PS-DomainIdentifier											CN-PS-DomainIdentifier,				--	( 10),
	id-Cause															Cause,								--	( 11),
	id-CoverageIndicator												CoverageIndicator,					--	( 310),
	id-CriticalityDiagnostics											CriticalityDiagnostics,				--	( 20),
	id-ContextInfoItem-Reset											ContextInfoItem-Reset,				--	( 211),
	id-ContextGroupInfoItem-Reset										ContextGroupInfoItem-Reset,			--	( 515),
	id-D-RNTI															D-RNTI,								--	( 21),
	id-D-RNTI-ReleaseIndication											D-RNTI-ReleaseIndication,			--	( 22),
	id-DCHs-to-Add-FDD													DCH-FDD-Information,					--	( 26),
	id-DCHs-to-Add-TDD													DCH-TDD-Information,					--	( 27),
	id-DCH-DeleteList-RL-ReconfPrepFDD									DCH-DeleteList-RL-ReconfPrepFDD,	--	( 30),
	id-DCH-DeleteList-RL-ReconfPrepTDD									DCH-DeleteList-RL-ReconfPrepTDD,	--	( 31),
	id-DCH-DeleteList-RL-ReconfRqstFDD									DCH-DeleteList-RL-ReconfRqstFDD,	--	( 32),
	id-DCH-DeleteList-RL-ReconfRqstTDD									DCH-DeleteList-RL-ReconfRqstTDD,	--	( 33),
	id-DCH-FDD-Information												DCH-FDD-Information,				--	( 34),
	id-DCH-TDD-Information												DCH-TDD-Information,				--	( 35),
	id-FDD-DCHs-to-Modify												FDD-DCHs-to-Modify,					--	( 39),
	id-TDD-DCHs-to-Modify												TDD-DCHs-to-Modify,					--	( 40),
	id-DCH-InformationResponse											DCH-InformationResponse,			--	( 43),
	id-DCH-Rate-InformationItem-RL-CongestInd							DCH-Rate-InformationItem-RL-CongestInd,				--	( 38),
	id-DL-CCTrCH-InformationAddItem-RL-ReconfPrepTDD					DL-CCTrCH-InformationAddItem-RL-ReconfPrepTDD,		--	( 44),
	id-DL-CCTrCH-InformationListIE-RL-ReconfReadyTDD					DL-CCTrCHInformationListIE-RL-ReconfReadyTDD,		--	( 45),
	id-DL-CCTrCH-InformationDeleteItem-RL-ReconfRqstTDD					DL-CCTrCH-InformationDeleteItem-RL-ReconfRqstTDD,	--	( 46),
	id-DL-CCTrCH-InformationItem-RL-SetupRqstTDD						DL-CCTrCH-InformationItem-RL-SetupRqstTDD,			--	( 47),
	id-DL-CCTrCH-InformationListIE-PhyChReconfRqstTDD					DL-CCTrCH-InformationListIE-PhyChReconfRqstTDD,		--	( 48),
	id-DL-CCTrCH-InformationListIE-RL-AdditionRspTDD					DL-CCTrCHInformationListIE-RL-AdditionRspTDD,		--	( 49),
	id-DL-CCTrCH-InformationListIE-RL-SetupRspTDD						DL-CCTrCH-InformationItem-RL-SetupRqstTDD,			--	( 50),
	id-DL-CCTrCH-InformationAddList-RL-ReconfPrepTDD					DL-CCTrCH-InformationAddList-RL-ReconfPrepTDD,		--	( 51),
	id-DL-CCTrCH-InformationDeleteList-RL-ReconfRqstTDD					DL-CCTrCH-InformationDeleteList-RL-ReconfRqstTDD,	--	( 52),
	id-DL-CCTrCH-InformationList-RL-SetupRqstTDD						DL-CCTrCH-InformationList-RL-SetupRqstTDD,	--	( 53),
	id-FDD-DL-CodeInformation											FDD-DL-CodeInformation,						--	( 54),
	id-DL-DPCH-Information-RL-ReconfPrepFDD								DL-DPCH-Information-RL-ReconfPrepFDD,		--	( 59),
	id-DL-DPCH-Information-RL-SetupRqstFDD								DL-DPCH-Information-RL-SetupRqstFDD,		--	( 60),
	id-DL-DPCH-Information-RL-ReconfRqstFDD								DL-DPCH-Information-RL-ReconfRqstFDD,		--	( 61),
	id-DL-DPCH-InformationItem-PhyChReconfRqstTDD						DL-DPCH-InformationItem-PhyChReconfRqstTDD,	--	( 62),
	id-DL-DPCH-InformationItem-RL-AdditionRspTDD						DL-DPCH-InformationItem-RL-AdditionRspTDD,	--	( 63),
	id-DL-DPCH-InformationItem-RL-SetupRspTDD							DL-DPCH-InformationItem-RL-SetupRspTDD,		--	( 64),
	id-DL-DPCH-TimingAdjustment											DL-DPCH-TimingAdjustment,					--	( 278),
	id-DLReferencePower													DL-Power,									--	( 67),
	id-DLReferencePowerList-DL-PC-Rqst									DL-ReferencePowerInformationList-DL-PC-Rqst,--	( 68),
	id-DL-ReferencePowerInformation-DL-PC-Rqst							DL-ReferencePowerInformation-DL-PC-Rqst,	--	( 69),
	id-DPC-Mode															DPC-Mode,									--	( 12),
	id-DRXCycleLengthCoefficient										DRXCycleLengthCoefficient,					--	( 70),
	id-DedicatedMeasurementObjectType-DM-Fail-Ind						DedicatedMeasurementObjectType-DM-Fail-Ind,	--	( 470),
	id-DedicatedMeasurementObjectType-DM-Fail							DedicatedMeasurementObjectType-DM-Fail,		--	( 471),
	id-DedicatedMeasurementObjectType-DM-Rprt							DedicatedMeasurementObjectType-DM-Rprt,		--	( 71),
	id-DedicatedMeasurementObjectType-DM-Rqst							DedicatedMeasurementObjectType-DM-Rqst,		--	( 72),
	id-DedicatedMeasurementObjectType-DM-Rsp							DedicatedMeasurementObjectType-DM-Rsp,		--	( 73),
	id-DedicatedMeasurementType											DedicatedMeasurementType,					--	( 74),
	id-FACH-InfoForUESelectedS-CCPCH-CTCH-ResourceRspFDD				FACH-InfoForUESelectedS-CCPCH-CTCH-ResourceRspFDD,		--	( 82),
	id-FACH-InfoForUESelectedS-CCPCH-CTCH-ResourceRspTDD				FACH-InfoForUESelectedS-CCPCH-CTCH-ResourceRspTDD,		--	( 83),
	id-Guaranteed-Rate-Information										Guaranteed-Rate-Information,	--	( 41),
	id-IMSI																IMSI,							--	( 84),
	id-HCS-Prio															HCS-Prio,						--	( 311),
	id-L3-Information													L3-Information,					--	( 85),
	id-AdjustmentPeriod													AdjustmentPeriod,				--	( 90),
	id-MaxAdjustmentStep												MaxAdjustmentStep,				--	( 91),
	id-MeasurementFilterCoefficient										MeasurementFilterCoefficient,	--	( 92),
	id-MessageStructure													MessageStructure,				--	( 57),
	id-MeasurementID													MeasurementID,					--	( 93),
	id-Neighbouring-GSM-CellInformation									Neighbouring-GSM-CellInformation,						--	( 13),
	id-Neighbouring-UMTS-CellInformationItem							Neighbouring-UMTS-CellInformationItem,					--	( 95),
	id-NRT-Load-Information-Value										NRT-Load-Information-Value,								--	( 305),
	id-NRT-Load-Information-Value-IncrDecrThres							NRT-Load-Information-Value-IncrDecrThres,				--	( 306),
	id-PagingArea-PagingRqst											PagingArea-PagingRqst,						--	( 102),
	id-FACH-FlowControlInformation										FACH-FlowControlInformation,				--	( 103),
	id-PartialReportingIndicator										PartialReportingIndicator,					--	( 472),
	id-Permanent-NAS-UE-Identity										Permanent-NAS-UE-Identity,					--	( 17),
	id-PowerAdjustmentType												PowerAdjustmentType,						--	( 107),
	id-RANAP-RelocationInformation										RANAP-RelocationInformation,				--	( 109),
	id-RL-Information-PhyChReconfRqstFDD								RL-Information-PhyChReconfRqstFDD,			--	( 110),
	id-RL-Information-PhyChReconfRqstTDD								RL-Information-PhyChReconfRqstTDD,			--	( 111),
	id-RL-Information-RL-AdditionRqstFDD								RL-Information-RL-AdditionRqstFDD,			--	( 112),
	id-RL-Information-RL-AdditionRqstTDD								RL-Information-RL-AdditionRqstTDD,			--	( 113),
	id-RL-Information-RL-DeletionRqst									RL-Information-RL-DeletionRqst,				--	( 114),
	id-RL-Information-RL-FailureInd										RL-Information-RL-FailureInd,				--	( 115),
	id-RL-Information-RL-ReconfPrepFDD									RL-Information-RL-ReconfPrepFDD,			--	( 116),
	id-RL-Information-RL-RestoreInd										RL-Information-RL-RestoreInd,				--	( 117),
	id-RL-Information-RL-SetupRqstFDD									RL-InformationList-RL-SetupRqstFDD,			--	( 118),
	id-RL-Information-RL-SetupRqstTDD									RL-Information-RL-SetupRqstTDD,				--	( 119),
	id-RL-InformationItem-RL-CongestInd									RL-InformationItem-RL-CongestInd,			--	( 55),
	id-RL-InformationItem-DM-Rprt										RL-InformationItem-DM-Rprt,					--	( 120),
	id-RL-InformationItem-DM-Rqst										RL-InformationItem-DM-Rqst,					--	( 121),
	id-RL-InformationItem-DM-Rsp										RL-InformationItem-DM-Rsp,					--	( 122),
	id-RL-InformationItem-RL-PreemptRequiredInd							RL-InformationItem-RL-PreemptRequiredInd,	--	( 2),
	id-RL-InformationItem-RL-SetupRqstFDD								RL-InformationItem-RL-SetupRqstFDD,			--	( 123),
	id-RL-InformationList-RL-CongestInd									RL-InformationList-RL-CongestInd,			--	( 56),
	id-RL-InformationList-RL-AdditionRqstFDD							RL-InformationList-RL-AdditionRqstFDD,		--	( 124),
	id-RL-InformationList-RL-DeletionRqst								RL-InformationList-RL-DeletionRqst,			--	( 125),
	id-RL-InformationList-RL-PreemptRequiredInd							RL-InformationList-RL-PreemptRequiredInd,	--	( 1),
	id-RL-InformationList-RL-ReconfPrepFDD								RL-InformationList-RL-ReconfPrepFDD,		-- ( 126),
	id-RL-InformationResponse-RL-AdditionRspTDD							RL-InformationResponse-RL-AdditionRspTDD,	--	( 127),
	id-RL-InformationResponse-RL-ReconfReadyTDD							RL-InformationResponse-RL-ReconfReadyTDD,	--	( 128),
	id-RL-InformationResponse-RL-SetupRspTDD							RL-InformationResponse-RL-SetupRspTDD,		--	( 129),
	id-RL-InformationResponseItem-RL-AdditionRspFDD						RL-InformationResponseItem-RL-AdditionRspFDD,	--	( 130),
	id-RL-InformationResponseItem-RL-ReconfReadyFDD						RL-InformationResponseItem-RL-ReconfReadyFDD,	--	( 131),
	id-RL-InformationResponseItem-RL-ReconfRspFDD						RL-InformationResponseItem-RL-ReconfRspFDD,		--	( 132),
	id-RL-InformationResponseItem-RL-SetupRspFDD						RL-InformationResponseItem-RL-SetupRspFDD,		--	( 133),
	id-RL-InformationResponseList-RL-AdditionRspFDD						RL-InformationResponseList-RL-AdditionRspFDD,	--	( 134),
	id-RL-InformationResponseList-RL-ReconfReadyFDD						RL-InformationResponseList-RL-ReconfReadyFDD,	--	( 135),
	id-RL-InformationResponseList-RL-ReconfRspFDD						RL-InformationResponseList-RL-ReconfRspFDD,		--	( 136),
	id-RL-InformationResponse-RL-ReconfRspTDD							RL-InformationResponse-RL-ReconfRspTDD,			--	( 28),
	id-RL-InformationResponseList-RL-SetupRspFDD						RL-InformationResponseList-RL-SetupRspFDD,		--	( 137),
	id-RL-ReconfigurationFailure-RL-ReconfFail							RL-ReconfigurationFailure-RL-ReconfFail,		--	( 141),
	id-RL-Set-InformationItem-DM-Rprt									RL-Set-InformationItem-DM-Rprt,					--	( 143),
	id-RL-Set-InformationItem-DM-Rqst									RL-Set-InformationItem-DM-Rqst,					--	( 144),
	id-RL-Set-InformationItem-DM-Rsp									RL-Set-InformationItem-DM-Rsp,					--	( 145),
	id-RL-Set-Information-RL-FailureInd									RL-Set-Information-RL-FailureInd,				--	( 146),
	id-RL-Set-Information-RL-RestoreInd									RL-Set-Information-RL-RestoreInd,				--	( 147),
	id-RL-Set-Successful-InformationItem-DM-Fail						RL-Set-Successful-InformationItem-DM-Fail,		--	( 473),
	id-RL-Set-Unsuccessful-InformationItem-DM-Fail						RL-Set-Unsuccessful-InformationItem-DM-Fail,	--	( 474),
	id-RL-Set-Unsuccessful-InformationItem-DM-Fail-Ind					RL-Set-Unsuccessful-InformationItem-DM-Fail-Ind,--	( 475),
	id-RL-Successful-InformationItem-DM-Fail							RL-Successful-InformationItem-DM-Fail,			--	( 476),
	id-RL-Unsuccessful-InformationItem-DM-Fail							RL-Unsuccessful-InformationItem-DM-Fail,		--	( 477),
	id-RL-Unsuccessful-InformationItem-DM-Fail-Ind						RL-Unsuccessful-InformationItem-DM-Fail-Ind,	--	( 478),
	id-ReportCharacteristics											ReportCharacteristics,							--	( 152),
	id-Reporting-Object-RL-FailureInd									Reporting-Object-RL-FailureInd,					--	( 153),
	id-Reporing-Object-RL-RestoreInd									Reporting-Object-RL-RestoreInd,					--	( 154),
	id-RT-Load-Value													RT-Load-Value,						--	( 307),
	id-RT-Load-Value-IncrDecrThres										RT-Load-Value-IncrDecrThres,		--	( 308),
	id-S-RNTI															S-RNTI,								--	( 155),
	id-ResetIndicator													ResetIndicator,						--	( 244),
	id-RNC-ID															RNC-ID,								--	( 245),
	id-SAI																SAI,								--	( 156),
	id-SRNC-ID															RNC-ID,								--	( 157),
	id-SuccessfulRL-InformationResponse-RL-AdditionFailureFDD			SuccessfulRL-InformationResponse-RL-AdditionFailureFDD,	--	( 159),
	id-SuccessfulRL-InformationResponse-RL-SetupFailureFDD				SuccessfulRL-InformationResponse-RL-SetupFailureFDD,	--	( 160),
	id-TransportBearerID												TransportBearerID,										--	( 163),
	id-TransportBearerRequestIndicator									TransportBearerRequestIndicator,						--	( 164),
	id-TransportLayerAddress											TransportLayerAddress,									--	( 165),
	id-TypeOfError														TypeOfError,											--	( 140),
	id-UC-ID															UC-ID,													--	( 166),
	id-UL-CCTrCH-AddInformation-RL-ReconfPrepTDD						UL-CCTrCH-AddInformation-RL-ReconfPrepTDD,				--	( 167),
	id-UL-CCTrCH-InformationAddList-RL-ReconfPrepTDD					UL-CCTrCH-InformationAddList-RL-ReconfPrepTDD,			--	( 169),
	id-UL-CCTrCH-InformationItem-RL-SetupRqstTDD						UL-CCTrCH-InformationItem-RL-SetupRqstTDD,				--	( 171),
	id-UL-CCTrCH-InformationList-RL-SetupRqstTDD						UL-CCTrCH-InformationList-RL-SetupRqstTDD,				--	( 172),
	id-UL-CCTrCH-InformationListIE-PhyChReconfRqstTDD					UL-CCTrCH-InformationListIE-PhyChReconfRqstTDD,			--	( 173),
	id-UL-CCTrCH-InformationListIE-RL-AdditionRspTDD					UL-CCTrCHInformationListIE-RL-AdditionRspTDD,			--	( 174),
	id-UL-CCTrCH-InformationListIE-RL-ReconfReadyTDD					UL-CCTrCHInformationListIE-RL-ReconfReadyTDD,			--	( 175),
	id-UL-CCTrCH-InformationListIE-RL-SetupRspTDD						UL-CCTrCHInformationListIE-RL-SetupRspTDD,				--	( 176),
	id-UL-DPCH-Information-RL-ReconfPrepFDD								UL-DPCH-Information-RL-ReconfPrepFDD,					--	( 177),
	id-UL-DPCH-Information-RL-ReconfRqstFDD								UL-DPCH-Information-RL-ReconfRqstFDD,					--	( 178),
	id-UL-DPCH-Information-RL-SetupRqstFDD								UL-DPCH-Information-RL-SetupRqstFDD,					--	( 179),
	id-UL-DPCH-InformationItem-PhyChReconfRqstTDD						UL-DPCH-InformationItem-PhyChReconfRqstTDD,				--	( 180),
	id-UL-DPCH-InformationItem-RL-AdditionRspTDD						UL-DPCH-InformationItem-RL-AdditionRspTDD,				--	( 181),
	id-UL-DPCH-InformationItem-RL-SetupRspTDD							UL-DPCH-InformationItem-RL-SetupRspTDD,					--	( 182),
	id-UL-DPCH-InformationAddListIE-RL-ReconfReadyTDD					UL-DPCH-InformationAddListIE-RL-ReconfReadyTDD,			--	( 183),
	id-UL-SIRTarget														UL-SIR,													--	( 184),
	id-URA-Information													URA-Information,										--	( 185),
	id-UnsuccessfulRL-InformationResponse-RL-AdditionFailureFDD			UnsuccessfulRL-InformationResponse-RL-AdditionFailureFDD,	--	( 188),
	id-UnsuccessfulRL-InformationResponse-RL-SetupFailureFDD			UnsuccessfulRL-InformationResponse-RL-SetupFailureFDD,	--	( 189),
	id-UnsuccessfulRL-InformationResponse-RL-SetupFailureTDD			UnsuccessfulRL-InformationResponse-RL-SetupFailureTDD,	--	( 190),
	id-Active-Pattern-Sequence-Information								Active-Pattern-Sequence-Information,					--	( 193),
	id-AdjustmentRatio													ScaledAdjustmentRatio,										--	( 194),
	id-CauseLevel-RL-AdditionFailureFDD									CauseLevel-RL-AdditionFailureFDD,						--	( 197),
	id-CauseLevel-RL-AdditionFailureTDD									CauseLevel-RL-AdditionFailureTDD,						--	( 198),
	id-CauseLevel-RL-ReconfFailure										CauseLevel-RL-ReconfFailure,							--	( 199),
	id-CauseLevel-RL-SetupFailureFDD									CauseLevel-RL-SetupFailureFDD,							--	( 200),
	id-CauseLevel-RL-SetupFailureTDD									CauseLevel-RL-SetupFailureTDD,							--	( 201),
	id-DL-CCTrCH-InformationDeleteItem-RL-ReconfPrepTDD					DL-CCTrCH-InformationDeleteItem-RL-ReconfPrepTDD,		--	( 205),
	id-DL-CCTrCH-InformationModifyItem-RL-ReconfPrepTDD					DL-CCTrCH-InformationModifyItem-RL-ReconfPrepTDD,		--	( 206),
	id-DL-CCTrCH-InformationModifyItem-RL-ReconfRqstTDD					DL-CCTrCH-InformationModifyItem-RL-ReconfRqstTDD,		--	( 207),
	id-DL-CCTrCH-InformationDeleteList-RL-ReconfPrepTDD					DL-CCTrCH-InformationDeleteList-RL-ReconfPrepTDD,		--	( 208),
	id-DL-CCTrCH-InformationModifyList-RL-ReconfPrepTDD					DL-CCTrCH-InformationModifyList-RL-ReconfPrepTDD,		--	( 209),
	id-DL-CCTrCH-InformationModifyList-RL-ReconfRqstTDD					DL-CCTrCH-InformationModifyList-RL-ReconfRqstTDD,		--	( 210),
	id-DL-DPCH-InformationAddListIE-RL-ReconfReadyTDD					DL-DPCH-InformationAddListIE-RL-ReconfReadyTDD,			--	( 212),
	id-DL-DPCH-InformationDeleteListIE-RL-ReconfReadyTDD				DL-DPCH-InformationDeleteListIE-RL-ReconfReadyTDD,		--	( 213),
	id-DL-DPCH-InformationModifyListIE-RL-ReconfReadyTDD				DL-DPCH-InformationModifyListIE-RL-ReconfReadyTDD,		--	( 214),
	id-DSCHs-to-Add-TDD													DSCH-TDD-Information,									--	( 215),
--	id-Unused-ProtocolIE-ID-216													( 216),
	id-DSCH-DeleteList-RL-ReconfPrepTDD									DSCH-DeleteList-RL-ReconfPrepTDD,						--	( 217),
--	id-Unused-ProtocolIE-ID-218													( 218),
--	id-Unused-ProtocolIE-ID-219													( 219),
	id-DSCH-InformationListIE-RL-AdditionRspTDD							DSCH-InformationListIE-RL-AdditionRspTDD,				--	( 220),
	id-DSCH-InformationListIEs-RL-SetupRspTDD							DSCH-InformationListIEs-RL-SetupRspTDD,					--	( 221),
	id-DSCH-TDD-Information												DSCH-TDD-Information,									--	( 222),
--	id-Unused-ProtocolIE-ID-223													( 223),
--	id-Unused-ProtocolIE-ID-226													( 226),
	id-DSCH-ModifyList-RL-ReconfPrepTDD									DSCH-ModifyList-RL-ReconfPrepTDD,						--	( 227),
--	id-Unused-ProtocolIE-ID-228													( 228),
--	id-Unused-ProtocolIE-ID-324													( 324),
--	id-Unused-ProtocolIE-ID-229													( 229),
	id-DSCHToBeAddedOrModifiedList-RL-ReconfReadyTDD					DSCHToBeAddedOrModifiedList-RL-ReconfReadyTDD,			--	( 230),
--	id-Unused-ProtocolIE-ID-29													( 29),
--	id-Unused-ProtocolIE-ID-225													( 225),
	id-GA-Cell															GA-Cell,												--	( 232),
	id-GA-CellAdditionalShapes											GA-CellAdditionalShapes,								--	( 3),
--	id-Unused-ProtocolIE-ID-246													( 246),
	id-Transmission-Gap-Pattern-Sequence-Information					Transmission-Gap-Pattern-Sequence-Information,			--	( 255),
	id-UL-CCTrCH-DeleteInformation-RL-ReconfPrepTDD						UL-CCTrCH-DeleteInformation-RL-ReconfPrepTDD,			--	( 256),
	id-UL-CCTrCH-ModifyInformation-RL-ReconfPrepTDD						UL-CCTrCH-ModifyInformation-RL-ReconfPrepTDD,			--	( 257),
	id-UL-CCTrCH-InformationModifyItem-RL-ReconfRqstTDD					UL-CCTrCH-InformationModifyItem-RL-ReconfRqstTDD,		--	( 258),
	id-UL-CCTrCH-InformationDeleteList-RL-ReconfPrepTDD					UL-CCTrCH-InformationDeleteList-RL-ReconfPrepTDD,		--	( 259),
	id-UL-CCTrCH-InformationModifyList-RL-ReconfPrepTDD					UL-CCTrCH-InformationModifyList-RL-ReconfPrepTDD,		--	( 260),
	id-UL-CCTrCH-InformationModifyList-RL-ReconfRqstTDD					UL-CCTrCH-InformationModifyList-RL-ReconfRqstTDD,		--	( 261),
	id-UL-CCTrCH-InformationDeleteItem-RL-ReconfRqstTDD					UL-CCTrCH-InformationDeleteItem-RL-ReconfRqstTDD,		--	( 262),
	id-UL-CCTrCH-InformationDeleteList-RL-ReconfRqstTDD					UL-CCTrCH-InformationDeleteList-RL-ReconfRqstTDD,		--	( 263),
	id-UL-DPCH-InformationDeleteListIE-RL-ReconfReadyTDD				UL-DPCH-InformationDeleteListIE-RL-ReconfReadyTDD,		--	( 264),
	id-UL-DPCH-InformationModifyListIE-RL-ReconfReadyTDD				UL-DPCH-InformationModifyListIE-RL-ReconfReadyTDD,		--	( 265),
	id-UnsuccessfulRL-InformationResponse-RL-AdditionFailureTDD			UnsuccessfulRL-InformationResponse-RL-AdditionFailureTDD,	--	( 266),
	id-USCHs-to-Add														USCH-Information,										--	( 267),
	id-USCH-DeleteList-RL-ReconfPrepTDD									USCH-DeleteList-RL-ReconfPrepTDD,						--	( 268),
	id-USCH-InformationListIE-RL-AdditionRspTDD							USCH-InformationListIE-RL-AdditionRspTDD,				--	( 269),
	id-USCH-InformationListIEs-RL-SetupRspTDD							USCH-InformationListIEs-RL-SetupRspTDD,					--	( 270),
	id-USCH-Information													USCH-Information,										--	( 271),
	id-USCH-ModifyList-RL-ReconfPrepTDD									USCH-ModifyList-RL-ReconfPrepTDD,						--	( 272),
	id-USCHToBeAddedOrModifiedList-RL-ReconfReadyTDD					USCHToBeAddedOrModifiedList-RL-ReconfReadyTDD,			--	( 273),
	id-DL-Physical-Channel-Information-RL-SetupRqstTDD					DL-Physical-Channel-Information-RL-SetupRqstTDD,		--	( 274),
	id-UL-Physical-Channel-Information-RL-SetupRqstTDD					UL-Physical-Channel-Information-RL-SetupRqstTDD,		--	( 275),
	id-ClosedLoopMode1-SupportIndicator									ClosedLoopMode1-SupportIndicator,						--	( 276),
--	id-Unused-ProtocolIE-ID-277													( 277),
	id-STTD-SupportIndicator											STTD-SupportIndicator,									--	( 279),
	id-CFNReportingIndicator             								FNReportingIndicator,									--	( 14),
	id-CNOriginatedPage-PagingRqst										CNOriginatedPage-PagingRqst,							--	( 23),
	id-InnerLoopDLPCStatus												InnerLoopDLPCStatus,									--	( 24),
	id-PropagationDelay													PropagationDelay,										--	( 25),
	id-RxTimingDeviationForTA											RxTimingDeviationForTA,									--	( 36),
	id-timeSlot-ISCP													DL-TimeSlot-ISCP-Info,									--	( 37),
	id-CCTrCH-InformationItem-RL-FailureInd								CCTrCH-InformationItem-RL-FailureInd,					--	( 15),
	id-CCTrCH-InformationItem-RL-RestoreInd								CCTrCH-InformationItem-RL-RestoreInd,					--	( 16),
	id-CommonMeasurementAccuracy										CommonMeasurementAccuracy,								--	( 280),
	id-CommonMeasurementObjectType-CM-Rprt								CommonMeasurementObjectType-CM-Rprt,					--	( 281),
	id-CommonMeasurementObjectType-CM-Rqst								CommonMeasurementObjectType-CM-Rqst,					--	( 282),
	id-CommonMeasurementObjectType-CM-Rsp								CommonMeasurementObjectType-CM-Rsp,						--	( 283),
	id-CommonMeasurementType											CommonMeasurementType,									--	( 284),
	id-CongestionCause 													CongestionCause,										--	( 18),
	id-SFN																SFN,													--	( 285),
	id-SFNReportingIndicator											FNReportingIndicator,									--	( 286),
	id-InformationExchangeID											InformationExchangeID,									--	( 287),
	id-InformationExchangeObjectType-InfEx-Rprt							InformationExchangeObjectType-InfEx-Rprt,				--	( 288),
	id-InformationExchangeObjectType-InfEx-Rqst							InformationExchangeObjectType-InfEx-Rqst,				--	( 289),
	id-InformationExchangeObjectType-InfEx-Rsp							InformationReportCharacteristics,						--	( 290),
	id-InformationReportCharacteristics									InformationReportCharacteristics,						--	( 291),
	id-InformationType													InformationType,										--	( 292),
	id-neighbouring-LCR-TDD-CellInformation								Neighbouring-LCR-TDD-CellInformation,					--	( 58),
	id-DL-Timeslot-ISCP-LCR-Information-RL-SetupRqstTDD					DL-TimeSlot-ISCP-LCR-Information,						--	( 65),
	id-RL-LCR-InformationResponse-RL-SetupRspTDD						RL-LCR-InformationResponse-RL-SetupRspTDD,				--	( 66),
	id-UL-CCTrCH-LCR-InformationListIE-RL-SetupRspTDD					UL-LCR-CCTrCHInformationListIE-RL-SetupRspTDD,			--	( 75),
	id-UL-DPCH-LCR-InformationItem-RL-SetupRspTDD						UL-DPCH-LCR-InformationItem-RL-SetupRspTDD,				--	( 76),
	id-DL-CCTrCH-LCR-InformationListIE-RL-SetupRspTDD					DL-CCTrCH-LCR-InformationListIE-RL-SetupRspTDD,			--	( 77),
	id-DL-DPCH-LCR-InformationItem-RL-SetupRspTDD						DL-DPCH-LCR-InformationItem-RL-SetupRspTDD,				--	( 78),
	id-DSCH-LCR-InformationListIEs-RL-SetupRspTDD						DSCH-LCR-InformationListIEs-RL-SetupRspTDD,				--	( 79),
	id-USCH-LCR-InformationListIEs-RL-SetupRspTDD						USCH-LCR-InformationListIEs-RL-SetupRspTDD,				--	( 80),
	id-DL-Timeslot-ISCP-LCR-Information-RL-AdditionRqstTDD				DL-TimeSlot-ISCP-LCR-Information,						--	( 81),
	id-RL-LCR-InformationResponse-RL-AdditionRspTDD						RL-LCR-InformationResponse-RL-AdditionRspTDD,			--	( 86),
	id-UL-CCTrCH-LCR-InformationListIE-RL-AdditionRspTDD				UL-CCTrCH-LCR-InformationListIE-RL-AdditionRspTDD,		--	( 87),
	id-UL-DPCH-LCR-InformationItem-RL-AdditionRspTDD					UL-DPCH-LCR-InformationItem-RL-AdditionRspTDD,			--	( 88),
	id-DL-CCTrCH-LCR-InformationListIE-RL-AdditionRspTDD				DL-CCTrCH-LCR-InformationListIE-RL-AdditionRspTDD,		--	( 89),
	id-DL-DPCH-LCR-InformationItem-RL-AdditionRspTDD					DL-DPCH-LCR-InformationItem-RL-AdditionRspTDD,			--	( 94),
	id-DSCH-LCR-InformationListIEs-RL-AdditionRspTDD					DSCH-LCR-InformationListIEs-RL-AdditionRspTDD,			--	( 96),
	id-USCH-LCR-InformationListIEs-RL-AdditionRspTDD					USCH-LCR-InformationListIEs-RL-AdditionRspTDD,			--	( 97),
	id-UL-DPCH-LCR-InformationAddListIE-RL-ReconfReadyTDD				UL-DPCH-LCR-InformationAddList-RL-ReconfReadyTDD,		--	( 98),
	id-UL-Timeslot-LCR-InformationModifyList-RL-ReconfReadyTDD			UL-TimeslotLCR-InformationModifyList-RL-ReconfReadyTDD,	--	( 100),
	id-DL-DPCH-LCR-InformationAddListIE-RL-ReconfReadyTDD				DL-DPCH-LCR-InformationAddList-RL-ReconfReadyTDD,		--	( 101),
	id-DL-Timeslot-LCR-InformationModifyList-RL-ReconfReadyTDD			DL-TimeslotLCR-InformationModifyList-RL-ReconfReadyTDD,	--	( 104),
	id-UL-Timeslot-LCR-InformationList-PhyChReconfRqstTDD				UL-TimeslotLCR-InformationList-PhyChReconfRqstTDD,		--	( 105),
	id-DL-Timeslot-LCR-InformationList-PhyChReconfRqstTDD				DL-TimeslotLCR-InformationList-PhyChReconfRqstTDD,		--	( 106),
	id-timeSlot-ISCP-LCR-List-DL-PC-Rqst-TDD							DL-TimeSlot-ISCP-LCR-Information,						--	( 138),
	id-TSTD-Support-Indicator-RL-SetupRqstTDD							TSTD-Support-Indicator,									--	( 139),
	id-RestrictionStateIndicator										RestrictionStateIndicator,								--	( 142),
	id-Load-Value														Load-Value,												--	( 233),
	id-Load-Value-IncrDecrThres											Load-Value-IncrDecrThres,								--	( 234),
	id-OnModification													OnModification,											--	( 235),
	id-Received-Total-Wideband-Power-Value								Received-Total-Wideband-Power-Value,					--	( 236),
	id-Received-Total-Wideband-Power-Value-IncrDecrThres				SFNSFNMeasurementThresholdInformation,					--	( 237),
	id-SFNSFNMeasurementThresholdInformation							SFNSFNMeasurementThresholdInformation,					--	( 238),
	id-Transmitted-Carrier-Power-Value									Transmitted-Carrier-Power-Value,						--	( 239),
	id-Transmitted-Carrier-Power-Value-IncrDecrThres					Transmitted-Carrier-Power-Value-IncrDecrThres,			--	( 240),
	id-TUTRANGPSMeasurementThresholdInformation							UL-Timeslot-ISCP-Value,									--	( 241),
	id-UL-Timeslot-ISCP-Value											UL-Timeslot-ISCP-Value,									--	( 242),
	id-UL-Timeslot-ISCP-Value-IncrDecrThres								UL-Timeslot-ISCP-Value-IncrDecrThres,					--	( 243),
	id-Rx-Timing-Deviation-Value-LCR									Rx-Timing-Deviation-Value-LCR,							--	( 293),
	id-DPC-Mode-Change-SupportIndicator									DPC-Mode-Change-SupportIndicator,						--	( 19),
--	id-Unused-ProtocolIE-ID-247													( 247),
--	id-Unused-ProtocolIE-ID-295													( 295),
	id-PrimaryCCPCH-RSCP-RL-ReconfPrepTDD								PrimaryCCPCH-RSCP,										--	( 202),
	id-DL-TimeSlot-ISCP-Info-RL-ReconfPrepTDD							DL-TimeSlot-ISCP-Info,									--	( 203),
	id-DL-Timeslot-ISCP-LCR-Information-RL-ReconfPrepTDD				DL-TimeSlot-ISCP-LCR-Information,						--	( 204),
	id-DSCH-RNTI														DSCH-RNTI,												--	( 249),
	id-DL-PowerBalancing-Information									DL-PowerBalancing-Information,							--	( 296),
	id-DL-PowerBalancing-ActivationIndicator							DL-PowerBalancing-ActivationIndicator,					--	( 297),
	id-DL-PowerBalancing-UpdatedIndicator								DL-PowerBalancing-UpdatedIndicator,						--	( 298),
	id-DL-ReferencePowerInformation										DL-ReferencePowerInformation,							--	( 299),
	id-Enhanced-PrimaryCPICH-EcNo										Enhanced-PrimaryCPICH-EcNo,								--	( 224),
	id-IPDL-TDD-ParametersLCR											IPDL-TDD-ParametersLCR,									--	( 252),
	id-CellCapabilityContainer-FDD										CellCapabilityContainer-FDD,							--	( 300),
	id-CellCapabilityContainer-TDD										CellCapabilityContainer-TDD,							--	( 301),
	id-CellCapabilityContainer-TDD-LCR									CellCapabilityContainer-TDD-LCR,						--	( 302),
	id-RL-Specific-DCH-Info												RL-Specific-DCH-Info,									--	( 317),
	id-RL-ReconfigurationRequestFDD-RL-InformationList 					RL-ReconfigurationRequestFDD-RL-InformationList,		--	( 318),
	id-RL-ReconfigurationRequestFDD-RL-Information-IEs					RL-ReconfigurationRequestFDD-RL-Information-IEs,		--	( 319),
	id-RL-ReconfigurationRequestTDD-RL-Information						RL-ReconfigurationRequestTDD-RL-Information,			--	( 321),
	id-CommonTransportChannelResourcesInitialisationNotRequired			CommonTransportChannelResourcesInitialisationNotRequired,	--	( 250),
	id-DelayedActivation 												DelayedActivation,										--	( 312),
	id-DelayedActivationList-RL-ActivationCmdFDD						DelayedActivationInformationList-RL-ActivationCmdFDD,	--	( 313),
	id-DelayedActivationInformation-RL-ActivationCmdFDD					DelayedActivationInformation-RL-ActivationCmdFDD,		--	( 314),
	id-DelayedActivationList-RL-ActivationCmdTDD						DelayedActivationInformationList-RL-ActivationCmdTDD,	--	( 315),
	id-DelayedActivationInformation-RL-ActivationCmdTDD					DelayedActivationInformation-RL-ActivationCmdTDD,		--	( 316),
	id-neighbouringTDDCellMeasurementInformationLCR						NeighbouringTDDCellMeasurementInformationLCR,			--	( 251),
	id-UL-SIR-Target-CCTrCH-InformationItem-RL-SetupRspTDD				UL-SIR,													--	( 150),
	id-UL-SIR-Target-CCTrCH-LCR-InformationItem-RL-SetupRspTDD			UL-SIR,													--	( 151),
	id-PrimCCPCH-RSCP-DL-PC-RqstTDD										PrimaryCCPCH-RSCP,										--	( 451),
	id-HSDSCH-FDD-Information											HSDSCH-FDD-Information,									--	( 452),
	id-HSDSCH-FDD-Information-Response									HSDSCH-FDD-Information-Response,						--	( 453),
	id-HSDSCH-FDD-Update-Information									HSDSCH-FDD-Update-Information,							--	( 466),
	id-HSDSCH-Information-to-Modify										HSDSCH-Information-to-Modify,							--	( 456),
	id-HSDSCHMacdFlowSpecificInformationList-RL-PreemptRequiredInd		HSDSCHMacdFlowSpecificInformationList-RL-PreemptRequiredInd,	--	( 516),
	id-HSDSCHMacdFlowSpecificInformationItem-RL-PreemptRequiredInd		HSDSCHMacdFlowSpecificInformationItem-RL-PreemptRequiredInd,	--	( 517),
	id-HSDSCH-RNTI														HSDSCH-RNTI,											--	( 457),
	id-HSDSCH-TDD-Information											HSDSCH-TDD-Information,									--	( 458),
	id-HSDSCH-TDD-Information-Response									HSDSCH-TDD-Information-Response,						--	( 459),
	id-HSDSCH-TDD-Update-Information									HSDSCH-TDD-Update-Information,							--	( 467),
	id-HSPDSCH-RL-ID													RL-ID,													--	( 463),
	id-HSDSCH-MACdFlows-to-Add 											HSDSCH-MACdFlows-Information,							--	( 531),
	id-HSDSCH-MACdFlows-to-Delete										HSDSCH-MACdFlows-to-Delete,								--	( 532),
	id-Angle-Of-Arrival-Value-LCR										Angle-Of-Arrival-Value-LCR,								--	( 148),
	id-TrafficClass														TrafficClass,											--	( 158),
--	id-Unused-ProtocolIE-ID-248													( 248),
--	id-Unused-ProtocolIE-ID-253													( 253),
	id-PDSCH-RL-ID														RL-ID,													--	( 323),
	id-TimeSlot-RL-SetupRspTDD											TimeSlot,												--	( 325),
	id-GERAN-Cell-Capability											GERAN-Cell-Capability,									--	( 468),
	id-GERAN-Classmark													GERAN-Classmark,										--	( 469),
	id-DSCH-InitialWindowSize											DSCH-InitialWindowSize,									--	( 480),
	id-UL-Synchronisation-Parameters-LCR								UL-Synchronisation-Parameters-LCR,						--	( 464),
	id-SNA-Information													SNA-Information,										--	( 479),
	id-MAChs-ResetIndicator												MAChs-ResetIndicator,									--	( 465),
	id-TDD-DL-DPCH-TimeSlotFormatModifyItem-LCR-RL-ReconfReadyTDD		TDD-DL-DPCH-TimeSlotFormat-LCR,							--	( 481),
	id-TDD-UL-DPCH-TimeSlotFormatModifyItem-LCR-RL-ReconfReadyTDD		TDD-UL-DPCH-TimeSlotFormat-LCR,								--	( 482),
	id-TDD-TPC-UplinkStepSize-LCR-RL-SetupRqstTDD						TDD-TPC-UplinkStepSize-LCR,									--	( 483),
	id-UL-CCTrCH-InformationList-RL-AdditionRqstTDD						UL-CCTrCH-InformationList-RL-AdditionRqstTDD,				--	( 484),
	id-UL-CCTrCH-InformationItem-RL-AdditionRqstTDD						UL-CCTrCH-InformationItem-RL-AdditionRqstTDD,				--	( 485),
	id-DL-CCTrCH-InformationList-RL-AdditionRqstTDD						DL-CCTrCH-InformationList-RL-AdditionRqstTDD,				--	( 486),
	id-DL-CCTrCH-InformationItem-RL-AdditionRqstTDD						DL-CCTrCH-InformationItem-RL-AdditionRqstTDD,				--	( 487),
	id-TDD-TPC-UplinkStepSize-InformationAdd-LCR-RL-ReconfPrepTDD		TDD-TPC-UplinkStepSize-LCR,									--	( 488),
	id-TDD-TPC-UplinkStepSize-InformationModify-LCR-RL-ReconfPrepTDD	TDD-TPC-UplinkStepSize-LCR,									--	( 489),
	id-TDD-TPC-DownlinkStepSize-InformationAdd-RL-ReconfPrepTDD			TDD-TPC-DownlinkStepSize,									--	( 490),
	id-TDD-TPC-DownlinkStepSize-InformationModify-RL-ReconfPrepTDD		TDD-TPC-DownlinkStepSize,									--	( 491),
	id-UL-TimingAdvanceCtrl-LCR											UL-TimingAdvanceCtrl-LCR,									--	( 492),
	id-HSPDSCH-Timeslot-InformationList-PhyChReconfRqstTDD				HSPDSCH-Timeslot-InformationList-PhyChReconfRqstTDD,		--	( 493),
	id-HSPDSCH-Timeslot-InformationListLCR-PhyChReconfRqstTDD			HSPDSCH-Timeslot-InformationListLCR-PhyChReconfRqstTDD,		--	( 494),
	id-HS-SICH-Reception-Quality 										HS-SICH-Reception-Quality-Value,							--	( 495),
	id-HS-SICH-Reception-Quality-Measurement-Value 						HS-SICH-Reception-Quality-Measurement-Value,				--	( 496),
	id-HSSICH-Info-DM-Rprt												HS-SICH-ID,													--	( 497),
	id-HSSICH-Info-DM-Rqst												HSSICH-Info-DM-Rqst,										--	( 498),
	id-HSSICH-Info-DM													HS-SICH-ID,													--	( 499),
	id-CCTrCH-Maximum-DL-Power-RL-SetupRspTDD							DL-Power,													--	( 500),
	id-CCTrCH-Minimum-DL-Power-RL-SetupRspTDD							DL-Power,													--	( 501),
	id-CCTrCH-Maximum-DL-Power-RL-AdditionRspTDD						DL-Power,													--	( 502),
	id-CCTrCH-Minimum-DL-Power-RL-AdditionRspTDD						DL-Power,													--	( 503),
	id-CCTrCH-Maximum-DL-Power-RL-ReconfReadyTDD						DL-Power,													--	( 504),
	id-CCTrCH-Minimum-DL-Power-RL-ReconfReadyTDD						DL-Power,													--	( 505),
	id-Maximum-DL-Power-TimeslotLCR-InformationModifyItem-RL-ReconfReadyTDD		DL-Power,											--	( 506),
	id-Minimum-DL-Power-TimeslotLCR-InformationModifyItem-RL-ReconfReadyTDD		DL-Power,											--	( 507),
	id-DL-CCTrCH-InformationList-RL-ReconfRspTDD						DL-CCTrCH-InformationList-RL-ReconfRspTDD,					--	( 508),
	id-DL-DPCH-InformationModifyItem-LCR-RL-ReconfRspTDD				DL-DPCH-InformationModifyItem-LCR-RL-ReconfRspTDD,			--	( 509),
	id-Maximum-DL-Power-TimeslotLCR-InformationItem						DL-Power,													--	( 510),
	id-Minimum-DL-Power-TimeslotLCR-InformationItem						DL-Power,													--	( 511),
	id-TDD-Support-8PSK													Support-8PSK,												--	( 512),
	id-TDD-maxNrDLPhysicalchannels										MaxNrDLPhysicalchannelsTS,									--	( 513),
	id-ExtendedGSMCellIndividualOffset									ExtendedGSMCellIndividualOffset,							--	( 514),
	id-RL-ParameterUpdateIndicationFDD-RL-InformationList 				RL-ParameterUpdateIndicationFDD-RL-InformationList,			--	( 518),
	id-Primary-CPICH-Usage-For-Channel-Estimation						Primary-CPICH-Usage-For-Channel-Estimation,					--	( 519),
	id-Secondary-CPICH-Information										Secondary-CPICH-Information,								--	( 520),
	id-Secondary-CPICH-Information-Change								Secondary-CPICH-Information-Change,							--	( 521),
--	id-Unused-ProtocolIE-ID-522													( 522),
--	id-Unused-ProtocolIE-ID-523													( 523),
	id-RL-ParameterUpdateIndicationFDD-RL-Information-Item				RL-ParameterUpdateIndicationFDD-RL-Information-Item,		--	( 524),
	id-Phase-Reference-Update-Indicator									Phase-Reference-Update-Indicator,							--	( 525),
	id-Unidirectional-DCH-Indicator										Unidirectional-DCH-Indicator,								--	( 526),
	id-RL-Information-RL-ReconfPrepTDD									RL-Information-RL-ReconfPrepTDD,							--	( 527),
	id-Multiple-RL-InformationResponse-RL-ReconfReadyTDD				Multiple-RL-InformationResponse-RL-ReconfReadyTDD,			--	( 528),
	id-RL-ReconfigurationResponseTDD-RL-Information						Multiple-RL-InformationResponse-RL-ReconfRspTDD,			--	( 529),
	id-Satellite-Almanac-Information-ExtItem							Satellite-Almanac-Information-ExtItem,						--	( 530),
	id-HSDSCH-Information-to-Modify-Unsynchronised						HSDSCH-Information-to-Modify-Unsynchronised,				--	( 533),
	id-TnlQos															TnlQos,														--	( 534),
	id-RTLoadValue														RTLoadValue,												--	( 535),
	id-NRTLoadInformationValue											NRTLoadInformationValue,									--	( 536),
	id-CellPortionID													CellPortionID,												--	( 537),
	id-UpPTSInterferenceValue											UpPTSInterferenceValue,										--	( 538),
	id-PrimaryCCPCH-RSCP-Delta											PrimaryCCPCH-RSCP-Delta,									--	( 539),
	id-UEMeasurementType													UEMeasurementType,											--	( 540),
	id-UEMeasurementTimeslotInfoHCR											UEMeasurementTimeslotInfoHCR,								--	( 541),
	id-UEMeasurementTimeslotInfoLCR											UEMeasurementTimeslotInfoLCR,								--	( 542),
	id-UEMeasurementReportCharacteristics									UEMeasurementReportCharacteristics,							--	( 543),
	id-UEMeasurementParameterModAllow										UEMeasurementParameterModAllow,								--	( 544),
	id-UEMeasurementValueInformation										UEMeasurementValueInformation,								--	( 545),
	id-InterfacesToTraceItem												InterfacesToTraceItem,										--	( 546),
	id-ListOfInterfacesToTrace												ListOfInterfacesToTrace,									--	( 547),
	id-TraceDepth															TraceDepth,													--	( 548),
	id-TraceRecordingSessionReference										TraceRecordingSessionReference,								--	( 549),
	id-TraceReference														TraceReference,												--	( 550),
	id-UEIdentity															UEIdentity,													--	( 551),
	id-NACC-Related-Data													NACC-Related-Data,											--	( 552),
	id-GSM-Cell-InfEx-Rqst													GSM-Cell-InfEx-Rqst,										--	( 553),
	id-MeasurementRecoveryBehavior											MeasurementRecoveryBehavior,								--	( 554),
	id-MeasurementRecoveryReportingIndicator								MeasurementRecoveryReportingIndicator,						--	( 555),
	id-MeasurementRecoverySupportIndicator									MeasurementRecoverySupportIndicator	,						--	( 556),
	id-DL-DPCH-Power-Information-RL-ReconfPrepFDD							DL-DPCH-Power-Information-RL-ReconfPrepFDD,					--	( 557),
	id-F-DPCH-Information-RL-ReconfPrepFDD									F-DPCH-Information-RL-ReconfPrepFDD,						--	( 558),
	id-F-DPCH-Information-RL-SetupRqstFDD									F-DPCH-Information-RL-SetupRqstFDD,							--	( 559),
	id-MBMS-Bearer-Service-List												MBMS-Bearer-Service-List,									--	( 560),
	id-MBMS-Bearer-Service-List-InfEx-Rsp									MBMS-Bearer-Service-List-InfEx-Rsp,							--	( 561),
	id-Active-MBMS-Bearer-ServiceFDD										Active-MBMS-Bearer-Service-ListFDD,								--	( 562),
	id-Active-MBMS-Bearer-ServiceTDD										Active-MBMS-Bearer-Service-ListTDD,								--	( 563),
	id-Old-URA-ID															URA-ID,				--	( 564),
	id-UE-State																UE-State,			--	( 568),
	id-URA-ID																URA-ID,				--	( 569),
	id-HARQ-Preamble-Mode													HARQ-Preamble-Mode,	--	( 571),
	id-SynchronisationIndicator												SynchronisationIndicator,									--	( 572),
	id-UL-DPDCHIndicatorEDCH												UL-DPDCHIndicatorEDCH,										--	( 573),
	id-EDPCH-Information													EDPCH-Information-FDD,										--	( 574),
	id-RL-Specific-EDCH-Information											RL-Specific-EDCH-Information,								--	( 575),
	id-EDCH-RL-Indication													EDCH-RL-Indication,											--	( 576),
	id-EDCH-FDD-Information													EDCH-FDD-Information,										--	( 577),
	id-EDCH-RLSet-Id														RL-Set-ID,													--	( 578),
	id-Serving-EDCHRL-Id													EDCH-Serving-RL,											--	( 579),
	id-EDCH-FDD-DL-ControlChannelInformation								EDCH-FDD-DL-ControlChannelInformation,						--	( 580),
	id-EDCH-FDD-InformationResponse											EDCH-FDD-InformationResponse,								--	( 581),
	id-EDCH-MACdFlows-To-Add												RL-Specific-EDCH-Information,								--	( 582),
	id-EDCH-FDD-Information-To-Modify										EDCH-FDD-Information-To-Modify,								--	( 583),
	id-EDCH-MACdFlows-To-Delete												EDCH-MACdFlows-To-Delete,									--	( 584),
	id-EDPCH-Information-RLReconfRequest-FDD								EDPCH-Information-RLReconfRequest-FDD,						--	( 585),
	id-EDCH-MacdFlowSpecificInformationList-RL-PreemptRequiredInd			EDCH-MacdFlowSpecificInformationList-RL-PreemptRequiredInd,	--	( 586),
	id-EDCH-MacdFlowSpecificInformationItem-RL-PreemptRequiredInd			EDCH-MacdFlowSpecificInformationItem-RL-PreemptRequiredInd,	--	( 587),
	id-EDCH-MacdFlowSpecificInformationList-RL-CongestInd  					EDCH-MacdFlowSpecificInformationList-RL-CongestInd,			--	( 588),
	id-EDCH-MacdFlowSpecificInformationItem-RL-CongestInd					EDCH-MacdFlowSpecificInformationItem-RL-CongestInd,			--	( 589),
	id-MBMS-Bearer-Service-Full-Address										MBMS-Bearer-Service-Full-Address,							--	( 590),
	id-Initial-DL-DPCH-TimingAdjustment										DL-DPCH-TimingAdjustment,									--	( 591),
	id-Initial-DL-DPCH-TimingAdjustment-Allowed								Initial-DL-DPCH-TimingAdjustment-Allowed,					--	( 592),
	id-User-Plane-Congestion-Fields-Inclusion								User-Plane-Congestion-Fields-Inclusion,						--	( 593),
	id-HARQ-Preamble-Mode-Activation-Indicator								HARQ-Preamble-Mode-Activation-Indicator,					--	( 594),
	id-multiple-DedicatedMeasurementValueList-TDD-DM-Rsp					Multiple-DedicatedMeasurementValueList-TDD-DM-Rsp,			--	( 595),
	id-multiple-DedicatedMeasurementValueList-LCR-TDD-DM-Rsp				Multiple-DedicatedMeasurementValueList-LCR-TDD-DM-Rsp,		--	( 596),
	id-ProvidedInformation													ProvidedInformation,										--	( 597),
	id-Active-MBMS-Bearer-ServiceFDD-PFL									Active-MBMS-Bearer-Service-ListTDD-PFL,						--	( 598),
	id-Active-MBMS-Bearer-ServiceTDD-PFL									Active-MBMS-Bearer-Service-ListTDD-PFL,						--	( 599),
	id-FrequencyBandIndicator												FrequencyBandIndicator,										--	( 600),
...
}
--END

--9.3.3	PDU Definitions
-- **************************************************************
--
-- PDU definitions for RNSAP.
--
-- **************************************************************

--RNSAP-PDU-Contents {
--itu-t (0) identified-organization (4) etsi (0) mobileDomain (0) 
--umts-Access (20) modules (3) rnsap (1) version1 (1) rnsap-PDU-Contents (1) }

--DEFINITIONS AUTOMATIC TAGS ::= 

--BEGIN

-- **************************************************************
--
-- IE parameter types from other modules.
--
-- **************************************************************
-- :
-- :
-- **************************************************************
--
-- RADIO LINK SETUP REQUEST FDD
--
-- **************************************************************
--RadioLinkSetupRequestFDD ::= SEQUENCE {
--	protocolIEs                     ProtocolIE-Container       {{RadioLinkSetupRequestFDD-IEs}},
--	protocolExtensions              ProtocolExtensionContainer {{RadioLinkSetupRequestFDD-Extensions}}                   OPTIONAL,
--	...
--}
RadioLinkSetupRequestFDD ::= SEQUENCE {
	protocolIEs                     ProtocolIE-Container,
	protocolExtensions              ProtocolExtensionContainer OPTIONAL,
	...
}
--RadioLinkSetupRequestFDD-IEs RNSAP-PROTOCOL-IES ::= {
--	{ ID id-SRNC-ID					CRITICALITY reject	TYPE RNC-ID						PRESENCE mandatory} |
--	{ ID id-S-RNTI					CRITICALITY reject	TYPE S-RNTI 					PRESENCE mandatory	} |
--	{ ID id-D-RNTI					CRITICALITY reject	TYPE D-RNTI					PRESENCE optional	} |
--	{ ID id-AllowedQueuingTime			CRITICALITY reject	TYPE AllowedQueuingTime 			PRESENCE optional	} |
--	{ ID id-UL-DPCH-Information-RL-SetupRqstFDD	CRITICALITY reject	TYPE UL-DPCH-Information-RL-SetupRqstFDD		PRESENCE mandatory	} |
--	{ ID id-DL-DPCH-Information-RL-SetupRqstFDD	CRITICALITY reject	TYPE DL-DPCH-Information-RL-SetupRqstFDD		PRESENCE optional	} |
--	{ ID id-DCH-FDD-Information		CRITICALITY reject	TYPE DCH-FDD-Information		PRESENCE mandatory	} |
--	{ ID id-RL-Information-RL-SetupRqstFDD		CRITICALITY notify	TYPE RL-InformationList-RL-SetupRqstFDD		PRESENCE mandatory	}|
--	{ ID id-Transmission-Gap-Pattern-Sequence-Information		CRITICALITY reject	TYPE Transmission-Gap-Pattern-Sequence-Information	 PRESENCE optional } |
--	{ ID id-Active-Pattern-Sequence-Information	CRITICALITY reject	TYPE Active-Pattern-Sequence-Information	 PRESENCE optional },
--	...
--}

UL-DPCH-Information-RL-SetupRqstFDD ::= SEQUENCE {
	ul-ScramblingCode				UL-ScramblingCode,
	minUL-ChannelisationCodeLength			MinUL-ChannelisationCodeLength,
	maxNrOfUL-DPCHs					MaxNrOfUL-DPCHs			OPTIONAL
	-- This IE shall be present if minUL-ChannelisationCodeLength equals to 4 -- ,
	ul-PunctureLimit				PunctureLimit,
	ul-TFCS							TFCS,
	ul-DPCCH-SlotFormat				UL-DPCCH-SlotFormat,
	ul-SIRTarget					UL-SIR			OPTIONAL,
	diversityMode					DiversityMode,
	not-Used-sSDT-CellIdLength		NULL			OPTIONAL,
	not-Used-s-FieldLength			NULL			OPTIONAL,
--	iE-Extensions					ProtocolExtensionContainer { {UL-DPCH-Information-RL-SetupRqstFDD-ExtIEs} } OPTIONAL,
	iE-Extensions					ProtocolExtensionContainer OPTIONAL,
	...
}

--UL-DPCH-Information-RL-SetupRqstFDD-ExtIEs RNSAP-PROTOCOL-EXTENSION ::= {
--	{ ID id-DPC-Mode				CRITICALITY reject		EXTENSION DPC-Mode				PRESENCE optional }|
--	{ ID id-UL-DPDCHIndicatorEDCH	CRITICALITY reject		EXTENSION UL-DPDCHIndicatorEDCH	PRESENCE conditional },
	-- This IE shall be present if E-DPCH Information IE is present.
--	...
--}

DL-DPCH-Information-RL-SetupRqstFDD ::= SEQUENCE {
	tFCS							TFCS,
	dl-DPCH-SlotFormat				DL-DPCH-SlotFormat,
	nrOfDLchannelisationcodes		NrOfDLchannelisationcodes,
	tFCI-SignallingMode				TFCI-SignallingMode,
	tFCI-Presence					TFCI-Presence			OPTIONAL
	-- This IE shall be present if DL DPCH Slot Format IE is equal to any of the values from 12 to 16 --,
	multiplexingPosition				MultiplexingPosition,
	powerOffsetInformation				PowerOffsetInformation-RL-SetupRqstFDD,
	fdd-dl-TPC-DownlinkStepSize		FDD-TPC-DownlinkStepSize,
	limitedPowerIncrease			LimitedPowerIncrease,
	innerLoopDLPCStatus				InnerLoopDLPCStatus,
--	iE-Extensions					ProtocolExtensionContainer { {DL-DPCH-Information-RL-SetupRqstFDD-ExtIEs} } OPTIONAL,
	iE-Extensions					ProtocolExtensionContainer OPTIONAL,
	...
}

--DL-DPCH-Information-RL-SetupRqstFDD-ExtIEs RNSAP-PROTOCOL-EXTENSION ::= {
--	...
--}

PowerOffsetInformation-RL-SetupRqstFDD ::= SEQUENCE {
		po1-ForTFCI-Bits				PowerOffset,
		po2-ForTPC-Bits					PowerOffset,
		po3-ForPilotBits				PowerOffset,
--		iE-Extensions					ProtocolExtensionContainer { { PowerOffsetInformation-RL-SetupRqstFDD-ExtIEs} } OPTIONAL,
		iE-Extensions					ProtocolExtensionContainer 
		OPTIONAL,
		...
}

--PowerOffsetInformation-RL-SetupRqstFDD-ExtIEs RNSAP-PROTOCOL-EXTENSION ::= {
--	...
--}

--RL-InformationList-RL-SetupRqstFDD 			::= SEQUENCE (SIZE (1..maxNrOfRLs)) OF ProtocolIE-Single-Container { {RL-InformationItemIEs-RL-SetupRqstFDD} }
RL-InformationList-RL-SetupRqstFDD::= SEQUENCE (SIZE (1..16)) OF ProtocolIE-Single-Container

--RL-InformationItemIEs-RL-SetupRqstFDD RNSAP-PROTOCOL-IES ::= {
--	{ ID id-RL-InformationItem-RL-SetupRqstFDD	CRITICALITY notify	TYPE RL-InformationItem-RL-SetupRqstFDD 		PRESENCE mandatory	}
--}

RL-InformationItem-RL-SetupRqstFDD ::= SEQUENCE {
	rL-ID							RL-ID,
	c-ID							C-ID,
	firstRLS-indicator				FirstRLS-Indicator,
	frameOffset						FrameOffset,
	chipOffset						ChipOffset,
	propagationDelay				PropagationDelay		OPTIONAL,
	diversityControlField			DiversityControlField		OPTIONAL
	-- This IE shall be present if the RL is not the first one in the RL-InformationList-RL-SetupRqstFDD --,
	dl-InitialTX-Power				DL-Power			OPTIONAL,
	primaryCPICH-EcNo				PrimaryCPICH-EcNo			OPTIONAL,
	not-Used-sSDT-CellID			NULL			OPTIONAL,
	transmitDiversityIndicator		TransmitDiversityIndicator		OPTIONAL,
	-- This IE shall be present unless Diversity Mode IE in UL DPCH Information group is "none"
--	iE-Extensions					ProtocolExtensionContainer { {RL-InformationItem-RL-SetupRqstFDD-ExtIEs} } OPTIONAL,
	iE-Extensions					ProtocolExtensionContainer OPTIONAL,
	...
}

--RL-InformationItem-RL-SetupRqstFDD-ExtIEs RNSAP-PROTOCOL-EXTENSION ::= {
--	{ ID id-Enhanced-PrimaryCPICH-EcNo	CRITICALITY ignore	EXTENSION Enhanced-PrimaryCPICH-EcNo	PRESENCE optional	}|
--	{ ID id-RL-Specific-DCH-Info		CRITICALITY ignore	EXTENSION RL-Specific-DCH-Info			PRESENCE optional	}|
--	{ ID id-DelayedActivation			CRITICALITY reject	EXTENSION DelayedActivation				PRESENCE optional }|
--	{ ID id-CellPortionID				CRITICALITY ignore	EXTENSION CellPortionID 				PRESENCE optional }|
--	{ ID id-RL-Specific-EDCH-Information			CRITICALITY reject		EXTENSION RL-Specific-EDCH-Information 			PRESENCE optional }|
--	{ ID id-EDCH-RL-Indication						CRITICALITY reject		EXTENSION EDCH-RL-Indication						PRESENCE optional },
--	...
--}

--RadioLinkSetupRequestFDD-Extensions RNSAP-PROTOCOL-EXTENSION ::= {
--	{ ID id-Permanent-NAS-UE-Identity					CRITICALITY ignore	EXTENSION Permanent-NAS-UE-Identity						PRESENCE optional }|
--	{ ID id-DL-PowerBalancing-Information				CRITICALITY ignore	EXTENSION DL-PowerBalancing-Information					PRESENCE optional}|
--	{ ID id-HSDSCH-FDD-Information						CRITICALITY reject	EXTENSION HSDSCH-FDD-Information					PRESENCE optional }|
--	{ ID id-HSPDSCH-RL-ID								CRITICALITY reject	EXTENSION RL-ID													PRESENCE conditional }|
	-- This IE shall be present if HS-DSCH Information IE is present.
--	{ ID id-MBMS-Bearer-Service-List				CRITICALITY notify	EXTENSION MBMS-Bearer-Service-List						PRESENCE optional }|
--	{ ID id-EDPCH-Information						CRITICALITY reject		EXTENSION EDPCH-Information-FDD					PRESENCE optional }|
--	{ ID id-EDCH-FDD-Information					CRITICALITY reject		EXTENSION EDCH-FDD-Information						PRESENCE conditional }|
	-- This IE is present if E-DPCH Information IE is present.
--	{ ID id-Serving-EDCHRL-Id						CRITICALITY reject		EXTENSION EDCH-Serving-RL											PRESENCE conditional }|
	-- This IE is present if E-DCHInformation IE is present.
--	{ ID id-F-DPCH-Information-RL-SetupRqstFDD		CRITICALITY reject	EXTENSION F-DPCH-Information-RL-SetupRqstFDD		PRESENCE optional }|
--	{ ID id-Initial-DL-DPCH-TimingAdjustment-Allowed	CRITICALITY ignore	EXTENSION Initial-DL-DPCH-TimingAdjustment-Allowed	PRESENCE optional },
--	...
--}


F-DPCH-Information-RL-SetupRqstFDD ::= SEQUENCE {
	powerOffsetInformation			PowerOffsetInformation-F-DPCH-RL-SetupRqstFDD,
	fdd-dl-TPC-DownlinkStepSize		FDD-TPC-DownlinkStepSize,
	limitedPowerIncrease			LimitedPowerIncrease,
	innerLoopDLPCStatus				InnerLoopDLPCStatus,
--	iE-Extensions					ProtocolExtensionContainer { { F-DPCH-Information-RL-SetupRqstFDD-ExtIEs} }					OPTIONAL,
	iE-Extensions					ProtocolExtensionContainer OPTIONAL,
	...
}

--F-DPCH-Information-RL-SetupRqstFDD-ExtIEs RNSAP-PROTOCOL-EXTENSION ::= {
--	...
--}

PowerOffsetInformation-F-DPCH-RL-SetupRqstFDD ::= SEQUENCE {
	po2-ForTPC-Bits					PowerOffset,
--	iE-Extensions					ProtocolExtensionContainer { { PowerOffsetInformation-F-DPCH-RL-SetupRqstFDD-ExtIEs} }		OPTIONAL,
	iE-Extensions					ProtocolExtensionContainer OPTIONAL,
	...
}

--PowerOffsetInformation-F-DPCH-RL-SetupRqstFDD-ExtIEs RNSAP-PROTOCOL-EXTENSION ::= {
--	...
--}

-- **************************************************************
--
-- RADIO LINK SETUP REQUEST TDD
--
-- **************************************************************

--RadioLinkSetupRequestTDD ::= SEQUENCE {
--	protocolIEs                     ProtocolIE-Container       {{RadioLinkSetupRequestTDD-IEs}},
--	protocolExtensions              ProtocolExtensionContainer {{RadioLinkSetupRequestTDD-Extensions}}                   OPTIONAL,
--	...
--}
RadioLinkSetupRequestTDD ::= SEQUENCE {
	protocolIEs                     ProtocolIE-Container,
	protocolExtensions              ProtocolExtensionContainer OPTIONAL,
	...
}
--RadioLinkSetupRequestTDD-IEs RNSAP-PROTOCOL-IES ::= {
--	{ ID id-SRNC-ID										CRITICALITY reject	TYPE RNC-ID													PRESENCE mandatory} |
--	{ ID id-S-RNTI										CRITICALITY reject	TYPE S-RNTI 												PRESENCE mandatory} |
--	{ ID id-D-RNTI										CRITICALITY reject	TYPE D-RNTI													PRESENCE optional	} |
--	{ ID id-UL-Physical-Channel-Information-RL-SetupRqstTDD	CRITICALITY reject	TYPE UL-Physical-Channel-Information-RL-SetupRqstTDD		PRESENCE mandatory	} |
--	{ ID id-DL-Physical-Channel-Information-RL-SetupRqstTDD	CRITICALITY reject	TYPE DL-Physical-Channel-Information-RL-SetupRqstTDD		PRESENCE mandatory	} |
--	{ ID id-AllowedQueuingTime							CRITICALITY reject	TYPE AllowedQueuingTime 									PRESENCE optional	} |
--	{ ID id-UL-CCTrCH-InformationList-RL-SetupRqstTDD	CRITICALITY notify	TYPE UL-CCTrCH-InformationList-RL-SetupRqstTDD	PRESENCE optional	} |
--	{ ID id-DL-CCTrCH-InformationList-RL-SetupRqstTDD	CRITICALITY notify	TYPE DL-CCTrCH-InformationList-RL-SetupRqstTDD 	PRESENCE optional	} |
--	{ ID id-DCH-TDD-Information			CRITICALITY reject	TYPE DCH-TDD-Information 			PRESENCE optional	} |
--	{ ID id-DSCH-TDD-Information		CRITICALITY reject	TYPE DSCH-TDD-Information			PRESENCE optional	} |
--	{ ID id-USCH-Information		CRITICALITY reject	TYPE USCH-Information			PRESENCE optional	} |
--	{ ID id-RL-Information-RL-SetupRqstTDD				CRITICALITY reject	TYPE RL-Information-RL-SetupRqstTDD					PRESENCE mandatory},
--	...
--}

UL-Physical-Channel-Information-RL-SetupRqstTDD ::= SEQUENCE {
	maxNrTimeslots-UL				MaxNrTimeslots,
	minimumSpreadingFactor-UL		MinimumSpreadingFactor,
	maxNrULPhysicalchannels			MaxNrULPhysicalchannels,
--	iE-Extensions					ProtocolExtensionContainer { {UL-Physical-Channel-InformationItem-RL-SetupRqstTDD-ExtIEs} } OPTIONAL,
	iE-Extensions					ProtocolExtensionContainer OPTIONAL,
	...
}

--UL-Physical-Channel-InformationItem-RL-SetupRqstTDD-ExtIEs RNSAP-PROTOCOL-EXTENSION ::= {
--	{ ID id-TDD-Support-8PSK		CRITICALITY ignore		EXTENSION Support-8PSK		PRESENCE optional	},
	-- Applicable to 1.28Mcps TDD only
--	...
--}

DL-Physical-Channel-Information-RL-SetupRqstTDD ::= SEQUENCE {
	maxNrTimeslots-DL				MaxNrTimeslots,
	minimumSpreadingFactor-DL		MinimumSpreadingFactor,
	maxNrDLPhysicalchannels			MaxNrDLPhysicalchannels,
--	iE-Extensions					ProtocolExtensionContainer { {DL-Physical-Channel-InformationItem-RL-SetupRqstTDD-ExtIEs} } OPTIONAL,
	iE-Extensions					ProtocolExtensionContainer OPTIONAL,
	...
}

--DL-Physical-Channel-InformationItem-RL-SetupRqstTDD-ExtIEs RNSAP-PROTOCOL-EXTENSION ::= {
--	{ ID id-TDD-maxNrDLPhysicalchannels		CRITICALITY ignore			EXTENSION MaxNrDLPhysicalchannelsTS		PRESENCE optional	}|
--	{ ID id-TDD-Support-8PSK				CRITICALITY ignore			EXTENSION Support-8PSK						PRESENCE optional	},
	-- Applicable to 1.28Mcps TDD only
--	...
--}

--UL-CCTrCH-InformationList-RL-SetupRqstTDD			::= SEQUENCE (SIZE (1..maxNrOfCCTrCHs)) OF ProtocolIE-Single-Container { {UL-CCTrCH-InformationItemIEs-RL-SetupRqstTDD} }
UL-CCTrCH-InformationList-RL-SetupRqstTDD			::= SEQUENCE (SIZE (1..16)) OF ProtocolIE-Single-Container

--UL-CCTrCH-InformationItemIEs-RL-SetupRqstTDD RNSAP-PROTOCOL-IES ::= {
--	{ ID id-UL-CCTrCH-InformationItem-RL-SetupRqstTDD	CRITICALITY notify	TYPE UL-CCTrCH-InformationItem-RL-SetupRqstTDD 	PRESENCE mandatory	}
--}

UL-CCTrCH-InformationItem-RL-SetupRqstTDD ::= SEQUENCE {
	cCTrCH-ID					CCTrCH-ID,
	ul-TFCS						TFCS,
	tFCI-Coding					TFCI-Coding,
	ul-PunctureLimit				PunctureLimit,
--	iE-Extensions					ProtocolExtensionContainer { {UL-CCTrCH-InformationItem-RL-SetupRqstTDD-ExtIEs} } OPTIONAL,
	iE-Extensions					ProtocolExtensionContainer OPTIONAL,
	...
}

--UL-CCTrCH-InformationItem-RL-SetupRqstTDD-ExtIEs RNSAP-PROTOCOL-EXTENSION ::= {
--	{ ID id-TDD-TPC-UplinkStepSize-LCR-RL-SetupRqstTDD		CRITICALITY reject		EXTENSION	TDD-TPC-UplinkStepSize-LCR		PRESENCE optional	},
	-- Mandatory for 1.28Mcps TDD, not applicable to 3.84Mcps TDD
--	...
--}

--DL-CCTrCH-InformationList-RL-SetupRqstTDD			::= SEQUENCE (SIZE (1..maxNrOfCCTrCHs)) OF ProtocolIE-Single-Container { {DL-CCTrCH-InformationItemIEs-RL-SetupRqstTDD} }
DL-CCTrCH-InformationList-RL-SetupRqstTDD			::= SEQUENCE (SIZE (1..16)) OF ProtocolIE-Single-Container

--DL-CCTrCH-InformationItemIEs-RL-SetupRqstTDD RNSAP-PROTOCOL-IES ::= {
--	{ ID id-DL-CCTrCH-InformationItem-RL-SetupRqstTDD	CRITICALITY notify	TYPE DL-CCTrCH-InformationItem-RL-SetupRqstTDD	PRESENCE mandatory	 }
--}

DL-CCTrCH-InformationItem-RL-SetupRqstTDD ::= SEQUENCE {
	cCTrCH-ID					CCTrCH-ID,
	dl-TFCS						TFCS,
	tFCI-Coding					TFCI-Coding,
	dl-PunctureLimit				PunctureLimit,
	tdd-TPC-DownlinkStepSize		TDD-TPC-DownlinkStepSize,
	cCTrCH-TPCList					CCTrCH-TPCList-RL-SetupRqstTDD	OPTIONAL,
--	iE-Extensions					ProtocolExtensionContainer { {DL-CCTrCH-InformationItem-RL-SetupRqstTDD-ExtIEs} } OPTIONAL,
	iE-Extensions					ProtocolExtensionContainer OPTIONAL,
	...
}

--DL-CCTrCH-InformationItem-RL-SetupRqstTDD-ExtIEs RNSAP-PROTOCOL-EXTENSION ::= {
--	...
--}

--CCTrCH-TPCList-RL-SetupRqstTDD ::= SEQUENCE (SIZE (1..maxNrOfCCTrCHs)) OF CCTrCH-TPCItem-RL-SetupRqstTDD
CCTrCH-TPCList-RL-SetupRqstTDD ::= SEQUENCE (SIZE (1..16)) OF CCTrCH-TPCItem-RL-SetupRqstTDD

CCTrCH-TPCItem-RL-SetupRqstTDD	 ::= SEQUENCE {
	cCTrCH-ID							CCTrCH-ID,
--	iE-Extensions						ProtocolExtensionContainer { { CCTrCH-TPCItem-RL-SetupRqstTDD-ExtIEs} } OPTIONAL,
	iE-Extensions						ProtocolExtensionContainer OPTIONAL,
	...
}

--CCTrCH-TPCItem-RL-SetupRqstTDD-ExtIEs RNSAP-PROTOCOL-EXTENSION ::= {
--	...
--}

RL-Information-RL-SetupRqstTDD ::= SEQUENCE {
	rL-ID						RL-ID,
	c-ID						C-ID,
	frameOffset					FrameOffset,
	specialBurstScheduling		SpecialBurstScheduling,
	primaryCCPCH-RSCP				PrimaryCCPCH-RSCP		OPTIONAL,
	dL-TimeSlot-ISCP				DL-TimeSlot-ISCP-Info	OPTIONAL,
	--for 3.84Mcps TDD only
--	iE-Extensions					ProtocolExtensionContainer { {RL-Information-RL-SetupRqstTDD-ExtIEs} } OPTIONAL,
	iE-Extensions					ProtocolExtensionContainer OPTIONAL,
	...
}

--RL-Information-RL-SetupRqstTDD-ExtIEs RNSAP-PROTOCOL-EXTENSION ::= {
--	{ ID id-DL-Timeslot-ISCP-LCR-Information-RL-SetupRqstTDD	CRITICALITY reject		EXTENSION 	DL-TimeSlot-ISCP-LCR-Information	PRESENCE optional	}|
--	{ ID id-TSTD-Support-Indicator-RL-SetupRqstTDD				CRITICALITY ignore		EXTENSION 	TSTD-Support-Indicator				PRESENCE optional	}|
	--for 1.28Mcps TDD only
--	{ ID id-RL-Specific-DCH-Info	CRITICALITY	ignore		EXTENSION 	RL-Specific-DCH-Info	PRESENCE 	optional	}|
--	{ ID id-DelayedActivation CRITICALITY reject EXTENSION DelayedActivation PRESENCE optional }|
--	{ ID id-UL-Synchronisation-Parameters-LCR			CRITICALITY	reject		EXTENSION 	UL-Synchronisation-Parameters-LCR		PRESENCE 	optional	}|
	-- Mandatory for 1.28Mcps TDD, Not Applicable to 3.84Mcps TDD
--	{ ID id-PrimaryCCPCH-RSCP-Delta		CRITICALITY	ignore		EXTENSION 	PrimaryCCPCH-RSCP-Delta		PRESENCE 	optional	},
--	...
--}

--RadioLinkSetupRequestTDD-Extensions RNSAP-PROTOCOL-EXTENSION ::= {
--	{ ID id-Permanent-NAS-UE-Identity				CRITICALITY ignore			EXTENSION Permanent-NAS-UE-Identity		PRESENCE optional	}|
--	{ ID id-HSDSCH-TDD-Information					CRITICALITY reject			EXTENSION HSDSCH-TDD-Information		PRESENCE optional	}|
--	{ ID id-HSPDSCH-RL-ID							CRITICALITY reject			EXTENSION RL-ID									PRESENCE conditional	}|
	-- This IE shall be present if HS-DSCH Information IE is present.
--	{ ID id-PDSCH-RL-ID				CRITICALITY ignore			EXTENSION RL-ID		PRESENCE optional }|
--	{ ID id-MBMS-Bearer-Service-List		CRITICALITY	notify 	EXTENSION MBMS-Bearer-Service-List			PRESENCE optional},	...
--}

-- **************************************************************
--
-- RADIO LINK SETUP RESPONSE FDD
--
-- **************************************************************

--RadioLinkSetupResponseFDD ::= SEQUENCE {
--	protocolIEs                     ProtocolIE-Container       {{RadioLinkSetupResponseFDD-IEs}},
--	protocolExtensions              ProtocolExtensionContainer {{RadioLinkSetupResponseFDD-Extensions}}                   OPTIONAL,
--	...
--}
RadioLinkSetupResponseFDD ::= SEQUENCE {
	protocolIEs                     ProtocolIE-Container,
	protocolExtensions              ProtocolExtensionContainer OPTIONAL,
	...
}

--RadioLinkSetupResponseFDD-IEs RNSAP-PROTOCOL-IES ::= {
--	{ ID id-D-RNTI							CRITICALITY ignore	TYPE D-RNTI 					PRESENCE optional	} |
--	{ ID id-CN-PS-DomainIdentifier			CRITICALITY ignore	TYPE CN-PS-DomainIdentifier			PRESENCE optional	} |
--	{ ID id-CN-CS-DomainIdentifier			CRITICALITY ignore	TYPE CN-CS-DomainIdentifier			PRESENCE optional	} |
--	{ ID id-RL-InformationResponseList-RL-SetupRspFDD	CRITICALITY ignore	TYPE RL-InformationResponseList-RL-SetupRspFDD 	PRESENCE mandatory	} |
--	{ ID id-UL-SIRTarget					CRITICALITY ignore	TYPE UL-SIR 				PRESENCE optional	} |
--	{ ID id-CriticalityDiagnostics			CRITICALITY ignore	TYPE CriticalityDiagnostics			PRESENCE optional	},
--	...
--}

--RL-InformationResponseList-RL-SetupRspFDD 		::= SEQUENCE (SIZE (1..maxNrOfRLs)) OF ProtocolIE-Single-Container { {RL-InformationResponseItemIEs-RL-SetupRspFDD} }
RL-InformationResponseList-RL-SetupRspFDD 		::= SEQUENCE (SIZE (1..16)) OF ProtocolIE-Single-Container

--RL-InformationResponseItemIEs-RL-SetupRspFDD RNSAP-PROTOCOL-IES ::= {
--	{ ID id-RL-InformationResponseItem-RL-SetupRspFDD	CRITICALITY ignore	TYPE RL-InformationResponseItem-RL-SetupRspFDD 	PRESENCE mandatory	}
--}

RL-InformationResponseItem-RL-SetupRspFDD ::= SEQUENCE {
	rL-ID							RL-ID,
	rL-Set-ID						RL-Set-ID,
	uRA-Information					URA-Information		OPTIONAL,
	sAI								SAI,
	gA-Cell							GA-Cell		OPTIONAL,
	gA-AccessPointPosition			GA-AccessPointPosition		OPTIONAL,
	received-total-wide-band-power	Received-total-wide-band-power,
	not-Used-secondary-CCPCH-Info			NULL		OPTIONAL,
	dl-CodeInformation				FDD-DL-CodeInformation,
	diversityIndication				DiversityIndication-RL-SetupRspFDD,

	sSDT-SupportIndicator			SSDT-SupportIndicator,
	maxUL-SIR						UL-SIR,
	minUL-SIR						UL-SIR,
	closedlooptimingadjustmentmode	Closedlooptimingadjustmentmode			OPTIONAL,
	maximumAllowedULTxPower			MaximumAllowedULTxPower,
	maximumDLTxPower				DL-Power,
	minimumDLTxPower				DL-Power,
	primaryScramblingCode			PrimaryScramblingCode					OPTIONAL,
	uL-UARFCN						UARFCN									OPTIONAL,
	dL-UARFCN						UARFCN									OPTIONAL,
	primaryCPICH-Power				PrimaryCPICH-Power,
	not-Used-dSCHInformationResponse	NULL								OPTIONAL,
	neighbouring-UMTS-CellInformation	Neighbouring-UMTS-CellInformation	OPTIONAL,
	neighbouring-GSM-CellInformation	Neighbouring-GSM-CellInformation	OPTIONAL,
	pC-Preamble						PC-Preamble,
	sRB-Delay						SRB-Delay,
--	iE-Extensions					ProtocolExtensionContainer { {RL-InformationResponseItem-RL-SetupRspFDD-ExtIEs} } OPTIONAL,
	iE-Extensions					ProtocolExtensionContainer OPTIONAL,
	...
}

--RL-InformationResponseItem-RL-SetupRspFDD-ExtIEs RNSAP-PROTOCOL-EXTENSION ::= {
--	{ ID id-GA-CellAdditionalShapes						CRITICALITY ignore	EXTENSION GA-CellAdditionalShapes								PRESENCE optional }|
--	{ ID id-DL-PowerBalancing-ActivationIndicator		CRITICALITY ignore	EXTENSION DL-PowerBalancing-ActivationIndicator			PRESENCE optional }|
--	{ ID id-HCS-Prio									CRITICALITY ignore	EXTENSION HCS-Prio													PRESENCE optional }|
--	{ ID id-Primary-CPICH-Usage-For-Channel-Estimation	CRITICALITY ignore	EXTENSION Primary-CPICH-Usage-For-Channel-Estimation	PRESENCE optional }|
--	{ ID id-Secondary-CPICH-Information					CRITICALITY ignore	EXTENSION Secondary-CPICH-Information						PRESENCE optional }|
--	{ ID id-Active-MBMS-Bearer-ServiceFDD-PFL				CRITICALITY ignore	EXTENSION Active-MBMS-Bearer-Service-ListFDD-PFL				PRESENCE optional }|
--	{ ID id-EDCH-RLSet-Id								CRITICALITY ignore	EXTENSION RL-Set-ID													PRESENCE optional }|
--	{ ID id-EDCH-FDD-DL-ControlChannelInformation		CRITICALITY ignore	EXTENSION EDCH-FDD-DL-ControlChannelInformation			PRESENCE optional }|
--	{ ID id-Initial-DL-DPCH-TimingAdjustment			CRITICALITY ignore	EXTENSION DL-DPCH-TimingAdjustment							PRESENCE optional },
--	...
--}

DiversityIndication-RL-SetupRspFDD ::= CHOICE {
	combining						Combining-RL-SetupRspFDD,
	nonCombiningOrFirstRL			NonCombiningOrFirstRL-RL-SetupRspFDD
}

Combining-RL-SetupRspFDD ::= SEQUENCE {
	rL-ID						RL-ID,
--	iE-Extensions				ProtocolExtensionContainer { { CombiningItem-RL-SetupRspFDD-ExtIEs} } OPTIONAL,
	iE-Extensions				ProtocolExtensionContainer OPTIONAL,
	...
}

--CombiningItem-RL-SetupRspFDD-ExtIEs RNSAP-PROTOCOL-EXTENSION ::= {
--	{ ID id-DCH-InformationResponse			CRITICALITY ignore	EXTENSION DCH-InformationResponse			PRESENCE optional	}|
--	{ ID id-EDCH-FDD-InformationResponse	CRITICALITY ignore	EXTENSION EDCH-FDD-InformationResponse			PRESENCE optional	},
--	...
--}

NonCombiningOrFirstRL-RL-SetupRspFDD ::= SEQUENCE {
	dCH-InformationResponse		DCH-InformationResponse,
--	iE-Extensions				ProtocolExtensionContainer { { NonCombiningOrFirstRLItem-RL-SetupRspFDD-ExtIEs} } OPTIONAL,
	iE-Extensions				ProtocolExtensionContainer OPTIONAL,
	...
}

--NonCombiningOrFirstRLItem-RL-SetupRspFDD-ExtIEs RNSAP-PROTOCOL-EXTENSION ::= {
--	{ID id-EDCH-FDD-InformationResponse		CRITICALITY ignore	EXTENSION EDCH-FDD-InformationResponse			PRESENCE mandatory},
--	...
--}

--RadioLinkSetupResponseFDD-Extensions RNSAP-PROTOCOL-EXTENSION ::= {
--	{ ID id-HSDSCH-RNTI							CRITICALITY ignore		EXTENSION HSDSCH-RNTI									PRESENCE optional }|
--	{ ID id-HSDSCH-FDD-Information-Response		CRITICALITY ignore		EXTENSION HSDSCH-FDD-Information-Response		PRESENCE optional },
--	...
--}

-- **************************************************************
--
-- RADIO LINK SETUP RESPONSE TDD
--
-- **************************************************************

--RadioLinkSetupResponseTDD ::= SEQUENCE {
--	protocolIEs                     ProtocolIE-Container       {{RadioLinkSetupResponseTDD-IEs}},
--	protocolExtensions              ProtocolExtensionContainer {{RadioLinkSetupResponseTDD-Extensions}}                   OPTIONAL,
--	...
--}
RadioLinkSetupResponseTDD ::= SEQUENCE {
	protocolIEs                     ProtocolIE-Container,
	protocolExtensions              ProtocolExtensionContainer	OPTIONAL,
	...
}

--RadioLinkSetupResponseTDD-IEs RNSAP-PROTOCOL-IES ::= {
--	{ ID id-D-RNTI					CRITICALITY ignore	TYPE D-RNTI 					PRESENCE optional	} |
--	{ ID id-CN-PS-DomainIdentifier			CRITICALITY ignore	TYPE CN-PS-DomainIdentifier			PRESENCE optional	} |
--	{ ID id-CN-CS-DomainIdentifier			CRITICALITY ignore	TYPE CN-CS-DomainIdentifier			PRESENCE optional	} |
--	{ ID id-RL-InformationResponse-RL-SetupRspTDD	CRITICALITY ignore	TYPE RL-InformationResponse-RL-SetupRspTDD 	PRESENCE optional	} |
	--Mandatory for 3.84Mcps TDD only
--	{ ID id-UL-SIRTarget				CRITICALITY ignore	TYPE UL-SIR 				PRESENCE mandatory	} |
--	{ ID id-CriticalityDiagnostics			CRITICALITY ignore	TYPE CriticalityDiagnostics			PRESENCE optional	},
--	...
--}

RL-InformationResponse-RL-SetupRspTDD ::= SEQUENCE {
	rL-ID						RL-ID,
	uRA-Information				URA-Information		OPTIONAL,
	sAI							SAI,
	gA-Cell						GA-Cell		OPTIONAL,
	gA-AccessPointPosition		GA-AccessPointPosition	OPTIONAL,
	ul-TimeSlot-ISCP-Info		UL-TimeSlot-ISCP-Info,
	maxUL-SIR					UL-SIR,
	minUL-SIR					UL-SIR,
	maximumAllowedULTxPower		MaximumAllowedULTxPower,
	maximumDLTxPower			DL-Power,
	minimumDLTxPower			DL-Power,
	uARFCNforNt					UARFCN				OPTIONAL,
	cellParameterID				CellParameterID		OPTIONAL,
	syncCase					SyncCase			OPTIONAL,
	sCH-TimeSlot				SCH-TimeSlot		OPTIONAL,
	-- This IE shall be present if Sync Case IE is equal to "Case2". --
	sCTD-Indicator				SCTD-Indicator	OPTIONAL,
	pCCPCH-Power				PCCPCH-Power,
	timingAdvanceApplied		TimingAdvanceApplied,
	alphaValue					AlphaValue,
	ul-PhysCH-SF-Variation		UL-PhysCH-SF-Variation,
	synchronisationConfiguration		SynchronisationConfiguration,
	secondary-CCPCH-Info-TDD			Secondary-CCPCH-Info-TDD	OPTIONAL,
	ul-CCTrCHInformation				UL-CCTrCHInformationList-RL-SetupRspTDD		OPTIONAL,
	dl-CCTrCHInformation				DL-CCTrCHInformationList-RL-SetupRspTDD		OPTIONAL,
	dCH-InformationResponse				DCH-InformationResponseList-RL-SetupRspTDD	OPTIONAL,
	dsch-InformationResponse			DSCH-InformationResponse-RL-SetupRspTDD OPTIONAL,
	usch-InformationResponse			USCH-InformationResponse-RL-SetupRspTDD OPTIONAL,
	neighbouring-UMTS-CellInformation			Neighbouring-UMTS-CellInformation OPTIONAL,
	neighbouring-GSM-CellInformation			Neighbouring-GSM-CellInformation OPTIONAL,
--	iE-Extensions					ProtocolExtensionContainer { {RL-InformationResponse-RL-SetupRspTDD-ExtIEs} } OPTIONAL,
	iE-Extensions					ProtocolExtensionContainer OPTIONAL,
	...
}

--RL-InformationResponse-RL-SetupRspTDD-ExtIEs RNSAP-PROTOCOL-EXTENSION ::= {
--	{ ID id-GA-CellAdditionalShapes			CRITICALITY	ignore	EXTENSION	GA-CellAdditionalShapes		PRESENCE optional }|
--	{ ID id-HCS-Prio			CRITICALITY	ignore	EXTENSION	HCS-Prio		PRESENCE optional }|
--	{ ID id-TimeSlot-RL-SetupRspTDD		CRITICALITY ignore	EXTENSION	TimeSlot	PRESENCE conditional	},
	-- This IE shall be present if Sync Case IE is Case1. --
--	...
--}

--UL-CCTrCHInformationList-RL-SetupRspTDD ::= ProtocolIE-Single-Container {{UL-CCTrCHInformationListIEs-RL-SetupRspTDD}}
UL-CCTrCHInformationList-RL-SetupRspTDD ::= ProtocolIE-Single-Container 

--UL-CCTrCHInformationListIEs-RL-SetupRspTDD RNSAP-PROTOCOL-IES ::= {
--	{ ID id-UL-CCTrCH-InformationListIE-RL-SetupRspTDD   CRITICALITY ignore	TYPE UL-CCTrCHInformationListIE-RL-SetupRspTDD		PRESENCE mandatory }
--}

--UL-CCTrCHInformationListIE-RL-SetupRspTDD ::= SEQUENCE (SIZE (1..maxNrOfCCTrCHs)) OF UL-CCTrCHInformationItem-RL-SetupRspTDD
UL-CCTrCHInformationListIE-RL-SetupRspTDD ::= SEQUENCE (SIZE (1..16)) OF UL-CCTrCHInformationItem-RL-SetupRspTDD

UL-CCTrCHInformationItem-RL-SetupRspTDD ::= SEQUENCE {
	cCTrCH-ID					CCTrCH-ID,
	ul-DPCH-Information				UL-DPCH-InformationList-RL-SetupRspTDD		OPTIONAL,
--	iE-Extensions					ProtocolExtensionContainer { {UL-CCTrCHInformationItem-RL-SetupRspTDD-ExtIEs} } OPTIONAL,
	iE-Extensions					ProtocolExtensionContainer OPTIONAL,
	...
}

--UL-CCTrCHInformationItem-RL-SetupRspTDD-ExtIEs RNSAP-PROTOCOL-EXTENSION ::= {
--	{ID id-UL-SIR-Target-CCTrCH-InformationItem-RL-SetupRspTDD		CRITICALITY ignore		EXTENSION UL-SIR		PRESENCE optional},
--	...
--}

--UL-DPCH-InformationList-RL-SetupRspTDD ::= ProtocolIE-Single-Container { {UL-DPCH-InformationListIEs-RL-SetupRspTDD} }
UL-DPCH-InformationList-RL-SetupRspTDD ::= ProtocolIE-Single-Container 

--UL-DPCH-InformationListIEs-RL-SetupRspTDD RNSAP-PROTOCOL-IES ::= {
--	{ ID id-UL-DPCH-InformationItem-RL-SetupRspTDD		CRITICALITY ignore	TYPE UL-DPCH-InformationItem-RL-SetupRspTDD  PRESENCE mandatory	}
--}


UL-DPCH-InformationItem-RL-SetupRspTDD ::= SEQUENCE {
	repetitionPeriod				RepetitionPeriod,
	repetitionLength				RepetitionLength,
	tDD-DPCHOffset					TDD-DPCHOffset,
	uL-Timeslot-Information			UL-Timeslot-Information,
--	iE-Extensions					ProtocolExtensionContainer { {UL-DPCH-InformationItem-RL-SetupRspTDD-ExtIEs} } OPTIONAL,
	iE-Extensions					ProtocolExtensionContainer OPTIONAL,
	...
}

--UL-DPCH-InformationItem-RL-SetupRspTDD-ExtIEs RNSAP-PROTOCOL-EXTENSION ::= {
--	...
--}

--DL-CCTrCHInformationList-RL-SetupRspTDD ::= ProtocolIE-Single-Container {{DL-CCTrCHInformationListIEs-RL-SetupRspTDD}}
DL-CCTrCHInformationList-RL-SetupRspTDD ::= ProtocolIE-Single-Container 

--DL-CCTrCHInformationListIEs-RL-SetupRspTDD RNSAP-PROTOCOL-IES ::= {
--	{ ID id-DL-CCTrCH-InformationListIE-RL-SetupRspTDD   CRITICALITY ignore	TYPE DL-CCTrCHInformationListIE-RL-SetupRspTDD  PRESENCE mandatory }
--}

--DL-CCTrCHInformationListIE-RL-SetupRspTDD ::= SEQUENCE (SIZE (1..maxNrOfCCTrCHs)) OF DL-CCTrCHInformationItem-RL-SetupRspTDD
DL-CCTrCHInformationListIE-RL-SetupRspTDD ::= SEQUENCE (SIZE (1..16)) OF DL-CCTrCHInformationItem-RL-SetupRspTDD

DL-CCTrCHInformationItem-RL-SetupRspTDD ::= SEQUENCE {
	cCTrCH-ID					CCTrCH-ID,
	dl-DPCH-Information				DL-DPCH-InformationList-RL-SetupRspTDD		OPTIONAL,
--	iE-Extensions					ProtocolExtensionContainer { {DL-CCTrCHInformationItem-RL-SetupRspTDD-ExtIEs} } OPTIONAL,
	iE-Extensions					ProtocolExtensionContainer OPTIONAL,
	...
}

--DL-CCTrCHInformationItem-RL-SetupRspTDD-ExtIEs RNSAP-PROTOCOL-EXTENSION ::= {
--	{ ID id-CCTrCH-Maximum-DL-Power-RL-SetupRspTDD		CRITICALITY ignore		EXTENSION  DL-Power    PRESENCE optional	}|
	-- this is a DCH type CCTrCH power
--	{ ID id-CCTrCH-Minimum-DL-Power-RL-SetupRspTDD		CRITICALITY ignore		EXTENSION  DL-Power    PRESENCE optional	}, 
	-- this is a DCH type CCTrCH power
--	...
--}

--DL-DPCH-InformationList-RL-SetupRspTDD ::= ProtocolIE-Single-Container { {DL-DPCH-InformationListIEs-RL-SetupRspTDD} }
DL-DPCH-InformationList-RL-SetupRspTDD ::= ProtocolIE-Single-Container

--DL-DPCH-InformationListIEs-RL-SetupRspTDD RNSAP-PROTOCOL-IES ::= {
--	{ ID id-DL-DPCH-InformationItem-RL-SetupRspTDD		CRITICALITY ignore	TYPE DL-DPCH-InformationItem-RL-SetupRspTDD  PRESENCE mandatory	}
--}

DL-DPCH-InformationItem-RL-SetupRspTDD ::= SEQUENCE {
	repetitionPeriod				RepetitionPeriod,
	repetitionLength				RepetitionLength,
	tDD-DPCHOffset					TDD-DPCHOffset,
	dL-Timeslot-Information			DL-Timeslot-Information,
--	iE-Extensions					ProtocolExtensionContainer { {DL-DPCH-InformationItem-RL-SetupRspTDD-ExtIEs} } OPTIONAL,
	iE-Extensions					ProtocolExtensionContainer OPTIONAL,
	...
}

--DL-DPCH-InformationItem-RL-SetupRspTDD-ExtIEs RNSAP-PROTOCOL-EXTENSION ::= {
--	...
--}

--DCH-InformationResponseList-RL-SetupRspTDD ::= ProtocolIE-Single-Container {{DCH-InformationResponseListIEs-RL-SetupRspTDD}}
DCH-InformationResponseList-RL-SetupRspTDD ::= ProtocolIE-Single-Container

--DCH-InformationResponseListIEs-RL-SetupRspTDD RNSAP-PROTOCOL-IES ::= {
--	{ ID id-DCH-InformationResponse   CRITICALITY ignore	TYPE DCH-InformationResponse  PRESENCE mandatory }
--}

--DSCH-InformationResponse-RL-SetupRspTDD ::= ProtocolIE-Single-Container {{DSCH-InformationList-RL-SetupRspTDD}}
DSCH-InformationResponse-RL-SetupRspTDD ::= ProtocolIE-Single-Container

--DSCH-InformationList-RL-SetupRspTDD RNSAP-PROTOCOL-IES ::= {
--	{ ID id-DSCH-InformationListIEs-RL-SetupRspTDD		CRITICALITY ignore	TYPE DSCH-InformationListIEs-RL-SetupRspTDD PRESENCE mandatory }
--}

--DSCH-InformationListIEs-RL-SetupRspTDD ::= SEQUENCE (SIZE(0..maxNoOfDSCHs)) OF DSCHInformationItem-RL-SetupRspTDD
DSCH-InformationListIEs-RL-SetupRspTDD ::= SEQUENCE (SIZE(0..10)) OF DSCHInformationItem-RL-SetupRspTDD

DSCHInformationItem-RL-SetupRspTDD ::= SEQUENCE {
	dsch-ID					DSCH-ID,
	dSCH-FlowControlInformation		DSCH-FlowControlInformation,
	bindingID				BindingID	OPTIONAL,
	transportLayerAddress	TransportLayerAddress	OPTIONAL,
	transportFormatManagement	TransportFormatManagement,
--	iE-Extensions			ProtocolExtensionContainer { {DSCHInformationItem-RL-SetupRspTDD-ExtIEs} } OPTIONAL,
	iE-Extensions			ProtocolExtensionContainer OPTIONAL,
	...
}

--DSCHInformationItem-RL-SetupRspTDD-ExtIEs RNSAP-PROTOCOL-EXTENSION ::= {
--	...
--}

--USCH-InformationResponse-RL-SetupRspTDD ::= ProtocolIE-Single-Container {{USCH-InformationList-RL-SetupRspTDD}}
USCH-InformationResponse-RL-SetupRspTDD ::= ProtocolIE-Single-Container 

--USCH-InformationList-RL-SetupRspTDD RNSAP-PROTOCOL-IES ::= {
--	{ ID id-USCH-InformationListIEs-RL-SetupRspTDD		CRITICALITY ignore	TYPE USCH-InformationListIEs-RL-SetupRspTDD PRESENCE mandatory }
--}

--USCH-InformationListIEs-RL-SetupRspTDD ::= SEQUENCE (SIZE(0..maxNoOfUSCHs)) OF USCHInformationItem-RL-SetupRspTDD 
USCH-InformationListIEs-RL-SetupRspTDD ::= SEQUENCE (SIZE(0..10)) OF USCHInformationItem-RL-SetupRspTDD 

USCHInformationItem-RL-SetupRspTDD ::= SEQUENCE {
	usch-ID						USCH-ID,
	bindingID					BindingID	OPTIONAL,
	transportLayerAddress		TransportLayerAddress	OPTIONAL,
	transportFormatManagement	TransportFormatManagement,
--	iE-Extensions				ProtocolExtensionContainer { {USCHInformationItem-RL-SetupRspTDD-ExtIEs} } OPTIONAL,
	iE-Extensions				ProtocolExtensionContainer OPTIONAL,
	...
}

--USCHInformationItem-RL-SetupRspTDD-ExtIEs RNSAP-PROTOCOL-EXTENSION ::= {
--	...
--}

--RadioLinkSetupResponseTDD-Extensions RNSAP-PROTOCOL-EXTENSION ::= {
--	{ ID id-RL-LCR-InformationResponse-RL-SetupRspTDD	CRITICALITY ignore	EXTENSION 	RL-LCR-InformationResponse-RL-SetupRspTDD		PRESENCE optional}|
	--Mandatory for 1.28Mcps TDD only
--	{ ID id-HSDSCH-RNTI							CRITICALITY ignore		EXTENSION HSDSCH-RNTI									PRESENCE optional }|
--	{ ID id-HSDSCH-TDD-Information-Response		CRITICALITY ignore		EXTENSION HSDSCH-TDD-Information-Response		PRESENCE optional }|
--	{ ID id-DSCH-RNTI							CRITICALITY ignore		EXTENSION DSCH-RNTI										PRESENCE optional }|
--	{ ID id-Active-MBMS-Bearer-ServiceTDD-PFL		CRITICALITY	ignore		EXTENSION Active-MBMS-Bearer-Service-ListTDD-PFL		PRESENCE optional},
--	...
--}

RL-LCR-InformationResponse-RL-SetupRspTDD ::= SEQUENCE {
	rL-ID						RL-ID,
	uRA-Information				URA-Information,
	sAI							SAI,
	gA-Cell						GA-Cell		OPTIONAL,
	gA-AccessPointPosition		GA-AccessPointPosition	OPTIONAL,
	ul-TimeSlot-ISCP-LCR-Info	UL-TimeSlot-ISCP-LCR-Info,
	maxUL-SIR					UL-SIR,
	minUL-SIR					UL-SIR,
	maximumAllowedULTxPower		MaximumAllowedULTxPower,
	maximumDLTxPower			DL-Power,
	minimumDLTxPower			DL-Power,
	uARFCNforNt					UARFCN					OPTIONAL,
	cellParameterID				CellParameterID			OPTIONAL,
	sCTD-Indicator		SCTD-Indicator	OPTIONAL,
	pCCPCH-Power				PCCPCH-Power,
	alphaValue					AlphaValue,
	ul-PhysCH-SF-Variation		UL-PhysCH-SF-Variation,
	synchronisationConfiguration			SynchronisationConfiguration,
	secondary-LCR-CCPCH-Info-TDD			Secondary-LCR-CCPCH-Info-TDD					OPTIONAL,
	ul-LCR-CCTrCHInformation				UL-LCR-CCTrCHInformationList-RL-SetupRspTDD		OPTIONAL,
	dl-LCR-CCTrCHInformation				DL-LCR-CCTrCHInformationList-RL-SetupRspTDD		OPTIONAL,
	dCH-InformationResponse					DCH-InformationResponseList-RL-SetupRspTDD	OPTIONAL,
	dsch-LCR-InformationResponse			DSCH-LCR-InformationResponse-RL-SetupRspTDD		OPTIONAL,
	usch-LCR-InformationResponse			USCH-LCR-InformationResponse-RL-SetupRspTDD     OPTIONAL,
	neighbouring-UMTS-CellInformation		Neighbouring-UMTS-CellInformation               OPTIONAL,
	neighbouring-GSM-CellInformation		Neighbouring-GSM-CellInformation				OPTIONAL,
--	iE-Extensions							ProtocolExtensionContainer { { RL-LCR-InformationResponseList-RL-SetupRspTDD-ExtIEs} }		OPTIONAL,
	iE-Extensions							ProtocolExtensionContainer OPTIONAL,
	... 
}

--RL-LCR-InformationResponseList-RL-SetupRspTDD-ExtIEs RNSAP-PROTOCOL-EXTENSION ::= {
--	{ ID id-GA-CellAdditionalShapes					CRITICALITY	ignore	EXTENSION	GA-CellAdditionalShapes		PRESENCE optional }|
--	{ ID id-HCS-Prio								CRITICALITY	ignore	EXTENSION	HCS-Prio							PRESENCE optional }|
--	{ ID id-UL-TimingAdvanceCtrl-LCR				CRITICALITY ignore	EXTENSION	UL-TimingAdvanceCtrl-LCR		PRESENCE optional },
	--Mandatory for 1.28Mcps TDD only
--	...
--}

--UL-LCR-CCTrCHInformationList-RL-SetupRspTDD ::= ProtocolIE-Single-Container {{UL-LCR-CCTrCHInformationListIEs-RL-SetupRspTDD}}
UL-LCR-CCTrCHInformationList-RL-SetupRspTDD ::= ProtocolIE-Single-Container

--UL-LCR-CCTrCHInformationListIEs-RL-SetupRspTDD RNSAP-PROTOCOL-IES ::= {
--	{ ID id-UL-CCTrCH-LCR-InformationListIE-RL-SetupRspTDD   CRITICALITY ignore	TYPE UL-LCR-CCTrCHInformationListIE-RL-SetupRspTDD		PRESENCE mandatory }
--}

--UL-LCR-CCTrCHInformationListIE-RL-SetupRspTDD ::= SEQUENCE (SIZE (1..maxNrOfCCTrCHsLCR)) OF UL-LCR-CCTrCHInformationItem-RL-SetupRspTDD
UL-LCR-CCTrCHInformationListIE-RL-SetupRspTDD ::= SEQUENCE (SIZE (1..16)) OF UL-LCR-CCTrCHInformationItem-RL-SetupRspTDD

UL-LCR-CCTrCHInformationItem-RL-SetupRspTDD ::= SEQUENCE {
	cCTrCH-ID					CCTrCH-ID,
	ul-DPCH-LCR-Information		UL-DPCH-LCR-InformationList-RL-SetupRspTDD		OPTIONAL,
--	iE-Extensions				ProtocolExtensionContainer { {UL-LCR-CCTrCHInformationItem-RL-SetupRspTDD-ExtIEs} } OPTIONAL,
	iE-Extensions				ProtocolExtensionContainer OPTIONAL,
	...
}

--UL-LCR-CCTrCHInformationItem-RL-SetupRspTDD-ExtIEs RNSAP-PROTOCOL-EXTENSION ::= {
--	{ID id-UL-SIR-Target-CCTrCH-LCR-InformationItem-RL-SetupRspTDD		CRITICALITY ignore		EXTENSION UL-SIR		PRESENCE optional},
--	...
--}

--UL-DPCH-LCR-InformationList-RL-SetupRspTDD ::= ProtocolIE-Single-Container { {UL-DPCH-LCR-InformationListIEs-RL-SetupRspTDD} }
UL-DPCH-LCR-InformationList-RL-SetupRspTDD ::= ProtocolIE-Single-Container

--UL-DPCH-LCR-InformationListIEs-RL-SetupRspTDD RNSAP-PROTOCOL-IES ::= {
--	{ ID id-UL-DPCH-LCR-InformationItem-RL-SetupRspTDD		CRITICALITY ignore	TYPE UL-DPCH-LCR-InformationItem-RL-SetupRspTDD  PRESENCE mandatory	}
--}

UL-DPCH-LCR-InformationItem-RL-SetupRspTDD ::= SEQUENCE {
	repetitionPeriod				RepetitionPeriod,
	repetitionLength				RepetitionLength,
	tDD-DPCHOffset					TDD-DPCHOffset,
	uL-TimeslotLCR-Information		UL-TimeslotLCR-Information,
--	iE-Extensions					ProtocolExtensionContainer { {UL-DPCH-LCR-InformationItem-RL-SetupRspTDD-ExtIEs} } OPTIONAL,
	iE-Extensions					ProtocolExtensionContainer OPTIONAL,
	...
}

--UL-DPCH-LCR-InformationItem-RL-SetupRspTDD-ExtIEs RNSAP-PROTOCOL-EXTENSION ::= {
--	...
--}
--DL-LCR-CCTrCHInformationList-RL-SetupRspTDD ::= ProtocolIE-Single-Container {{DL-LCR-CCTrCHInformationListIEs-RL-SetupRspTDD}}
DL-LCR-CCTrCHInformationList-RL-SetupRspTDD ::= ProtocolIE-Single-Container

--DL-LCR-CCTrCHInformationListIEs-RL-SetupRspTDD RNSAP-PROTOCOL-IES ::= {
--	{ ID id-DL-CCTrCH-LCR-InformationListIE-RL-SetupRspTDD   CRITICALITY ignore	TYPE DL-CCTrCH-LCR-InformationListIE-RL-SetupRspTDD  PRESENCE mandatory }
--}

--DL-CCTrCH-LCR-InformationListIE-RL-SetupRspTDD ::= SEQUENCE (SIZE (1..maxNrOfCCTrCHsLCR)) OF DL-CCTrCH-LCR-InformationItem-RL-SetupRspTDD
DL-CCTrCH-LCR-InformationListIE-RL-SetupRspTDD ::= SEQUENCE (SIZE (1..16)) OF DL-CCTrCH-LCR-InformationItem-RL-SetupRspTDD

DL-CCTrCH-LCR-InformationItem-RL-SetupRspTDD ::= SEQUENCE {
	cCTrCH-ID					CCTrCH-ID,
	dl-DPCH-LCR-Information		DL-DPCH-LCR-InformationList-RL-SetupRspTDD		OPTIONAL,
--	iE-Extensions				ProtocolExtensionContainer { {DL-CCTrCH-LCR-InformationItem-RL-SetupRspTDD-ExtIEs} } OPTIONAL,
	iE-Extensions				ProtocolExtensionContainer OPTIONAL,
	...
}

--DL-CCTrCH-LCR-InformationItem-RL-SetupRspTDD-ExtIEs RNSAP-PROTOCOL-EXTENSION ::= {
--	...
--}

--DL-DPCH-LCR-InformationList-RL-SetupRspTDD ::= ProtocolIE-Single-Container { {DL-DPCH-LCR-InformationListIEs-RL-SetupRspTDD} }
DL-DPCH-LCR-InformationList-RL-SetupRspTDD ::= ProtocolIE-Single-Container

--DL-DPCH-LCR-InformationListIEs-RL-SetupRspTDD RNSAP-PROTOCOL-IES ::= {
--	{ ID id-DL-DPCH-LCR-InformationItem-RL-SetupRspTDD		CRITICALITY ignore	TYPE DL-DPCH-LCR-InformationItem-RL-SetupRspTDD  PRESENCE mandatory	}
--}

DL-DPCH-LCR-InformationItem-RL-SetupRspTDD ::= SEQUENCE {
	repetitionPeriod				RepetitionPeriod,
	repetitionLength				RepetitionLength,
	tDD-DPCHOffset					TDD-DPCHOffset,
	dL-Timeslot-LCR-Information		DL-TimeslotLCR-Information,
	tSTD-Indicator					TSTD-Indicator,
--	iE-Extensions					ProtocolExtensionContainer { {DL-DPCH-LCR-InformationItem-RL-SetupRspTDD-ExtIEs} } OPTIONAL,
	iE-Extensions					ProtocolExtensionContainer OPTIONAL,
	...
}

--DL-DPCH-LCR-InformationItem-RL-SetupRspTDD-ExtIEs RNSAP-PROTOCOL-EXTENSION ::= {
--	...
--}

--DSCH-LCR-InformationResponse-RL-SetupRspTDD ::= ProtocolIE-Single-Container {{DSCH-LCR-InformationList-RL-SetupRspTDD}}
DSCH-LCR-InformationResponse-RL-SetupRspTDD ::= ProtocolIE-Single-Container

--DSCH-LCR-InformationList-RL-SetupRspTDD RNSAP-PROTOCOL-IES ::= {
--	{ ID id-DSCH-LCR-InformationListIEs-RL-SetupRspTDD		CRITICALITY ignore	TYPE DSCH-LCR-InformationListIEs-RL-SetupRspTDD PRESENCE mandatory }
--}

--DSCH-LCR-InformationListIEs-RL-SetupRspTDD ::= SEQUENCE (SIZE(0..maxNoOfDSCHsLCR)) OF DSCH-LCR-InformationItem-RL-SetupRspTDD
DSCH-LCR-InformationListIEs-RL-SetupRspTDD ::= SEQUENCE (SIZE(0..10)) OF DSCH-LCR-InformationItem-RL-SetupRspTDD

DSCH-LCR-InformationItem-RL-SetupRspTDD ::= SEQUENCE {
	dsch-ID					DSCH-ID,
	dSCH-FlowControlInformation		DSCH-FlowControlInformation,
	bindingID				BindingID	OPTIONAL,
	transportLayerAddress	TransportLayerAddress	OPTIONAL,
	transportFormatManagement	TransportFormatManagement,
--	iE-Extensions			ProtocolExtensionContainer { {DSCH-LCR-InformationItem-RL-SetupRspTDD-ExtIEs} } OPTIONAL,
	iE-Extensions			ProtocolExtensionContainer OPTIONAL,
	...
}

--DSCH-LCR-InformationItem-RL-SetupRspTDD-ExtIEs RNSAP-PROTOCOL-EXTENSION ::= {
--	...
--}

--USCH-LCR-InformationResponse-RL-SetupRspTDD ::= ProtocolIE-Single-Container {{USCH-LCR-InformationList-RL-SetupRspTDD}}
USCH-LCR-InformationResponse-RL-SetupRspTDD ::= ProtocolIE-Single-Container

--USCH-LCR-InformationList-RL-SetupRspTDD RNSAP-PROTOCOL-IES ::= {
--	{ ID id-USCH-LCR-InformationListIEs-RL-SetupRspTDD		CRITICALITY ignore	TYPE USCH-LCR-InformationListIEs-RL-SetupRspTDD PRESENCE mandatory }
--}

--USCH-LCR-InformationListIEs-RL-SetupRspTDD ::= SEQUENCE (SIZE(0..maxNoOfUSCHsLCR)) OF USCH-LCR-InformationItem-RL-SetupRspTDD 
USCH-LCR-InformationListIEs-RL-SetupRspTDD ::= SEQUENCE (SIZE(0..10)) OF USCH-LCR-InformationItem-RL-SetupRspTDD 

USCH-LCR-InformationItem-RL-SetupRspTDD ::= SEQUENCE {
	usch-ID						USCH-ID,
	bindingID					BindingID	OPTIONAL,
	transportLayerAddress		TransportLayerAddress	OPTIONAL,
	transportFormatManagement	TransportFormatManagement,
--	iE-Extensions				ProtocolExtensionContainer { {USCH-LCR-InformationItem-RL-SetupRspTDD-ExtIEs} } OPTIONAL,
	iE-Extensions				ProtocolExtensionContainer OPTIONAL,
	...
}

--USCH-LCR-InformationItem-RL-SetupRspTDD-ExtIEs RNSAP-PROTOCOL-EXTENSION ::= {
--	...
--}

-- **************************************************************
--
-- RADIO LINK SETUP FAILURE FDD
--
-- **************************************************************

--RadioLinkSetupFailureFDD ::= SEQUENCE {
--	protocolIEs                     ProtocolIE-Container       {{RadioLinkSetupFailureFDD-IEs}},
--	protocolExtensions              ProtocolExtensionContainer {{RadioLinkSetupFailureFDD-Extensions}}                   OPTIONAL,
--	...
--}
RadioLinkSetupFailureFDD ::= SEQUENCE {
	protocolIEs                     ProtocolIE-Container,
	protocolExtensions              ProtocolExtensionContainer OPTIONAL,
	...
}

--RadioLinkSetupFailureFDD-IEs RNSAP-PROTOCOL-IES ::= {
--	{ ID id-D-RNTI					CRITICALITY ignore	TYPE D-RNTI					PRESENCE optional	} |
--	{ ID id-CN-PS-DomainIdentifier			CRITICALITY ignore	TYPE CN-PS-DomainIdentifier			PRESENCE optional	} |
--	{ ID id-CN-CS-DomainIdentifier			CRITICALITY ignore	TYPE CN-CS-DomainIdentifier			PRESENCE optional	} |
--	{ ID id-CauseLevel-RL-SetupFailureFDD				CRITICALITY	ignore 	   TYPE	CauseLevel-RL-SetupFailureFDD		PRESENCE mandatory }|
--	{ ID id-UL-SIRTarget				CRITICALITY ignore	TYPE UL-SIR 				PRESENCE optional	} |
--	{ ID id-CriticalityDiagnostics			CRITICALITY ignore	TYPE CriticalityDiagnostics			PRESENCE optional	},
--	...
--}

CauseLevel-RL-SetupFailureFDD ::= CHOICE {
	generalCause		GeneralCauseList-RL-SetupFailureFDD,
	rLSpecificCause		RLSpecificCauseList-RL-SetupFailureFDD,
	...
}

GeneralCauseList-RL-SetupFailureFDD ::= SEQUENCE {
	cause										Cause,
--	iE-Extensions								ProtocolExtensionContainer { { GeneralCauseItem-RL-SetupFailureFDD-ExtIEs} }		OPTIONAL,
	iE-Extensions								ProtocolExtensionContainer OPTIONAL,
	...
}

--GeneralCauseItem-RL-SetupFailureFDD-ExtIEs RNSAP-PROTOCOL-EXTENSION ::= {
--	...
--}

RLSpecificCauseList-RL-SetupFailureFDD ::= SEQUENCE {
	unsuccessful-RL-InformationRespList-RL-SetupFailureFDD		UnsuccessfulRL-InformationResponseList-RL-SetupFailureFDD,
	successful-RL-InformationRespList-RL-SetupFailureFDD		SuccessfulRL-InformationResponseList-RL-SetupFailureFDD	OPTIONAL,
--	iE-Extensions								ProtocolExtensionContainer { { RLSpecificCauseItem-RL-SetupFailureFDD-ExtIEs} }		OPTIONAL,
	iE-Extensions								ProtocolExtensionContainer OPTIONAL,
	...
}

--RLSpecificCauseItem-RL-SetupFailureFDD-ExtIEs RNSAP-PROTOCOL-EXTENSION ::= {
--	{ ID id-HSDSCH-RNTI							CRITICALITY ignore		EXTENSION HSDSCH-RNTI									PRESENCE optional }|
--	{ ID id-HSDSCH-FDD-Information-Response		CRITICALITY ignore		EXTENSION HSDSCH-FDD-Information-Response		PRESENCE optional },
--	...
--}

--UnsuccessfulRL-InformationResponseList-RL-SetupFailureFDD ::= SEQUENCE (SIZE (1..maxNrOfRLs)) OF ProtocolIE-Single-Container { {UnsuccessfulRL-InformationResponse-RL-SetupFailureFDD-IEs} }
UnsuccessfulRL-InformationResponseList-RL-SetupFailureFDD ::= SEQUENCE (SIZE (1..16)) OF ProtocolIE-Single-Container 

--UnsuccessfulRL-InformationResponse-RL-SetupFailureFDD-IEs RNSAP-PROTOCOL-IES ::= {
--	{ ID id-UnsuccessfulRL-InformationResponse-RL-SetupFailureFDD		CRITICALITY ignore	TYPE UnsuccessfulRL-InformationResponse-RL-SetupFailureFDD		PRESENCE mandatory	}
--}

UnsuccessfulRL-InformationResponse-RL-SetupFailureFDD ::= SEQUENCE {
	rL-ID						RL-ID,
	cause						Cause,
--	iE-Extensions					ProtocolExtensionContainer { {UnsuccessfulRL-InformationResponse-RL-SetupFailureFDD-ExtIEs} } OPTIONAL,
	iE-Extensions					ProtocolExtensionContainer OPTIONAL,
	...
}

--UnsuccessfulRL-InformationResponse-RL-SetupFailureFDD-ExtIEs RNSAP-PROTOCOL-EXTENSION ::= {
--	...
--}

--SuccessfulRL-InformationResponseList-RL-SetupFailureFDD ::= SEQUENCE (SIZE (0..maxNrOfRLs-1)) OF ProtocolIE-Single-Container { {SuccessfulRL-InformationResponse-RL-SetupFailureFDD-IEs} }
SuccessfulRL-InformationResponseList-RL-SetupFailureFDD ::= SEQUENCE (SIZE (0..15)) OF ProtocolIE-Single-Container 

--SuccessfulRL-InformationResponse-RL-SetupFailureFDD-IEs RNSAP-PROTOCOL-IES ::= {
--	{ ID id-SuccessfulRL-InformationResponse-RL-SetupFailureFDD		CRITICALITY ignore	TYPE SuccessfulRL-InformationResponse-RL-SetupFailureFDD		PRESENCE mandatory	}
--}

SuccessfulRL-InformationResponse-RL-SetupFailureFDD ::= SEQUENCE {
	rL-ID									RL-ID,
	rL-Set-ID								RL-Set-ID,
	uRA-Information							URA-Information						OPTIONAL,
	sAI										SAI,
	gA-Cell									GA-Cell		OPTIONAL,
	gA-AccessPointPosition					GA-AccessPointPosition				OPTIONAL,
	received-total-wide-band-power			Received-total-wide-band-power,
	not-Used-secondary-CCPCH-Info					NULL				OPTIONAL,
	dl-CodeInformation						FDD-DL-CodeInformation,
	diversityIndication						DiversityIndication-RL-SetupFailureFDD, 
	sSDT-SupportIndicator					SSDT-SupportIndicator,
	maxUL-SIR								UL-SIR,
	minUL-SIR								UL-SIR,
	closedlooptimingadjustmentmode			Closedlooptimingadjustmentmode		OPTIONAL,
	maximumAllowedULTxPower					MaximumAllowedULTxPower,
	maximumDLTxPower						DL-Power,
	minimumDLTxPower						DL-Power,
	primaryCPICH-Power						PrimaryCPICH-Power,
	primaryScramblingCode					PrimaryScramblingCode				OPTIONAL,
	uL-UARFCN								UARFCN								OPTIONAL,
	dL-UARFCN								UARFCN								OPTIONAL,
	not-Used-dSCH-InformationResponse-RL-SetupFailureFDD	NULL				OPTIONAL,
	neighbouring-UMTS-CellInformation		Neighbouring-UMTS-CellInformation	OPTIONAL,
	neighbouring-GSM-CellInformation		Neighbouring-GSM-CellInformation	OPTIONAL,
	pC-Preamble								PC-Preamble,
	sRB-Delay								SRB-Delay,
--	iE-Extensions							ProtocolExtensionContainer { {SuccessfulRL-InformationResponse-RL-SetupFailureFDD-ExtIEs} } OPTIONAL,
	iE-Extensions							ProtocolExtensionContainer OPTIONAL,
	...
}

--SuccessfulRL-InformationResponse-RL-SetupFailureFDD-ExtIEs RNSAP-PROTOCOL-EXTENSION ::= {
--	{ ID id-GA-CellAdditionalShapes						CRITICALITY ignore	EXTENSION GA-CellAdditionalShapes								PRESENCE optional }|
--	{ ID id-DL-PowerBalancing-ActivationIndicator		CRITICALITY ignore	EXTENSION DL-PowerBalancing-ActivationIndicator			PRESENCE optional }|
--	{ ID id-HCS-Prio									CRITICALITY ignore	EXTENSION HCS-Prio													PRESENCE optional }|
--	{ ID id-Primary-CPICH-Usage-For-Channel-Estimation	CRITICALITY ignore	EXTENSION Primary-CPICH-Usage-For-Channel-Estimation	PRESENCE optional }|
--	{ ID id-Secondary-CPICH-Information					CRITICALITY ignore	EXTENSION Secondary-CPICH-Information						PRESENCE optional }|
--	{ ID id-Active-MBMS-Bearer-ServiceFDD-PFL				CRITICALITY ignore	EXTENSION Active-MBMS-Bearer-Service-ListFDD-PFL				PRESENCE optional }|
--	{ ID id-EDCH-RLSet-Id								CRITICALITY ignore	EXTENSION RL-Set-ID													PRESENCE optional }|
--	{ ID id-EDCH-FDD-DL-ControlChannelInformation		CRITICALITY ignore	EXTENSION EDCH-FDD-DL-ControlChannelInformation			PRESENCE optional }|
--	{ ID id-Initial-DL-DPCH-TimingAdjustment			CRITICALITY ignore	EXTENSION DL-DPCH-TimingAdjustment							PRESENCE optional },
--	...
--}

DiversityIndication-RL-SetupFailureFDD ::= CHOICE {
	combining						Combining-RL-SetupFailureFDD,
	nonCombiningOrFirstRL		NonCombiningOrFirstRL-RL-SetupFailureFDD
}

Combining-RL-SetupFailureFDD ::= SEQUENCE {
	rL-ID						RL-ID,
--	iE-Extensions				ProtocolExtensionContainer { { CombiningItem-RL-SetupFailureFDD-ExtIEs} } OPTIONAL,
	iE-Extensions				ProtocolExtensionContainer OPTIONAL,
	...
}

--CombiningItem-RL-SetupFailureFDD-ExtIEs RNSAP-PROTOCOL-EXTENSION ::= {
--	{ ID id-DCH-InformationResponse			CRITICALITY ignore	EXTENSION DCH-InformationResponse			PRESENCE optional	}|
--	{ ID id-EDCH-FDD-InformationResponse	CRITICALITY ignore	EXTENSION EDCH-FDD-InformationResponse			PRESENCE optional	},
--	...
--}

NonCombiningOrFirstRL-RL-SetupFailureFDD ::= SEQUENCE {
	dCH-InformationResponse					DCH-InformationResponse,
--	iE-Extensions							ProtocolExtensionContainer { { NonCombiningOrFirstRLItem-RL-SetupFailureFDD-ExtIEs} } OPTIONAL,
	iE-Extensions							ProtocolExtensionContainer OPTIONAL,
	...
}

--NonCombiningOrFirstRLItem-RL-SetupFailureFDD-ExtIEs RNSAP-PROTOCOL-EXTENSION ::= {
--	{ ID id-EDCH-FDD-InformationResponse	CRITICALITY ignore	EXTENSION EDCH-FDD-InformationResponse			PRESENCE optional	},
--	...
--}

--RadioLinkSetupFailureFDD-Extensions RNSAP-PROTOCOL-EXTENSION ::= {
--	...
--}

-- **************************************************************
--
-- RADIO LINK SETUP FAILURE TDD
--
-- **************************************************************

--RadioLinkSetupFailureTDD ::= SEQUENCE {
--	protocolIEs                     ProtocolIE-Container       {{RadioLinkSetupFailureTDD-IEs}},
--	protocolExtensions              ProtocolExtensionContainer {{RadioLinkSetupFailureTDD-Extensions}}                   OPTIONAL,
--	...
--}
RadioLinkSetupFailureTDD ::= SEQUENCE {
	protocolIEs                     ProtocolIE-Container,
	protocolExtensions              ProtocolExtensionContainer OPTIONAL,
	...
}

--RadioLinkSetupFailureTDD-IEs RNSAP-PROTOCOL-IES ::= {
--	{ ID id-CauseLevel-RL-SetupFailureTDD	CRITICALITY ignore	TYPE CauseLevel-RL-SetupFailureTDD		PRESENCE mandatory }|
--	{ ID id-CriticalityDiagnostics			CRITICALITY ignore	TYPE CriticalityDiagnostics			PRESENCE optional	},
--	...
--}

CauseLevel-RL-SetupFailureTDD ::= CHOICE {
	generalCause		GeneralCauseList-RL-SetupFailureTDD,
	rLSpecificCause		RLSpecificCauseList-RL-SetupFailureTDD,
	...
}

GeneralCauseList-RL-SetupFailureTDD ::= SEQUENCE {
	cause						Cause,
--	iE-Extensions				ProtocolExtensionContainer { { GeneralCauseItem-RL-SetupFailureTDD-ExtIEs} }		OPTIONAL,
	iE-Extensions				ProtocolExtensionContainer OPTIONAL,
	...
}

--GeneralCauseItem-RL-SetupFailureTDD-ExtIEs RNSAP-PROTOCOL-EXTENSION ::= {
--	...
--}

RLSpecificCauseList-RL-SetupFailureTDD ::= SEQUENCE {
	unsuccessful-RL-InformationRespItem-RL-SetupFailureTDD	Unsuccessful-RL-InformationRespItem-RL-SetupFailureTDD,
--	iE-Extensions											ProtocolExtensionContainer { { RLSpecificCauseItem-RL-SetupFailureTDD-ExtIEs} }		OPTIONAL,
	iE-Extensions											ProtocolExtensionContainer OPTIONAL,
	...
}

--RLSpecificCauseItem-RL-SetupFailureTDD-ExtIEs RNSAP-PROTOCOL-EXTENSION ::= {
--	...
--}

--Unsuccessful-RL-InformationRespItem-RL-SetupFailureTDD ::= ProtocolIE-Single-Container { {Unsuccessful-RL-InformationRespItemIE-RL-SetupFailureTDD} }
Unsuccessful-RL-InformationRespItem-RL-SetupFailureTDD ::= ProtocolIE-Single-Container

--Unsuccessful-RL-InformationRespItemIE-RL-SetupFailureTDD RNSAP-PROTOCOL-IES ::= {
--	{ ID	id-UnsuccessfulRL-InformationResponse-RL-SetupFailureTDD		CRITICALITY	ignore 		TYPE 	UnsuccessfulRL-InformationResponse-RL-SetupFailureTDD		PRESENCE	mandatory	}
--}

UnsuccessfulRL-InformationResponse-RL-SetupFailureTDD ::= SEQUENCE {
	rL-ID						RL-ID,
	cause						Cause,
--	iE-Extensions					ProtocolExtensionContainer { {UnsuccessfulRL-InformationResponse-RL-SetupFailureTDD-ExtIEs} } OPTIONAL,
	iE-Extensions					ProtocolExtensionContainer OPTIONAL,
	...
}

--UnsuccessfulRL-InformationResponse-RL-SetupFailureTDD-ExtIEs RNSAP-PROTOCOL-EXTENSION ::= {
--	...
--}

--RadioLinkSetupFailureTDD-Extensions RNSAP-PROTOCOL-EXTENSION ::= {
--	...
--}

-- **************************************************************
--
-- RADIO LINK ADDITION REQUEST FDD
--
-- **************************************************************

--RadioLinkAdditionRequestFDD ::= SEQUENCE {
--	protocolIEs                     ProtocolIE-Container       {{RadioLinkAdditionRequestFDD-IEs}},
--	protocolExtensions              ProtocolExtensionContainer {{RadioLinkAdditionRequestFDD-Extensions}}                   OPTIONAL,
--	...
--}
RadioLinkAdditionRequestFDD ::= SEQUENCE {
	protocolIEs                     ProtocolIE-Container,
	protocolExtensions              ProtocolExtensionContainer OPTIONAL,
	...
}
--RadioLinkAdditionRequestFDD-IEs RNSAP-PROTOCOL-IES ::= {
--	{ ID id-UL-SIRTarget				CRITICALITY reject	TYPE UL-SIR					PRESENCE mandatory	} |
--	{ ID id-RL-InformationList-RL-AdditionRqstFDD	CRITICALITY notify	TYPE RL-InformationList-RL-AdditionRqstFDD	PRESENCE mandatory	}|
--	{ ID id-Active-Pattern-Sequence-Information	CRITICALITY reject	TYPE Active-Pattern-Sequence-Information	 PRESENCE optional },
--	...
--}

--RL-InformationList-RL-AdditionRqstFDD			::= SEQUENCE (SIZE (1..maxNrOfRLs-1)) OF ProtocolIE-Single-Container { {RL-Information-RL-AdditionRqstFDD-IEs} }
RL-InformationList-RL-AdditionRqstFDD			::= SEQUENCE (SIZE (1..15)) OF ProtocolIE-Single-Container

--RL-Information-RL-AdditionRqstFDD-IEs RNSAP-PROTOCOL-IES ::= {
--	{ ID id-RL-Information-RL-AdditionRqstFDD	CRITICALITY notify	TYPE RL-Information-RL-AdditionRqstFDD		PRESENCE mandatory	}
--}

RL-Information-RL-AdditionRqstFDD ::= SEQUENCE {
	rL-ID							RL-ID,
	c-ID							C-ID,
	frameOffset						FrameOffset,
	chipOffset						ChipOffset,
	diversityControlField			DiversityControlField,
	primaryCPICH-EcNo				PrimaryCPICH-EcNo		OPTIONAL,
	not-Used-sSDT-CellID			NULL			OPTIONAL,
	transmitDiversityIndicator		TransmitDiversityIndicator		OPTIONAL,
--	iE-Extensions					ProtocolExtensionContainer { {RL-Information-RL-AdditionRqstFDD-ExtIEs} } OPTIONAL,
	iE-Extensions					ProtocolExtensionContainer OPTIONAL,
	...
}

--RL-Information-RL-AdditionRqstFDD-ExtIEs RNSAP-PROTOCOL-EXTENSION ::= {
--	{ ID id-DLReferencePower	CRITICALITY ignore		EXTENSION	DL-Power		PRESENCE optional}|
--	{ ID id-Enhanced-PrimaryCPICH-EcNo				CRITICALITY ignore			EXTENSION Enhanced-PrimaryCPICH-EcNo		PRESENCE optional	}|
--	{ ID id-RL-Specific-DCH-Info		CRITICALITY	ignore		EXTENSION 	RL-Specific-DCH-Info	PRESENCE 	optional	}|
--	{ ID id-DelayedActivation CRITICALITY reject EXTENSION DelayedActivation PRESENCE optional }|
--	{ ID id-RL-Specific-EDCH-Information			CRITICALITY reject		EXTENSION RL-Specific-EDCH-Information 			PRESENCE optional }|
--	{ ID id-EDCH-RL-Indication						CRITICALITY reject		EXTENSION EDCH-RL-Indication						PRESENCE optional }|
--	{ ID id-SynchronisationIndicator				CRITICALITY ignore		EXTENSION SynchronisationIndicator				PRESENCE optional},
--	...
--}

--RadioLinkAdditionRequestFDD-Extensions RNSAP-PROTOCOL-EXTENSION ::= {
--	{ ID id-DPC-Mode									CRITICALITY reject	EXTENSION DPC-Mode													PRESENCE optional }|
--	{ ID id-Permanent-NAS-UE-Identity					CRITICALITY ignore	EXTENSION Permanent-NAS-UE-Identity							PRESENCE optional }|
--		{ ID id-Serving-EDCHRL-Id						CRITICALITY reject	EXTENSION EDCH-Serving-RL															PRESENCE conditional }|
	-- This IE is present if RL Specific E-DCHInformation IE is present.
--	{ ID id-Initial-DL-DPCH-TimingAdjustment-Allowed	CRITICALITY ignore	EXTENSION Initial-DL-DPCH-TimingAdjustment-Allowed		PRESENCE optional },
--	...
--}

-- **************************************************************
--
-- RADIO LINK ADDITION REQUEST TDD
--
-- **************************************************************

--RadioLinkAdditionRequestTDD ::= SEQUENCE {
--	protocolIEs                     ProtocolIE-Container       {{RadioLinkAdditionRequestTDD-IEs}},
--	protocolExtensions              ProtocolExtensionContainer {{RadioLinkAdditionRequestTDD-Extensions}}                   OPTIONAL,
--	...
--}
RadioLinkAdditionRequestTDD ::= SEQUENCE {
	protocolIEs                     ProtocolIE-Container,
	protocolExtensions              ProtocolExtensionContainer OPTIONAL,
	...
}
--RadioLinkAdditionRequestTDD-IEs RNSAP-PROTOCOL-IES ::= {
--	{ ID id-RL-Information-RL-AdditionRqstTDD	CRITICALITY reject	TYPE RL-Information-RL-AdditionRqstTDD		PRESENCE mandatory	},
--	...
--}

RL-Information-RL-AdditionRqstTDD ::= SEQUENCE {
	rL-ID							RL-ID,
	c-ID							C-ID,
	frameOffset						FrameOffset,
	diversityControlField			DiversityControlField,
	primaryCCPCH-RSCP				PrimaryCCPCH-RSCP		OPTIONAL,
	dL-TimeSlot-ISCP-Info			DL-TimeSlot-ISCP-Info	OPTIONAL,
	--for 3.84Mcps TDD only
--	iE-Extensions					ProtocolExtensionContainer { {RL-Information-RL-AdditionRqstTDD-ExtIEs} } OPTIONAL,
	iE-Extensions					ProtocolExtensionContainer OPTIONAL,
	...
}

--RL-Information-RL-AdditionRqstTDD-ExtIEs RNSAP-PROTOCOL-EXTENSION ::= {
--	{ ID id-DL-Timeslot-ISCP-LCR-Information-RL-AdditionRqstTDD	CRITICALITY reject		EXTENSION 	DL-TimeSlot-ISCP-LCR-Information		PRESENCE optional	}|
	--for 1.28Mcps TDD only
--  { ID id-RL-Specific-DCH-Info		CRITICALITY	ignore		EXTENSION 	RL-Specific-DCH-Info	PRESENCE 	optional	}|
--	{ ID id-DelayedActivation CRITICALITY reject EXTENSION DelayedActivation PRESENCE optional }|
--	{ ID id-UL-Synchronisation-Parameters-LCR			CRITICALITY	reject		EXTENSION 	UL-Synchronisation-Parameters-LCR		PRESENCE 	optional	}|
	-- Mandatory for 1.28Mcps TDD, Not Applicable to 3.84Mcps TDD
--	{ ID id-PrimaryCCPCH-RSCP-Delta		CRITICALITY	ignore		EXTENSION 	PrimaryCCPCH-RSCP-Delta		PRESENCE 	optional	},
--	...
--}

--RadioLinkAdditionRequestTDD-Extensions RNSAP-PROTOCOL-EXTENSION ::= {
--	{ ID id-Permanent-NAS-UE-Identity				CRITICALITY ignore			EXTENSION Permanent-NAS-UE-Identity		PRESENCE optional	}|
--	{ ID id-UL-CCTrCH-InformationList-RL-AdditionRqstTDD	CRITICALITY notify	EXTENSION UL-CCTrCH-InformationList-RL-AdditionRqstTDD	PRESENCE optional	} |
--	{ ID id-DL-CCTrCH-InformationList-RL-AdditionRqstTDD	CRITICALITY notify	EXTENSION DL-CCTrCH-InformationList-RL-AdditionRqstTDD 	PRESENCE optional	},
--	...
--}

--UL-CCTrCH-InformationList-RL-AdditionRqstTDD	::= SEQUENCE (SIZE (1..maxNrOfCCTrCHs)) OF ProtocolIE-Single-Container { {UL-CCTrCH-InformationItemIEs-RL-AdditionRqstTDD} }
UL-CCTrCH-InformationList-RL-AdditionRqstTDD	::= SEQUENCE (SIZE (1..16)) OF ProtocolIE-Single-Container

--UL-CCTrCH-InformationItemIEs-RL-AdditionRqstTDD RNSAP-PROTOCOL-IES ::= {
--	{ ID id-UL-CCTrCH-InformationItem-RL-AdditionRqstTDD	CRITICALITY notify	TYPE UL-CCTrCH-InformationItem-RL-AdditionRqstTDD 	PRESENCE optional},
--	...
--}

UL-CCTrCH-InformationItem-RL-AdditionRqstTDD ::= SEQUENCE {
	cCTrCH-ID					CCTrCH-ID,
	uplinkStepSizeLCR			TDD-TPC-UplinkStepSize-LCR    OPTIONAL, 
	-- Applicable to 1.28Mcps TDD only
--	iE-Extensions				ProtocolExtensionContainer { {UL-CCTrCH-InformationItem-RL-AdditionRqstTDD-ExtIEs} } OPTIONAL,
	iE-Extensions				ProtocolExtensionContainer OPTIONAL,
	...
}

--UL-CCTrCH-InformationItem-RL-AdditionRqstTDD-ExtIEs RNSAP-PROTOCOL-EXTENSION ::= {
--	...
--}

--DL-CCTrCH-InformationList-RL-AdditionRqstTDD	::= SEQUENCE (SIZE (1..maxNrOfCCTrCHs)) OF ProtocolIE-Single-Container { {DL-CCTrCH-InformationItemIEs-RL-AdditionRqstTDD} }
DL-CCTrCH-InformationList-RL-AdditionRqstTDD	::= SEQUENCE (SIZE (1..16)) OF ProtocolIE-Single-Container

--DL-CCTrCH-InformationItemIEs-RL-AdditionRqstTDD RNSAP-PROTOCOL-IES ::= {
--	{ ID id-DL-CCTrCH-InformationItem-RL-AdditionRqstTDD	CRITICALITY notify	TYPE DL-CCTrCH-InformationItem-RL-AdditionRqstTDD	PRESENCE optional},
--	...
--}

DL-CCTrCH-InformationItem-RL-AdditionRqstTDD ::= SEQUENCE {
	cCTrCH-ID					CCTrCH-ID,
	downlinkStepSize			TDD-TPC-DownlinkStepSize   OPTIONAL,
--	iE-Extensions				ProtocolExtensionContainer { {DL-CCTrCH-InformationItem-RL-AdditionRqstTDD-ExtIEs} } OPTIONAL,
	iE-Extensions				ProtocolExtensionContainer OPTIONAL,
	...
}

--DL-CCTrCH-InformationItem-RL-AdditionRqstTDD-ExtIEs RNSAP-PROTOCOL-EXTENSION ::= {
--	...
--}

-- **************************************************************
--
-- RADIO LINK ADDITION RESPONSE FDD
--
-- **************************************************************

--RadioLinkAdditionResponseFDD ::= SEQUENCE {
--	protocolIEs                     ProtocolIE-Container       {{RadioLinkAdditionResponseFDD-IEs}},
--	protocolExtensions              ProtocolExtensionContainer {{RadioLinkAdditionResponseFDD-Extensions}}                   OPTIONAL,
--	...
--}
RadioLinkAdditionResponseFDD ::= SEQUENCE {
	protocolIEs                     ProtocolIE-Container,
	protocolExtensions              ProtocolExtensionContainer OPTIONAL,
	...
}

--RadioLinkAdditionResponseFDD-IEs RNSAP-PROTOCOL-IES ::= {
--	{ ID id-RL-InformationResponseList-RL-AdditionRspFDD	CRITICALITY ignore	TYPE RL-InformationResponseList-RL-AdditionRspFDD 		PRESENCE mandatory	} |
--	{ ID id-CriticalityDiagnostics			CRITICALITY ignore	TYPE CriticalityDiagnostics			PRESENCE optional	},
--	...
--}

--RL-InformationResponseList-RL-AdditionRspFDD 		::= SEQUENCE (SIZE (1..maxNrOfRLs-1)) OF ProtocolIE-Single-Container { {RL-InformationResponseItemIEs-RL-AdditionRspFDD} }
RL-InformationResponseList-RL-AdditionRspFDD 		::= SEQUENCE (SIZE (1..15)) OF ProtocolIE-Single-Container

--RL-InformationResponseItemIEs-RL-AdditionRspFDD RNSAP-PROTOCOL-IES ::= {
--	{ ID id-RL-InformationResponseItem-RL-AdditionRspFDD		CRITICALITY ignore	TYPE RL-InformationResponseItem-RL-AdditionRspFDD 	PRESENCE mandatory	}
--}

RL-InformationResponseItem-RL-AdditionRspFDD ::= SEQUENCE {
	rL-ID							RL-ID,
	rL-Set-ID						RL-Set-ID,
	uRA-Information					URA-Information		OPTIONAL,
	sAI								SAI,
	gA-Cell							GA-Cell		OPTIONAL,
	gA-AccessPointPosition			GA-AccessPointPosition	OPTIONAL,
	received-total-wide-band-power	Received-total-wide-band-power,
	not-Used-secondary-CCPCH-Info			NULL		OPTIONAL,
	dl-CodeInformation				DL-CodeInformationList-RL-AdditionRspFDD,
	diversityIndication				DiversityIndication-RL-AdditionRspFDD, 

	sSDT-SupportIndicator				SSDT-SupportIndicator,
	minUL-SIR							UL-SIR,
	maxUL-SIR							UL-SIR,
	closedlooptimingadjustmentmode		Closedlooptimingadjustmentmode	OPTIONAL,
	maximumAllowedULTxPower				MaximumAllowedULTxPower,
	maximumDLTxPower					DL-Power,
	minimumDLTxPower					DL-Power,
	neighbouring-UMTS-CellInformation	Neighbouring-UMTS-CellInformation	OPTIONAL,
	neighbouring-GSM-CellInformation	Neighbouring-GSM-CellInformation OPTIONAL,
	pC-Preamble							PC-Preamble,
	sRB-Delay							SRB-Delay,
	primaryCPICH-Power					PrimaryCPICH-Power,
--	iE-Extensions						ProtocolExtensionContainer { {RL-InformationResponseItem-RL-AdditionRspFDD-ExtIEs} } OPTIONAL,
	iE-Extensions						ProtocolExtensionContainer OPTIONAL,
	...
}

--RL-InformationResponseItem-RL-AdditionRspFDD-ExtIEs RNSAP-PROTOCOL-EXTENSION ::= {
--	{ ID id-GA-CellAdditionalShapes					CRITICALITY ignore	EXTENSION GA-CellAdditionalShapes							PRESENCE optional }|
--	{ ID id-DL-PowerBalancing-ActivationIndicator	CRITICALITY ignore	EXTENSION DL-PowerBalancing-ActivationIndicator		PRESENCE optional}|
--	{ ID id-HCS-Prio								CRITICALITY ignore	EXTENSION HCS-Prio												PRESENCE optional }|
--	{ ID id-Active-MBMS-Bearer-ServiceFDD-PFL			CRITICALITY ignore EXTENSION Active-MBMS-Bearer-Service-ListFDD-PFL				PRESENCE optional }|
--	{ ID id-EDCH-RLSet-Id							CRITICALITY ignore EXTENSION RL-Set-ID												PRESENCE optional }|
--	{ ID id-EDCH-FDD-DL-ControlChannelInformation	CRITICALITY ignore EXTENSION EDCH-FDD-DL-ControlChannelInformation			PRESENCE optional }|
--	{ ID id-Initial-DL-DPCH-TimingAdjustment		CRITICALITY ignore EXTENSION DL-DPCH-TimingAdjustment							PRESENCE optional },
--	...
--}

--DL-CodeInformationList-RL-AdditionRspFDD ::= ProtocolIE-Single-Container {{ DL-CodeInformationListIEs-RL-AdditionRspFDD }}
DL-CodeInformationList-RL-AdditionRspFDD ::= ProtocolIE-Single-Container

--DL-CodeInformationListIEs-RL-AdditionRspFDD RNSAP-PROTOCOL-IES ::= {
--	{ ID id-FDD-DL-CodeInformation   CRITICALITY ignore	TYPE FDD-DL-CodeInformation		PRESENCE mandatory }
--}

DiversityIndication-RL-AdditionRspFDD ::= CHOICE {
	combining						Combining-RL-AdditionRspFDD,
	nonCombining					NonCombining-RL-AdditionRspFDD
}

Combining-RL-AdditionRspFDD ::= SEQUENCE {
	rL-ID						RL-ID,
--	iE-Extensions				ProtocolExtensionContainer { { CombiningItem-RL-AdditionRspFDD-ExtIEs} } OPTIONAL,
	iE-Extensions				ProtocolExtensionContainer OPTIONAL,
	...
}

--CombiningItem-RL-AdditionRspFDD-ExtIEs RNSAP-PROTOCOL-EXTENSION ::= {
--	{ ID id-DCH-InformationResponse			CRITICALITY ignore	EXTENSION DCH-InformationResponse			PRESENCE optional	}|
--	{ ID id-EDCH-FDD-InformationResponse	CRITICALITY ignore	EXTENSION EDCH-FDD-InformationResponse			PRESENCE optional	},
--	...
--}

NonCombining-RL-AdditionRspFDD ::= SEQUENCE {
	dCH-InformationResponse					DCH-InformationResponse,
--	iE-Extensions								ProtocolExtensionContainer { { NonCombiningItem-RL-AdditionRspFDD-ExtIEs} } OPTIONAL,
	iE-Extensions								ProtocolExtensionContainer OPTIONAL,
	...
}

--NonCombiningItem-RL-AdditionRspFDD-ExtIEs RNSAP-PROTOCOL-EXTENSION ::= {
--	{ ID id-EDCH-FDD-InformationResponse	CRITICALITY ignore	EXTENSION EDCH-FDD-InformationResponse			PRESENCE optional	},
--	...
--}

--RadioLinkAdditionResponseFDD-Extensions RNSAP-PROTOCOL-EXTENSION ::= {
--	...
--}

-- **************************************************************
--
-- RADIO LINK ADDITION RESPONSE TDD
--
-- **************************************************************

--RadioLinkAdditionResponseTDD ::= SEQUENCE {
--	protocolIEs                     ProtocolIE-Container       {{RadioLinkAdditionResponseTDD-IEs}},
--	protocolExtensions              ProtocolExtensionContainer {{RadioLinkAdditionResponseTDD-Extensions}}                   OPTIONAL,
--	...
--}
RadioLinkAdditionResponseTDD ::= SEQUENCE {
	protocolIEs                     ProtocolIE-Container,
	protocolExtensions              ProtocolExtensionContainer OPTIONAL,
	...
}
--RadioLinkAdditionResponseTDD-IEs RNSAP-PROTOCOL-IES ::= {
--	{ ID id-RL-InformationResponse-RL-AdditionRspTDD		CRITICALITY ignore	TYPE RL-InformationResponse-RL-AdditionRspTDD 	PRESENCE optional	} |
	--Mandatory for 3.84Mcps TDD only
--	{ ID id-CriticalityDiagnostics			CRITICALITY ignore	TYPE CriticalityDiagnostics			PRESENCE optional	},
--	...
--}

RL-InformationResponse-RL-AdditionRspTDD ::= SEQUENCE {
	rL-ID								RL-ID,
	uRA-Information						URA-Information		OPTIONAL,
	sAI									SAI,
	gA-Cell								GA-Cell		OPTIONAL,
	gA-AccessPointPosition				GA-AccessPointPosition	OPTIONAL,
	ul-TimeSlot-ISCP-Info				UL-TimeSlot-ISCP-Info,
	minUL-SIR							UL-SIR,
	maxUL-SIR							UL-SIR,
	maximumAllowedULTxPower				MaximumAllowedULTxPower,
	maximumDLTxPower					DL-Power,
	minimumDLTxPower					DL-Power,
	pCCPCH-Power						PCCPCH-Power,
	timingAdvanceApplied				TimingAdvanceApplied,
	alphaValue							AlphaValue,
	ul-PhysCH-SF-Variation				UL-PhysCH-SF-Variation,
	synchronisationConfiguration		SynchronisationConfiguration,
	secondary-CCPCH-Info-TDD			Secondary-CCPCH-Info-TDD						OPTIONAL,
	ul-CCTrCHInformation				UL-CCTrCHInformationList-RL-AdditionRspTDD		OPTIONAL,
	dl-CCTrCHInformation				DL-CCTrCHInformationList-RL-AdditionRspTDD		OPTIONAL,
	dCH-Information						DCH-Information-RL-AdditionRspTDD				OPTIONAL,
	dSCH-InformationResponse			DSCH-InformationResponse-RL-AdditionRspTDD		OPTIONAL,
	uSCH-InformationResponse			USCH-InformationResponse-RL-AdditionRspTDD		OPTIONAL,
	neighbouring-UMTS-CellInformation	Neighbouring-UMTS-CellInformation 	OPTIONAL,
	neighbouring-GSM-CellInformation	Neighbouring-GSM-CellInformation OPTIONAL,
--	iE-Extensions						ProtocolExtensionContainer { {RL-InformationResponse-RL-AdditionRspTDD-ExtIEs} } OPTIONAL,
	iE-Extensions						ProtocolExtensionContainer OPTIONAL,
	...
}

--RL-InformationResponse-RL-AdditionRspTDD-ExtIEs RNSAP-PROTOCOL-EXTENSION ::= {
--	{ ID id-GA-CellAdditionalShapes			CRITICALITY	ignore	EXTENSION	GA-CellAdditionalShapes		PRESENCE optional }|
--	{ ID id-HCS-Prio			CRITICALITY	ignore	EXTENSION	HCS-Prio		PRESENCE optional },
--	...
--}

--UL-CCTrCHInformationList-RL-AdditionRspTDD ::= ProtocolIE-Single-Container {{UL-CCTrCHInformationListIEs-RL-AdditionRspTDD}}
UL-CCTrCHInformationList-RL-AdditionRspTDD ::= ProtocolIE-Single-Container

--UL-CCTrCHInformationListIEs-RL-AdditionRspTDD RNSAP-PROTOCOL-IES ::= {
--	{ ID id-UL-CCTrCH-InformationListIE-RL-AdditionRspTDD   CRITICALITY ignore	TYPE UL-CCTrCHInformationListIE-RL-AdditionRspTDD		PRESENCE mandatory }
--}

--UL-CCTrCHInformationListIE-RL-AdditionRspTDD ::= SEQUENCE (SIZE (1..maxNrOfCCTrCHs)) OF UL-CCTrCHInformationItem-RL-AdditionRspTDD
UL-CCTrCHInformationListIE-RL-AdditionRspTDD ::= SEQUENCE (SIZE (1..16)) OF UL-CCTrCHInformationItem-RL-AdditionRspTDD

UL-CCTrCHInformationItem-RL-AdditionRspTDD ::= SEQUENCE {
	cCTrCH-ID					CCTrCH-ID,
	ul-DPCH-Information				UL-DPCH-InformationList-RL-AdditionRspTDD		OPTIONAL,
--	iE-Extensions					ProtocolExtensionContainer { {UL-CCTrCHInformationItem-RL-AdditionRspTDD-ExtIEs} } OPTIONAL,
	iE-Extensions					ProtocolExtensionContainer OPTIONAL,
	...
}

--UL-CCTrCHInformationItem-RL-AdditionRspTDD-ExtIEs RNSAP-PROTOCOL-EXTENSION ::= {
--	...
--}

--UL-DPCH-InformationList-RL-AdditionRspTDD ::= ProtocolIE-Single-Container { {UL-DPCH-InformationListIEs-RL-AdditionRspTDD} }
UL-DPCH-InformationList-RL-AdditionRspTDD ::= ProtocolIE-Single-Container

--UL-DPCH-InformationListIEs-RL-AdditionRspTDD RNSAP-PROTOCOL-IES ::= {
--	{ ID id-UL-DPCH-InformationItem-RL-AdditionRspTDD		CRITICALITY ignore	TYPE UL-DPCH-InformationItem-RL-AdditionRspTDD  PRESENCE mandatory	}
--}

UL-DPCH-InformationItem-RL-AdditionRspTDD ::= SEQUENCE {
	repetitionPeriod				RepetitionPeriod,
	repetitionLength				RepetitionLength,
	tDD-DPCHOffset					TDD-DPCHOffset,
	uL-Timeslot-Information			UL-Timeslot-Information,
--	iE-Extensions					ProtocolExtensionContainer { {UL-DPCH-InformationItem-RL-AdditionRspTDD-ExtIEs} } OPTIONAL,
	iE-Extensions					ProtocolExtensionContainer OPTIONAL,
	...
}

--UL-DPCH-InformationItem-RL-AdditionRspTDD-ExtIEs RNSAP-PROTOCOL-EXTENSION ::= {
--	...
--}

--DL-CCTrCHInformationList-RL-AdditionRspTDD ::= ProtocolIE-Single-Container {{DL-CCTrCHInformationListIEs-RL-AdditionRspTDD}}
DL-CCTrCHInformationList-RL-AdditionRspTDD ::= ProtocolIE-Single-Container 

--DL-CCTrCHInformationListIEs-RL-AdditionRspTDD RNSAP-PROTOCOL-IES ::= {
--	{ ID id-DL-CCTrCH-InformationListIE-RL-AdditionRspTDD   CRITICALITY ignore	TYPE DL-CCTrCHInformationListIE-RL-AdditionRspTDD		PRESENCE mandatory }
--}

--DL-CCTrCHInformationListIE-RL-AdditionRspTDD ::= SEQUENCE (SIZE (1..maxNrOfCCTrCHs)) OF DL-CCTrCHInformationItem-RL-AdditionRspTDD
DL-CCTrCHInformationListIE-RL-AdditionRspTDD ::= SEQUENCE (SIZE (1..16)) OF DL-CCTrCHInformationItem-RL-AdditionRspTDD

DL-CCTrCHInformationItem-RL-AdditionRspTDD ::= SEQUENCE {
	cCTrCH-ID					CCTrCH-ID,
	dl-DPCH-Information				DL-DPCH-InformationList-RL-AdditionRspTDD		OPTIONAL,
--	iE-Extensions					ProtocolExtensionContainer { {DL-CCTrCHInformationItem-RL-AdditionRspTDD-ExtIEs} } OPTIONAL,
	iE-Extensions					ProtocolExtensionContainer OPTIONAL,
	...
}

--DL-CCTrCHInformationItem-RL-AdditionRspTDD-ExtIEs RNSAP-PROTOCOL-EXTENSION ::= {
--	{ ID id-CCTrCH-Maximum-DL-Power-RL-AdditionRspTDD		CRITICALITY ignore		EXTENSION  DL-Power    PRESENCE optional	}|
 -- this is a DCH type CCTrCH power
--	{ ID id-CCTrCH-Minimum-DL-Power-RL-AdditionRspTDD		CRITICALITY ignore		EXTENSION  DL-Power    PRESENCE optional	},
 -- this is a DCH type CCTrCH power
--	...
--}

--DL-DPCH-InformationList-RL-AdditionRspTDD ::= ProtocolIE-Single-Container { {DL-DPCH-InformationListIEs-RL-AdditionRspTDD} }
DL-DPCH-InformationList-RL-AdditionRspTDD ::= ProtocolIE-Single-Container

--DL-DPCH-InformationListIEs-RL-AdditionRspTDD RNSAP-PROTOCOL-IES ::= {
--	{ ID id-DL-DPCH-InformationItem-RL-AdditionRspTDD		CRITICALITY ignore	TYPE DL-DPCH-InformationItem-RL-AdditionRspTDD  PRESENCE mandatory	}
--}

DL-DPCH-InformationItem-RL-AdditionRspTDD ::= SEQUENCE {
	repetitionPeriod				RepetitionPeriod,
	repetitionLength				RepetitionLength,
	tDD-DPCHOffset					TDD-DPCHOffset,
	dL-Timeslot-Information			DL-Timeslot-Information,
--	iE-Extensions					ProtocolExtensionContainer { {DL-DPCH-InformationItem-RL-AdditionRspTDD-ExtIEs} } OPTIONAL,
	iE-Extensions					ProtocolExtensionContainer OPTIONAL,
	...
}

--DL-DPCH-InformationItem-RL-AdditionRspTDD-ExtIEs RNSAP-PROTOCOL-EXTENSION ::= {
--	...
--}

DCH-Information-RL-AdditionRspTDD ::= SEQUENCE {
	diversityIndication					DiversityIndication-RL-AdditionRspTDD,

--	iE-Extensions					ProtocolExtensionContainer { { DCH-Information-RL-AdditionRspTDD-ExtIEs} } OPTIONAL,
	iE-Extensions					ProtocolExtensionContainer OPTIONAL,
	...
}

--DCH-Information-RL-AdditionRspTDD-ExtIEs RNSAP-PROTOCOL-EXTENSION ::= {
--	...
--}

DiversityIndication-RL-AdditionRspTDD ::= CHOICE {
	combining		Combining-RL-AdditionRspTDD,
	nonCombining	NonCombining-RL-AdditionRspTDD
}

Combining-RL-AdditionRspTDD	::= SEQUENCE {
	rL-ID						RL-ID,
--	iE-Extensions				ProtocolExtensionContainer { { CombiningItem-RL-AdditionRspTDD-ExtIEs} } OPTIONAL,
	iE-Extensions				ProtocolExtensionContainer OPTIONAL,
	...
}

--CombiningItem-RL-AdditionRspTDD-ExtIEs RNSAP-PROTOCOL-EXTENSION ::= {
--	{ ID id-DCH-InformationResponse			CRITICALITY ignore	EXTENSION DCH-InformationResponse			PRESENCE optional	},
--	...
--}

NonCombining-RL-AdditionRspTDD	::= SEQUENCE {
	dCH-InformationResponse		DCH-InformationResponse,
--	iE-Extensions					ProtocolExtensionContainer { { NonCombiningItem-RL-AdditionRspTDD-ExtIEs} } OPTIONAL,
	iE-Extensions					ProtocolExtensionContainer OPTIONAL,
	...
}

--NonCombiningItem-RL-AdditionRspTDD-ExtIEs RNSAP-PROTOCOL-EXTENSION ::= {
--	...
--}

--DSCH-InformationResponse-RL-AdditionRspTDD ::= ProtocolIE-Single-Container {{DSCH-InformationListIEs-RL-AdditionRspTDD}}
DSCH-InformationResponse-RL-AdditionRspTDD ::= ProtocolIE-Single-Container

--DSCH-InformationListIEs-RL-AdditionRspTDD RNSAP-PROTOCOL-IES ::= {
--	{ ID id-DSCH-InformationListIE-RL-AdditionRspTDD	CRITICALITY ignore	TYPE DSCH-InformationListIE-RL-AdditionRspTDD		PRESENCE mandatory }
--}

--DSCH-InformationListIE-RL-AdditionRspTDD ::= SEQUENCE (SIZE(0..maxNoOfDSCHs)) OF DSCHInformationItem-RL-AdditionRspTDD 
DSCH-InformationListIE-RL-AdditionRspTDD ::= SEQUENCE (SIZE(0..10)) OF DSCHInformationItem-RL-AdditionRspTDD 

DSCHInformationItem-RL-AdditionRspTDD ::= SEQUENCE {
	dsch-ID					DSCH-ID,
	transportFormatManagement	TransportFormatManagement,
	dSCH-FlowControlInformation		DSCH-FlowControlInformation,
	diversityIndication		DiversityIndication-RL-AdditionRspTDD2 OPTIONAL,
	-- diversityIndication present, if CHOICE = nonCombining
--	iE-Extensions			ProtocolExtensionContainer { {DSCHInformationItem-RL-AdditionRspTDD-ExtIEs} } OPTIONAL,
	iE-Extensions			ProtocolExtensionContainer OPTIONAL,
	...
}

--DSCHInformationItem-RL-AdditionRspTDD-ExtIEs RNSAP-PROTOCOL-EXTENSION ::= {
--	...
--}

DiversityIndication-RL-AdditionRspTDD2 ::= SEQUENCE {
	bindingID				BindingID	OPTIONAL,
	transportLayerAddress	TransportLayerAddress	OPTIONAL,
--	iE-Extensions			ProtocolExtensionContainer { {DiversityIndication-RL-AdditionRspTDD2-ExtIEs} } OPTIONAL,
	iE-Extensions			ProtocolExtensionContainer OPTIONAL,
	...
}
--DiversityIndication-RL-AdditionRspTDD2-ExtIEs RNSAP-PROTOCOL-EXTENSION ::= {
--	...
--}

--USCH-InformationResponse-RL-AdditionRspTDD ::= ProtocolIE-Single-Container {{USCH-InformationListIEs-RL-AdditionRspTDD}}
USCH-InformationResponse-RL-AdditionRspTDD ::= ProtocolIE-Single-Container

--USCH-InformationListIEs-RL-AdditionRspTDD RNSAP-PROTOCOL-IES ::= {
--	{ ID id-USCH-InformationListIE-RL-AdditionRspTDD	CRITICALITY ignore	TYPE USCH-InformationListIE-RL-AdditionRspTDD		PRESENCE mandatory }
--}

--USCH-InformationListIE-RL-AdditionRspTDD ::= SEQUENCE (SIZE(0..maxNoOfUSCHs)) OF USCHInformationItem-RL-AdditionRspTDD 
USCH-InformationListIE-RL-AdditionRspTDD ::= SEQUENCE (SIZE(0..10)) OF USCHInformationItem-RL-AdditionRspTDD 

USCHInformationItem-RL-AdditionRspTDD ::= SEQUENCE {
	uSCH-ID					USCH-ID,
	transportFormatManagement	TransportFormatManagement,
	diversityIndication		DiversityIndication-RL-AdditionRspTDD2 OPTIONAL,
	-- diversityIndication present, if CHOICE = nonCombining
--	iE-Extensions			ProtocolExtensionContainer { {USCHInformationItem-RL-AdditionRspTDD-ExtIEs} } OPTIONAL,
	iE-Extensions			ProtocolExtensionContainer OPTIONAL,
	...
}

--USCHInformationItem-RL-AdditionRspTDD-ExtIEs RNSAP-PROTOCOL-EXTENSION ::= {
--	...
--}

--RadioLinkAdditionResponseTDD-Extensions RNSAP-PROTOCOL-EXTENSION ::= {
--	{ ID id-RL-LCR-InformationResponse-RL-AdditionRspTDD	CRITICALITY ignore		EXTENSION 	RL-LCR-InformationResponse-RL-AdditionRspTDD		PRESENCE optional	}|
	--Mandatory for 1.28Mcps TDD only
--	{ ID id-Active-MBMS-Bearer-ServiceTDD-PFL					CRITICALITY ignore		EXTENSION Active-MBMS-Bearer-Service-ListTDD-PFL						PRESENCE optional},
--	...
--}

RL-LCR-InformationResponse-RL-AdditionRspTDD ::= SEQUENCE { 
	rL-ID						RL-ID,
	uRA-Information				URA-Information,
	sAI							SAI,
	gA-Cell						GA-Cell		OPTIONAL,
	gA-AccessPointPosition		GA-AccessPointPosition	OPTIONAL,
	ul-TimeSlot-ISCP-LCR-Info	UL-TimeSlot-ISCP-LCR-Info,
	maxUL-SIR					UL-SIR,
	minUL-SIR					UL-SIR,
	pCCPCH-Power				PCCPCH-Power,
	maximumAllowedULTxPower		MaximumAllowedULTxPower,
	maximumDLTxPower			DL-Power,
	minimumDLTxPower			DL-Power,
	alphaValue					AlphaValue,
	ul-PhysCH-SF-Variation		UL-PhysCH-SF-Variation,
	synchronisationConfiguration		SynchronisationConfiguration,
	secondary-LCR-CCPCH-Info-TDD		Secondary-LCR-CCPCH-Info-TDD						OPTIONAL,
	ul-CCTrCH-LCR-Information			UL-CCTrCH-LCR-InformationList-RL-AdditionRspTDD		OPTIONAL,
	dl-CCTrCH-LCR-Information			DL-CCTrCH-LCR-InformationList-RL-AdditionRspTDD		OPTIONAL,
	dCH-InformationResponse				DCH-InformationResponseList-RL-AdditionRspTDD	OPTIONAL,
	dsch-LCR-InformationResponse		DSCH-LCR-InformationResponse-RL-AdditionRspTDD     OPTIONAL,
	usch-LCR-InformationResponse			USCH-LCR-InformationResponse-RL-AdditionRspTDD     OPTIONAL,
	neighbouring-UMTS-CellInformation			Neighbouring-UMTS-CellInformation               OPTIONAL,
	neighbouring-GSM-CellInformation			Neighbouring-GSM-CellInformation			 OPTIONAL,
--	iE-Extensions								ProtocolExtensionContainer { { RL-LCR-InformationResponseList-RL-AdditionRspTDD-ExtIEs} }		OPTIONAL,
	iE-Extensions								ProtocolExtensionContainer OPTIONAL,
	...
}

--RL-LCR-InformationResponseList-RL-AdditionRspTDD-ExtIEs RNSAP-PROTOCOL-EXTENSION ::= {
--	{ ID id-GA-CellAdditionalShapes		CRITICALITY	ignore	EXTENSION	GA-CellAdditionalShapes			PRESENCE optional }|
--	{ ID id-HCS-Prio					CRITICALITY	ignore	EXTENSION	HCS-Prio						PRESENCE optional }|
--	{ ID id-UL-TimingAdvanceCtrl-LCR	CRITICALITY ignore	EXTENSION	UL-TimingAdvanceCtrl-LCR		PRESENCE optional },
	--Mandatory for 1.28Mcps TDD only
--	...
--}

--UL-CCTrCH-LCR-InformationList-RL-AdditionRspTDD ::= ProtocolIE-Single-Container {{UL-CCTrCH-LCR-InformationListIEs-RL-AdditionRspTDD }}
UL-CCTrCH-LCR-InformationList-RL-AdditionRspTDD ::= ProtocolIE-Single-Container

--UL-CCTrCH-LCR-InformationListIEs-RL-AdditionRspTDD RNSAP-PROTOCOL-IES ::= {
--	{ ID id-UL-CCTrCH-LCR-InformationListIE-RL-AdditionRspTDD   CRITICALITY ignore	TYPE UL-CCTrCH-LCR-InformationListIE-RL-AdditionRspTDD		PRESENCE mandatory }
--}

--UL-CCTrCH-LCR-InformationListIE-RL-AdditionRspTDD ::= SEQUENCE (SIZE (1..maxNrOfCCTrCHsLCR)) OF UL-CCTrCH-LCR-InformationItem-RL-AdditionRspTDD
UL-CCTrCH-LCR-InformationListIE-RL-AdditionRspTDD ::= SEQUENCE (SIZE (1..16)) OF UL-CCTrCH-LCR-InformationItem-RL-AdditionRspTDD

UL-CCTrCH-LCR-InformationItem-RL-AdditionRspTDD ::= SEQUENCE {
	cCTrCH-ID					CCTrCH-ID,
	ul-DPCH-LCR-Information				UL-DPCH-LCR-InformationList-RL-AdditionRspTDD		OPTIONAL,
--	iE-Extensions					ProtocolExtensionContainer { {UL-CCTrCH-LCR-InformationItem-RL-AdditionRspTDD-ExtIEs} } OPTIONAL,
	iE-Extensions					ProtocolExtensionContainer OPTIONAL,
	...
}

--UL-CCTrCH-LCR-InformationItem-RL-AdditionRspTDD-ExtIEs RNSAP-PROTOCOL-EXTENSION ::= {
--	...
--}

--UL-DPCH-LCR-InformationList-RL-AdditionRspTDD ::= ProtocolIE-Single-Container { {UL-DPCH-LCR-InformationListIEs-RL-AdditionRspTDD} }
UL-DPCH-LCR-InformationList-RL-AdditionRspTDD ::= ProtocolIE-Single-Container

--UL-DPCH-LCR-InformationListIEs-RL-AdditionRspTDD RNSAP-PROTOCOL-IES ::= {
--	{ ID id-UL-DPCH-LCR-InformationItem-RL-AdditionRspTDD		CRITICALITY ignore	TYPE UL-DPCH-LCR-InformationItem-RL-AdditionRspTDD  PRESENCE mandatory	}
--}

UL-DPCH-LCR-InformationItem-RL-AdditionRspTDD ::= SEQUENCE {
	repetitionPeriod				RepetitionPeriod,
	repetitionLength				RepetitionLength,
	tDD-DPCHOffset					TDD-DPCHOffset,
	uL-TimeslotLCR-Information		UL-TimeslotLCR-Information,
--	iE-Extensions					ProtocolExtensionContainer { {UL-DPCH-LCR-InformationItem-RL-AdditionRspTDD-ExtIEs} } OPTIONAL,
	iE-Extensions					ProtocolExtensionContainer OPTIONAL,
	...
}

--UL-DPCH-LCR-InformationItem-RL-AdditionRspTDD-ExtIEs RNSAP-PROTOCOL-EXTENSION ::= {
--	...
--}

--DL-CCTrCH-LCR-InformationList-RL-AdditionRspTDD ::= ProtocolIE-Single-Container {{DL-CCTrCH-LCR-InformationListIEs-RL-AdditionRspTDD}}
DL-CCTrCH-LCR-InformationList-RL-AdditionRspTDD ::= ProtocolIE-Single-Container

--DL-CCTrCH-LCR-InformationListIEs-RL-AdditionRspTDD RNSAP-PROTOCOL-IES ::= {
--	{ ID id-DL-CCTrCH-LCR-InformationListIE-RL-AdditionRspTDD   CRITICALITY ignore	TYPE DL-CCTrCH-LCR-InformationListIE-RL-AdditionRspTDD  PRESENCE mandatory }
--}

--DL-CCTrCH-LCR-InformationListIE-RL-AdditionRspTDD ::= SEQUENCE (SIZE (1..maxNrOfCCTrCHsLCR)) OF DL-CCTrCH-LCR-InformationItem-RL-AdditionRspTDD
DL-CCTrCH-LCR-InformationListIE-RL-AdditionRspTDD ::= SEQUENCE (SIZE (1..16)) OF DL-CCTrCH-LCR-InformationItem-RL-AdditionRspTDD

DL-CCTrCH-LCR-InformationItem-RL-AdditionRspTDD ::= SEQUENCE {
	cCTrCH-ID					CCTrCH-ID,
	dl-DPCH-LCR-Information		DL-DPCH-LCR-InformationList-RL-AdditionRspTDD		OPTIONAL,
--	iE-Extensions				ProtocolExtensionContainer { {DL-CCTrCH-LCR-InformationItem-RL-AdditionRspTDD-ExtIEs} } OPTIONAL,
	iE-Extensions				ProtocolExtensionContainer OPTIONAL,
	...
}

--DL-CCTrCH-LCR-InformationItem-RL-AdditionRspTDD-ExtIEs RNSAP-PROTOCOL-EXTENSION ::= {
--	...
--}

--DL-DPCH-LCR-InformationList-RL-AdditionRspTDD ::= ProtocolIE-Single-Container { {DL-DPCH-LCR-InformationListIEs-RL-AdditionRspTDD} }
DL-DPCH-LCR-InformationList-RL-AdditionRspTDD ::= ProtocolIE-Single-Container

--DL-DPCH-LCR-InformationListIEs-RL-AdditionRspTDD RNSAP-PROTOCOL-IES ::= {
--	{ ID id-DL-DPCH-LCR-InformationItem-RL-AdditionRspTDD		CRITICALITY ignore	TYPE DL-DPCH-LCR-InformationItem-RL-AdditionRspTDD  PRESENCE mandatory	}
--}

DL-DPCH-LCR-InformationItem-RL-AdditionRspTDD ::= SEQUENCE {
	repetitionPeriod				RepetitionPeriod,
	repetitionLength				RepetitionLength,
	tDD-DPCHOffset					TDD-DPCHOffset,
	dL-TimeslotLCR-Information		DL-TimeslotLCR-Information,
	tSTD-Indicator					TSTD-Indicator,
--	iE-Extensions					ProtocolExtensionContainer { {DL-DPCH-LCR-InformationItem-RL-AdditionRspTDD-ExtIEs} } OPTIONAL,
	iE-Extensions					ProtocolExtensionContainer OPTIONAL,
	...
}

--DL-DPCH-LCR-InformationItem-RL-AdditionRspTDD-ExtIEs RNSAP-PROTOCOL-EXTENSION ::= {
--	...
--}

--DCH-InformationResponseList-RL-AdditionRspTDD ::= ProtocolIE-Single-Container {{DCH-InformationResponseListIEs-RL-AdditionRspTDD}}
DCH-InformationResponseList-RL-AdditionRspTDD ::= ProtocolIE-Single-Container

--DCH-InformationResponseListIEs-RL-AdditionRspTDD RNSAP-PROTOCOL-IES ::= {
--	{ ID id-DCH-InformationResponse   CRITICALITY ignore	TYPE DCH-InformationResponse  PRESENCE mandatory }
--}

--DSCH-LCR-InformationResponse-RL-AdditionRspTDD ::= ProtocolIE-Single-Container {{DSCH-LCR-InformationList-RL-AdditionRspTDD}}
DSCH-LCR-InformationResponse-RL-AdditionRspTDD ::= ProtocolIE-Single-Container

--DSCH-LCR-InformationList-RL-AdditionRspTDD RNSAP-PROTOCOL-IES ::= {
--	{ ID id-DSCH-LCR-InformationListIEs-RL-AdditionRspTDD		CRITICALITY ignore	TYPE DSCH-LCR-InformationListIEs-RL-AdditionRspTDD PRESENCE mandatory }
--}

--DSCH-LCR-InformationListIEs-RL-AdditionRspTDD ::= SEQUENCE (SIZE(0..maxNoOfDSCHsLCR)) OF DSCH-LCR-InformationItem-RL-AdditionRspTDD
DSCH-LCR-InformationListIEs-RL-AdditionRspTDD ::= SEQUENCE (SIZE(0..10)) OF DSCH-LCR-InformationItem-RL-AdditionRspTDD

DSCH-LCR-InformationItem-RL-AdditionRspTDD ::= SEQUENCE {
	dsch-ID					DSCH-ID,
	dSCH-FlowControlInformation		DSCH-FlowControlInformation,
	bindingID				BindingID	OPTIONAL,
	transportLayerAddress	TransportLayerAddress	OPTIONAL,
	transportFormatManagement	TransportFormatManagement,
--	iE-Extensions			ProtocolExtensionContainer { {DSCH-LCR-InformationItem-RL-AdditionRspTDD-ExtIEs} } OPTIONAL,
	iE-Extensions			ProtocolExtensionContainer OPTIONAL,
	...
}

--DSCH-LCR-InformationItem-RL-AdditionRspTDD-ExtIEs RNSAP-PROTOCOL-EXTENSION ::= {
--	...
--}

--USCH-LCR-InformationResponse-RL-AdditionRspTDD ::= ProtocolIE-Single-Container {{USCH-LCR-InformationList-RL-AdditionRspTDD}}
USCH-LCR-InformationResponse-RL-AdditionRspTDD ::= ProtocolIE-Single-Container

--USCH-LCR-InformationList-RL-AdditionRspTDD RNSAP-PROTOCOL-IES ::= {
--	{ ID id-USCH-LCR-InformationListIEs-RL-AdditionRspTDD		CRITICALITY ignore	TYPE USCH-LCR-InformationListIEs-RL-AdditionRspTDD PRESENCE mandatory }
--}

--USCH-LCR-InformationListIEs-RL-AdditionRspTDD ::= SEQUENCE (SIZE(0..maxNoOfUSCHsLCR)) OF USCH-LCR-InformationItem-RL-AdditionRspTDD 
USCH-LCR-InformationListIEs-RL-AdditionRspTDD ::= SEQUENCE (SIZE(0..10)) OF USCH-LCR-InformationItem-RL-AdditionRspTDD 

USCH-LCR-InformationItem-RL-AdditionRspTDD ::= SEQUENCE {
	usch-ID						USCH-ID,
	transportFormatManagement	TransportFormatManagement,
	diversityIndication			DiversityIndication-RL-AdditionRspTDD2		OPTIONAL,
--	iE-Extensions				ProtocolExtensionContainer { {USCH-LCR-InformationItem-RL-AdditionRspTDD-ExtIEs} } OPTIONAL,
	iE-Extensions				ProtocolExtensionContainer OPTIONAL,
	...
}

--USCH-LCR-InformationItem-RL-AdditionRspTDD-ExtIEs RNSAP-PROTOCOL-EXTENSION ::= {
--	...
--}

-- **************************************************************
--
-- RADIO LINK ADDITION FAILURE FDD
--
-- **************************************************************

--RadioLinkAdditionFailureFDD ::= SEQUENCE {
--	protocolIEs                     ProtocolIE-Container       {{RadioLinkAdditionFailureFDD-IEs}},
--	protocolExtensions              ProtocolExtensionContainer {{RadioLinkAdditionFailureFDD-Extensions}}                   OPTIONAL,
--	...
--}
RadioLinkAdditionFailureFDD ::= SEQUENCE {
	protocolIEs                     ProtocolIE-Container,
	protocolExtensions              ProtocolExtensionContainer OPTIONAL,
	...
}

--RadioLinkAdditionFailureFDD-IEs RNSAP-PROTOCOL-IES ::= {
--	{ ID id-CauseLevel-RL-AdditionFailureFDD					CRITICALITY		ignore				TYPE CauseLevel-RL-AdditionFailureFDD							PRESENCE	mandatory }|
--	{ ID id-CriticalityDiagnostics			CRITICALITY ignore	TYPE CriticalityDiagnostics			PRESENCE optional	},
--	...
--}

CauseLevel-RL-AdditionFailureFDD ::= CHOICE {
	generalCause		GeneralCauseList-RL-AdditionFailureFDD,
	rLSpecificCause		RLSpecificCauseList-RL-AdditionFailureFDD,
	...
}

GeneralCauseList-RL-AdditionFailureFDD ::= SEQUENCE {
	cause										Cause,
--	iE-Extensions								ProtocolExtensionContainer { { GeneralCauseItem-RL-AdditionFailureFDD-ExtIEs} }			OPTIONAL,
	iE-Extensions								ProtocolExtensionContainer OPTIONAL,
	...
}

--GeneralCauseItem-RL-AdditionFailureFDD-ExtIEs  RNSAP-PROTOCOL-EXTENSION ::= {
--	...
--}

RLSpecificCauseList-RL-AdditionFailureFDD ::= SEQUENCE {
	unsuccessful-RL-InformationRespList-RL-AdditionFailureFDD		UnsuccessfulRL-InformationResponseList-RL-AdditionFailureFDD,
	successful-RL-InformationRespList-RL-AdditionFailureFDD			SuccessfulRL-InformationResponseList-RL-AdditionFailureFDD  OPTIONAL,
--	iE-Extensions								ProtocolExtensionContainer { { RLSpecificCauseItem-RL-AdditionFailureFDD-ExtIEs} }			OPTIONAL,
	iE-Extensions								ProtocolExtensionContainer OPTIONAL,
	...
}

--RLSpecificCauseItem-RL-AdditionFailureFDD-ExtIEs  RNSAP-PROTOCOL-EXTENSION ::= {
--	...
--}

--UnsuccessfulRL-InformationResponseList-RL-AdditionFailureFDD ::= SEQUENCE (SIZE (1..maxNrOfRLs-1)) OF ProtocolIE-Single-Container { {UnsuccessfulRL-InformationResponse-RL-AdditionFailureFDD-IEs} }
UnsuccessfulRL-InformationResponseList-RL-AdditionFailureFDD ::= SEQUENCE (SIZE (1..15)) OF ProtocolIE-Single-Container

--UnsuccessfulRL-InformationResponse-RL-AdditionFailureFDD-IEs RNSAP-PROTOCOL-IES ::= {
--	{ ID id-UnsuccessfulRL-InformationResponse-RL-AdditionFailureFDD	CRITICALITY ignore	TYPE UnsuccessfulRL-InformationResponse-RL-AdditionFailureFDD		PRESENCE mandatory	}
--}

UnsuccessfulRL-InformationResponse-RL-AdditionFailureFDD ::= SEQUENCE {
	rL-ID							RL-ID,
	cause							Cause,
--	iE-Extensions					ProtocolExtensionContainer { {UnsuccessfulRL-InformationResponse-RL-AdditionFailureFDD-ExtIEs} } OPTIONAL,
	iE-Extensions					ProtocolExtensionContainer OPTIONAL,
	...
}

--UnsuccessfulRL-InformationResponse-RL-AdditionFailureFDD-ExtIEs RNSAP-PROTOCOL-EXTENSION ::= {
--	...
--}

--SuccessfulRL-InformationResponseList-RL-AdditionFailureFDD ::= SEQUENCE (SIZE (0..maxNrOfRLs-2)) OF ProtocolIE-Single-Container { {SuccessfulRL-InformationResponse-RL-AdditionFailureFDD-IEs} }
SuccessfulRL-InformationResponseList-RL-AdditionFailureFDD ::= SEQUENCE (SIZE (0..14)) OF ProtocolIE-Single-Container

--SuccessfulRL-InformationResponse-RL-AdditionFailureFDD-IEs RNSAP-PROTOCOL-IES ::= {
--	{ ID id-SuccessfulRL-InformationResponse-RL-AdditionFailureFDD		CRITICALITY ignore	TYPE SuccessfulRL-InformationResponse-RL-AdditionFailureFDD		PRESENCE mandatory	}
--}

SuccessfulRL-InformationResponse-RL-AdditionFailureFDD ::= SEQUENCE {
	rL-ID								RL-ID,
	rL-Set-ID							RL-Set-ID,
	uRA-Information						URA-Information		OPTIONAL,
	sAI									SAI,
	gA-Cell								GA-Cell		OPTIONAL,
	gA-AccessPointPosition				GA-AccessPointPosition		OPTIONAL,
	received-total-wide-band-power		Received-total-wide-band-power,
	not-Used-secondary-CCPCH-Info				NULL		OPTIONAL,
	dl-CodeInformation					DL-CodeInformationList-RL-AdditionFailureFDD,
	diversityIndication					DiversityIndication-RL-AdditionFailureFDD, 
	-- This IE represents both the Diversity Indication IE and the choice based on the diversity indication as described in 
	-- the tabular message format in subclause 9.1.
	sSDT-SupportIndicator				SSDT-SupportIndicator,
	minUL-SIR							UL-SIR,
	maxUL-SIR							UL-SIR,
	closedlooptimingadjustmentmode		Closedlooptimingadjustmentmode	OPTIONAL,
	maximumAllowedULTxPower				MaximumAllowedULTxPower,
	maximumDLTxPower					DL-Power,
	minimumDLTxPower					DL-Power,
	neighbouring-UMTS-CellInformation	Neighbouring-UMTS-CellInformation OPTIONAL,
	neighbouring-GSM-CellInformation	Neighbouring-GSM-CellInformation OPTIONAL,
	primaryCPICH-Power					PrimaryCPICH-Power,
	pC-Preamble							PC-Preamble,
	sRB-Delay							SRB-Delay,
--	iE-Extensions						ProtocolExtensionContainer { {SuccessfulRL-InformationResponse-RL-AdditionFailureFDD-ExtIEs} } OPTIONAL,
	iE-Extensions						ProtocolExtensionContainer OPTIONAL,
	...
}

--SuccessfulRL-InformationResponse-RL-AdditionFailureFDD-ExtIEs RNSAP-PROTOCOL-EXTENSION ::= {
--	{ ID id-GA-CellAdditionalShapes						CRITICALITY	ignore	EXTENSION GA-CellAdditionalShapes								PRESENCE optional }|
--	{ ID id-DL-PowerBalancing-ActivationIndicator		CRITICALITY ignore	EXTENSION DL-PowerBalancing-ActivationIndicator			PRESENCE optional }|
--	{ ID id-HCS-Prio									CRITICALITY	ignore	EXTENSION HCS-Prio												PRESENCE optional }|
--	{ ID id-Active-MBMS-Bearer-ServiceFDD-PFL				CRITICALITY ignore	EXTENSION Active-MBMS-Bearer-Service-ListFDD-PFL			PRESENCE optional }|
--	{ ID id-EDCH-RLSet-Id								CRITICALITY ignore	EXTENSION RL-Set-ID												PRESENCE optional }|
--	{ ID id-EDCH-FDD-DL-ControlChannelInformation		CRITICALITY ignore	EXTENSION EDCH-FDD-DL-ControlChannelInformation		PRESENCE optional }|
--	{ ID id-Initial-DL-DPCH-TimingAdjustment			CRITICALITY ignore	EXTENSION DL-DPCH-TimingAdjustment						PRESENCE optional },
--	...
--}

--DL-CodeInformationList-RL-AdditionFailureFDD ::= ProtocolIE-Single-Container {{ DL-CodeInformationListIEs-RL-AdditionFailureFDD }}
DL-CodeInformationList-RL-AdditionFailureFDD ::= ProtocolIE-Single-Container

--DL-CodeInformationListIEs-RL-AdditionFailureFDD RNSAP-PROTOCOL-IES ::= {
--	{ ID id-FDD-DL-CodeInformation   CRITICALITY ignore	TYPE FDD-DL-CodeInformation		PRESENCE mandatory }
--}

DiversityIndication-RL-AdditionFailureFDD ::= CHOICE {
	combining						Combining-RL-AdditionFailureFDD,
	nonCombining					NonCombining-RL-AdditionFailureFDD
}

Combining-RL-AdditionFailureFDD ::= SEQUENCE {
	rL-ID						RL-ID,
--	iE-Extensions				ProtocolExtensionContainer { { CombiningItem-RL-AdditionFailureFDD-ExtIEs} } OPTIONAL,
	iE-Extensions				ProtocolExtensionContainer OPTIONAL,
	...
}

--CombiningItem-RL-AdditionFailureFDD-ExtIEs RNSAP-PROTOCOL-EXTENSION ::= {
--	{ ID id-DCH-InformationResponse			CRITICALITY ignore	EXTENSION DCH-InformationResponse			PRESENCE optional	}|
--	{ ID id-EDCH-FDD-InformationResponse	CRITICALITY ignore	EXTENSION EDCH-FDD-InformationResponse			PRESENCE optional	},
--	...
--}

NonCombining-RL-AdditionFailureFDD ::= SEQUENCE {
	dCH-InformationResponse		DCH-InformationResponse,
--	iE-Extensions								ProtocolExtensionContainer { { NonCombiningItem-RL-AdditionFailureFDD-ExtIEs} } OPTIONAL,
	iE-Extensions								ProtocolExtensionContainer  OPTIONAL,
	...
}

--NonCombiningItem-RL-AdditionFailureFDD-ExtIEs RNSAP-PROTOCOL-EXTENSION ::= {
--	{ ID id-EDCH-FDD-InformationResponse	CRITICALITY ignore	EXTENSION EDCH-FDD-InformationResponse			PRESENCE optional	},
--	...
--}

--RadioLinkAdditionFailureFDD-Extensions RNSAP-PROTOCOL-EXTENSION ::= {
--	...
--}

-- **************************************************************
--
-- RADIO LINK ADDITION FAILURE TDD
--
-- **************************************************************

--RadioLinkAdditionFailureTDD ::= SEQUENCE {
--	protocolIEs                     ProtocolIE-Container       {{RadioLinkAdditionFailureTDD-IEs}},
--	protocolExtensions              ProtocolExtensionContainer {{RadioLinkAdditionFailureTDD-Extensions}}                   OPTIONAL,
--	...
--}
RadioLinkAdditionFailureTDD ::= SEQUENCE {
	protocolIEs                     ProtocolIE-Container,
	protocolExtensions              ProtocolExtensionContainer OPTIONAL,
	...
}

--RadioLinkAdditionFailureTDD-IEs RNSAP-PROTOCOL-IES ::= {
--	{ ID id-CauseLevel-RL-AdditionFailureTDD	CRITICALITY ignore	TYPE CauseLevel-RL-AdditionFailureTDD	PRESENCE mandatory }|
--	{ ID id-CriticalityDiagnostics			CRITICALITY ignore	TYPE CriticalityDiagnostics			PRESENCE optional	},
--	...
--}

CauseLevel-RL-AdditionFailureTDD ::= CHOICE {
	generalCause		GeneralCauseList-RL-AdditionFailureTDD,
	rLSpecificCause		RLSpecificCauseList-RL-AdditionFailureTDD,
	...
}

GeneralCauseList-RL-AdditionFailureTDD ::= SEQUENCE {
	cause						Cause,
--	iE-Extensions				ProtocolExtensionContainer { { GeneralCauseItem-RL-AdditionFailureTDD-ExtIEs} }		OPTIONAL,
	iE-Extensions				ProtocolExtensionContainer OPTIONAL,
	...
}

--GeneralCauseItem-RL-AdditionFailureTDD-ExtIEs RNSAP-PROTOCOL-EXTENSION ::= {
--	...
--}

RLSpecificCauseList-RL-AdditionFailureTDD ::= SEQUENCE {
	unsuccessful-RL-InformationRespItem-RL-AdditionFailureTDD	Unsuccessful-RL-InformationRespItem-RL-AdditionFailureTDD,
--	iE-Extensions												ProtocolExtensionContainer { { RLSpecificCauseItem-RL-AdditionFailureTDD-ExtIEs} }		OPTIONAL,
	iE-Extensions												ProtocolExtensionContainer OPTIONAL,
	...
}

--RLSpecificCauseItem-RL-AdditionFailureTDD-ExtIEs RNSAP-PROTOCOL-EXTENSION ::= {
--	...
--}

--Unsuccessful-RL-InformationRespItem-RL-AdditionFailureTDD ::= ProtocolIE-Single-Container { {Unsuccessful-RL-InformationRespItemIE-RL-AdditionFailureTDD} }
Unsuccessful-RL-InformationRespItem-RL-AdditionFailureTDD ::= ProtocolIE-Single-Container

--Unsuccessful-RL-InformationRespItemIE-RL-AdditionFailureTDD RNSAP-PROTOCOL-IES ::= {
--	{ ID	id-UnsuccessfulRL-InformationResponse-RL-AdditionFailureTDD		CRITICALITY	ignore 		TYPE 	UnsuccessfulRL-InformationResponse-RL-AdditionFailureTDD	PRESENCE mandatory}
--}

UnsuccessfulRL-InformationResponse-RL-AdditionFailureTDD ::= SEQUENCE {
	rL-ID						RL-ID,
	cause						Cause,
--	iE-Extensions				ProtocolExtensionContainer { {UnsuccessfulRL-InformationResponse-RL-AdditionFailureTDD-ExtIEs} } OPTIONAL,
	iE-Extensions				ProtocolExtensionContainer OPTIONAL,
	...
}

--UnsuccessfulRL-InformationResponse-RL-AdditionFailureTDD-ExtIEs RNSAP-PROTOCOL-EXTENSION ::= {
--	...
--}

--RadioLinkAdditionFailureTDD-Extensions RNSAP-PROTOCOL-EXTENSION ::= {
--	...
--}

-- **************************************************************
--
-- RADIO LINK DELETION REQUEST
--
-- **************************************************************

--RadioLinkDeletionRequest ::= SEQUENCE {
--	protocolIEs                     ProtocolIE-Container       {{RadioLinkDeletionRequest-IEs}},
--	protocolExtensions              ProtocolExtensionContainer {{RadioLinkDeletionRequest-Extensions}}                   OPTIONAL,
--	...
--}
RadioLinkDeletionRequest ::= SEQUENCE {
	protocolIEs                     ProtocolIE-Container,
	protocolExtensions              ProtocolExtensionContainer OPTIONAL,
	...
}
--RadioLinkDeletionRequest-IEs RNSAP-PROTOCOL-IES ::= {
--	{ ID id-RL-InformationList-RL-DeletionRqst	CRITICALITY notify	TYPE RL-InformationList-RL-DeletionRqst		PRESENCE mandatory	},
--	...
--}

--RL-InformationList-RL-DeletionRqst			::= SEQUENCE (SIZE (1..maxNrOfRLs)) OF ProtocolIE-Single-Container { {RL-Information-RL-DeletionRqst-IEs} }
RL-InformationList-RL-DeletionRqst			::= SEQUENCE (SIZE (1..16)) OF ProtocolIE-Single-Container

--RL-Information-RL-DeletionRqst-IEs RNSAP-PROTOCOL-IES ::= {
--	{ ID id-RL-Information-RL-DeletionRqst		CRITICALITY notify	TYPE RL-Information-RL-DeletionRqst		PRESENCE mandatory	}
--}

RL-Information-RL-DeletionRqst ::= SEQUENCE {
	rL-ID						RL-ID,
--	iE-Extensions				ProtocolExtensionContainer { {RL-Information-RL-DeletionRqst-ExtIEs} } OPTIONAL,
	iE-Extensions				ProtocolExtensionContainer OPTIONAL,
	...
}

--RL-Information-RL-DeletionRqst-ExtIEs RNSAP-PROTOCOL-EXTENSION ::= {
--	...
--}

--RadioLinkDeletionRequest-Extensions RNSAP-PROTOCOL-EXTENSION ::= {
--	...
--}

-- **************************************************************
--
-- RADIO LINK DELETION RESPONSE
--
-- **************************************************************

--RadioLinkDeletionResponse ::= SEQUENCE {
--	protocolIEs                     ProtocolIE-Container       {{RadioLinkDeletionResponse-IEs}},
--	protocolExtensions              ProtocolExtensionContainer {{RadioLinkDeletionResponse-Extensions}}                   OPTIONAL,
--	...
--}
RadioLinkDeletionResponse ::= SEQUENCE {
	protocolIEs                     ProtocolIE-Container,
	protocolExtensions              ProtocolExtensionContainer OPTIONAL,
	...
}

--RadioLinkDeletionResponse-IEs RNSAP-PROTOCOL-IES ::= {
--	{ ID id-CriticalityDiagnostics			CRITICALITY ignore	TYPE CriticalityDiagnostics			PRESENCE optional	},
--	...
--}

--RadioLinkDeletionResponse-Extensions RNSAP-PROTOCOL-EXTENSION ::= {
--	...
--}

-- **************************************************************
--
-- RADIO LINK RECONFIGURATION PREPARE FDD
--
-- **************************************************************

--RadioLinkReconfigurationPrepareFDD ::= SEQUENCE {
--	protocolIEs                     ProtocolIE-Container       {{RadioLinkReconfigurationPrepareFDD-IEs}},
--	protocolExtensions              ProtocolExtensionContainer {{RadioLinkReconfigurationPrepareFDD-Extensions}}                   OPTIONAL,
--	...
--}
RadioLinkReconfigurationPrepareFDD ::= SEQUENCE {
	protocolIEs                     ProtocolIE-Container,
	protocolExtensions              ProtocolExtensionContainer OPTIONAL,
	...
}

--RadioLinkReconfigurationPrepareFDD-IEs RNSAP-PROTOCOL-IES ::= {
--	{ ID id-AllowedQueuingTime			CRITICALITY reject	TYPE AllowedQueuingTime				PRESENCE optional	} |
--	{ ID id-UL-DPCH-Information-RL-ReconfPrepFDD			CRITICALITY reject	TYPE UL-DPCH-Information-RL-ReconfPrepFDD			PRESENCE optional	} |
--	{ ID id-DL-DPCH-Information-RL-ReconfPrepFDD			CRITICALITY reject	TYPE DL-DPCH-Information-RL-ReconfPrepFDD			PRESENCE optional	} |
--	{ ID id-FDD-DCHs-to-Modify		CRITICALITY reject	TYPE FDD-DCHs-to-Modify		PRESENCE optional	} |
--	{ ID id-DCHs-to-Add-FDD		CRITICALITY reject	TYPE DCH-FDD-Information		PRESENCE optional	} |
--	{ ID id-DCH-DeleteList-RL-ReconfPrepFDD		CRITICALITY reject	TYPE DCH-DeleteList-RL-ReconfPrepFDD		PRESENCE optional	} |
--	{ ID id-RL-InformationList-RL-ReconfPrepFDD	CRITICALITY reject	TYPE RL-InformationList-RL-ReconfPrepFDD	PRESENCE optional	}|
--	{ ID id-Transmission-Gap-Pattern-Sequence-Information	CRITICALITY reject	TYPE Transmission-Gap-Pattern-Sequence-Information	 PRESENCE optional },
--	...
--}

UL-DPCH-Information-RL-ReconfPrepFDD ::= SEQUENCE {
	ul-ScramblingCode				UL-ScramblingCode		OPTIONAL,
	ul-SIRTarget					UL-SIR					OPTIONAL,
	minUL-ChannelisationCodeLength	MinUL-ChannelisationCodeLength 	OPTIONAL,
	maxNrOfUL-DPDCHs				MaxNrOfUL-DPCHs			OPTIONAL
	-- This IE shall be present if minUL-ChannelisationCodeLength equals to 4 --,
	ul-PunctureLimit				PunctureLimit			OPTIONAL,
	tFCS							TFCS 	OPTIONAL,
	ul-DPCCH-SlotFormat				UL-DPCCH-SlotFormat		OPTIONAL,
	diversityMode					DiversityMode			OPTIONAL,
	not-Used-sSDT-CellIDLength		NULL		OPTIONAL,
	not-Used-s-FieldLength			NULL			OPTIONAL,
--	iE-Extensions					ProtocolExtensionContainer { {UL-DPCH-Information-RL-ReconfPrepFDD-ExtIEs} } OPTIONAL,
	iE-Extensions					ProtocolExtensionContainer OPTIONAL,
	...
}

--UL-DPCH-Information-RL-ReconfPrepFDD-ExtIEs RNSAP-PROTOCOL-EXTENSION ::= {
--	{ ID id-UL-DPDCHIndicatorEDCH	CRITICALITY reject		EXTENSION UL-DPDCHIndicatorEDCH	PRESENCE optional	},
--	...
--}

DL-DPCH-Information-RL-ReconfPrepFDD ::= SEQUENCE {
	tFCS							TFCS	OPTIONAL,
	dl-DPCH-SlotFormat				DL-DPCH-SlotFormat		OPTIONAL,
	nrOfDLchannelisationcodes		NrOfDLchannelisationcodes	OPTIONAL,
	tFCI-SignallingMode				TFCI-SignallingMode		OPTIONAL,
	tFCI-Presence					TFCI-Presence			OPTIONAL
	-- This IE shall be present if DL DPCH Slot Format IE is from 12 to 16 --,
	multiplexingPosition			MultiplexingPosition		OPTIONAL,
	limitedPowerIncrease			LimitedPowerIncrease		OPTIONAL,
--	iE-Extensions					ProtocolExtensionContainer { {DL-DPCH-Information-RL-ReconfPrepFDD-ExtIEs} } OPTIONAL,
	iE-Extensions					ProtocolExtensionContainer OPTIONAL,
	...
}

--DL-DPCH-Information-RL-ReconfPrepFDD-ExtIEs RNSAP-PROTOCOL-EXTENSION ::= {
--	{ ID id-DL-DPCH-Power-Information-RL-ReconfPrepFDD	CRITICALITY reject	EXTENSION DL-DPCH-Power-Information-RL-ReconfPrepFDD	PRESENCE optional	},
--	...
--}

DL-DPCH-Power-Information-RL-ReconfPrepFDD ::= SEQUENCE {
	powerOffsetInformation					PowerOffsetInformation-RL-ReconfPrepFDD,
	fdd-TPC-DownlinkStepSize				FDD-TPC-DownlinkStepSize,
	innerLoopDLPCStatus						InnerLoopDLPCStatus,
--	iE-Extensions							ProtocolExtensionContainer { { DL-DPCH-Power-Information-RL-ReconfPrepFDD-ExtIEs } }	OPTIONAL,
	iE-Extensions							ProtocolExtensionContainer OPTIONAL,
	...
}

--DL-DPCH-Power-Information-RL-ReconfPrepFDD-ExtIEs RNSAP-PROTOCOL-EXTENSION ::= {
--	...
--}

PowerOffsetInformation-RL-ReconfPrepFDD ::= SEQUENCE {
	pO1-ForTFCI-Bits						PowerOffset,
	pO2-ForTPC-Bits							PowerOffset,
	pO3-ForPilotBits						PowerOffset,
--	iE-Extensions							ProtocolExtensionContainer { { PowerOffsetInformation-RL-ReconfPrepFDD-ExtIEs} }	OPTIONAL,
	iE-Extensions							ProtocolExtensionContainer OPTIONAL,
	...
}

--PowerOffsetInformation-RL-ReconfPrepFDD-ExtIEs RNSAP-PROTOCOL-EXTENSION ::= {
--	...
--}

--DCH-DeleteList-RL-ReconfPrepFDD				::= SEQUENCE (SIZE (0..maxNrOfDCHs)) OF DCH-DeleteItem-RL-ReconfPrepFDD
DCH-DeleteList-RL-ReconfPrepFDD				::= SEQUENCE (SIZE (0..128)) OF DCH-DeleteItem-RL-ReconfPrepFDD

DCH-DeleteItem-RL-ReconfPrepFDD ::= SEQUENCE {
	dCH-ID							DCH-ID,
--	iE-Extensions					ProtocolExtensionContainer { {DCH-DeleteItem-RL-ReconfPrepFDD-ExtIEs} } OPTIONAL,
	iE-Extensions					ProtocolExtensionContainer OPTIONAL,
	...
}

--DCH-DeleteItem-RL-ReconfPrepFDD-ExtIEs RNSAP-PROTOCOL-EXTENSION ::= {
--	...
--}

--RL-InformationList-RL-ReconfPrepFDD			::= SEQUENCE (SIZE (0..maxNrOfRLs)) OF ProtocolIE-Single-Container { {RL-Information-RL-ReconfPrepFDD-IEs} }
RL-InformationList-RL-ReconfPrepFDD			::= SEQUENCE (SIZE (0..16)) OF ProtocolIE-Single-Container

--RL-Information-RL-ReconfPrepFDD-IEs RNSAP-PROTOCOL-IES ::= {
--	{ ID id-RL-Information-RL-ReconfPrepFDD		CRITICALITY reject	TYPE RL-Information-RL-ReconfPrepFDD		PRESENCE mandatory	}
--}

RL-Information-RL-ReconfPrepFDD ::= SEQUENCE {
	rL-ID						RL-ID,
	not-Used-sSDT-Indication			NULL		OPTIONAL,
	not-Used-sSDT-CellIdentity			NULL		OPTIONAL,
	transmitDiversityIndicator		TransmitDiversityIndicator		OPTIONAL,
	-- This IE shall be present if Diversity Mode IE is present in UL DPCH Information IE and is not equal to “none”
--	iE-Extensions					ProtocolExtensionContainer { {RL-Information-RL-ReconfPrepFDD-ExtIEs} } OPTIONAL,
	iE-Extensions					ProtocolExtensionContainer OPTIONAL,
	...
}

--RL-Information-RL-ReconfPrepFDD-ExtIEs RNSAP-PROTOCOL-EXTENSION ::= {
--	{ ID id-DLReferencePower					CRITICALITY ignore	EXTENSION	DL-Power				PRESENCE optional	}|
--	{ ID id-RL-Specific-DCH-Info				CRITICALITY	ignore	EXTENSION RL-Specific-DCH-Info	PRESENCE 	optional	}|
--	{ ID id-DL-DPCH-TimingAdjustment			CRITICALITY reject	EXTENSION DL-DPCH-TimingAdjustment	PRESENCE optional }|
--	{ ID id-Phase-Reference-Update-Indicator	CRITICALITY ignore	EXTENSION Phase-Reference-Update-Indicator	PRESENCE optional }|
--	{ ID id-RL-Specific-EDCH-Information		CRITICALITY reject		EXTENSION RL-Specific-EDCH-Information 		PRESENCE optional }|
--	{ ID id-EDCH-MACdFlows-To-Add				CRITICALITY reject		EXTENSION RL-Specific-EDCH-Information 		PRESENCE optional }|
--	{ ID id-EDCH-RL-Indication					CRITICALITY reject		EXTENSION EDCH-RL-Indication						PRESENCE optional },
--	...
--}

--RadioLinkReconfigurationPrepareFDD-Extensions RNSAP-PROTOCOL-EXTENSION ::= {
--	{ ID id-HSDSCH-FDD-Information							CRITICALITY reject	EXTENSION HSDSCH-FDD-Information					PRESENCE optional}|
--	{ ID id-HSDSCH-Information-to-Modify					CRITICALITY reject	EXTENSION HSDSCH-Information-to-Modify				PRESENCE optional}|
--	{ ID id-HSDSCH-MACdFlows-to-Add							CRITICALITY reject	EXTENSION HSDSCH-MACdFlows-Information				PRESENCE optional}|
--	{ ID id-HSDSCH-MACdFlows-to-Delete						CRITICALITY reject	EXTENSION HSDSCH-MACdFlows-to-Delete				PRESENCE optional}|
--	{ ID id-HSPDSCH-RL-ID									CRITICALITY reject	EXTENSION RL-ID												PRESENCE optional}|
--	{ ID id-EDPCH-Information								CRITICALITY reject	EXTENSION EDPCH-Information-RLReconfPrepare-FDD						PRESENCE optional}|
--	{ ID id-EDCH-FDD-Information							CRITICALITY reject	EXTENSION EDCH-FDD-Information						PRESENCE optional}|
--	{ ID id-EDCH-FDD-Information-To-Modify					CRITICALITY reject	EXTENSION EDCH-FDD-Information-To-Modify			PRESENCE optional}|
--	{ ID id-EDCH-MACdFlows-To-Delete						CRITICALITY reject	EXTENSION EDCH-MACdFlows-To-Delete					PRESENCE optional}|
--	{ ID id-Serving-EDCHRL-Id								CRITICALITY reject	EXTENSION EDCH-Serving-RL												PRESENCE conditional}|
	-- This IE is present if RL Specific E-DCHInformation IE is present.
--	{ ID id-F-DPCH-Information-RL-ReconfPrepFDD				CRITICALITY reject	EXTENSION F-DPCH-Information-RL-ReconfPrepFDD	PRESENCE optional},
--	...
--}

F-DPCH-Information-RL-ReconfPrepFDD ::= SEQUENCE {
	powerOffsetInformation			PowerOffsetInformation-F-DPCH-RL-ReconfPrepFDD,
	fdd-dl-TPC-DownlinkStepSize		FDD-TPC-DownlinkStepSize,
	limitedPowerIncrease			LimitedPowerIncrease,
	innerLoopDLPCStatus				InnerLoopDLPCStatus,
--	iE-Extensions					ProtocolExtensionContainer { { F-DPCH-Information-RL-ReconfPrepFDD-ExtIEs} }					OPTIONAL,
	iE-Extensions					ProtocolExtensionContainer OPTIONAL,
	...
}

--F-DPCH-Information-RL-ReconfPrepFDD-ExtIEs RNSAP-PROTOCOL-EXTENSION ::= {
--	...
--}

PowerOffsetInformation-F-DPCH-RL-ReconfPrepFDD ::= SEQUENCE {
	po2-ForTPC-Bits					PowerOffset,
--	iE-Extensions					ProtocolExtensionContainer { { PowerOffsetInformation-F-DPCH-RL-ReconfPrepFDD-ExtIEs} }		OPTIONAL,
	iE-Extensions					ProtocolExtensionContainer OPTIONAL,
	...
}

--PowerOffsetInformation-F-DPCH-RL-ReconfPrepFDD-ExtIEs RNSAP-PROTOCOL-EXTENSION ::= {
--	...
--}


-- **************************************************************
--
-- RADIO LINK RECONFIGURATION PREPARE TDD
--
-- **************************************************************
--RadioLinkReconfigurationPrepareTDD ::= SEQUENCE {
--	protocolIEs                     ProtocolIE-Container       {{RadioLinkReconfigurationPrepareTDD-IEs}},
--	protocolExtensions              ProtocolExtensionContainer {{RadioLinkReconfigurationPrepareTDD-Extensions}}                   OPTIONAL,
--	...
--}
RadioLinkReconfigurationPrepareTDD ::= SEQUENCE {
	protocolIEs                     ProtocolIE-Container,
	protocolExtensions              ProtocolExtensionContainer OPTIONAL,
	...
}

--RadioLinkReconfigurationPrepareTDD-IEs RNSAP-PROTOCOL-IES ::= {
--	{ ID id-AllowedQueuingTime			CRITICALITY reject	TYPE AllowedQueuingTime				PRESENCE optional	} |
--	{ ID id-UL-CCTrCH-InformationAddList-RL-ReconfPrepTDD	CRITICALITY notify	TYPE UL-CCTrCH-InformationAddList-RL-ReconfPrepTDD	PRESENCE optional	} |
--	{ ID id-UL-CCTrCH-InformationModifyList-RL-ReconfPrepTDD	CRITICALITY notify	TYPE UL-CCTrCH-InformationModifyList-RL-ReconfPrepTDD	PRESENCE optional	} |
--	{ ID id-UL-CCTrCH-InformationDeleteList-RL-ReconfPrepTDD	CRITICALITY notify	TYPE UL-CCTrCH-InformationDeleteList-RL-ReconfPrepTDD	PRESENCE optional	} |
--	{ ID id-DL-CCTrCH-InformationAddList-RL-ReconfPrepTDD	CRITICALITY notify	TYPE DL-CCTrCH-InformationAddList-RL-ReconfPrepTDD	PRESENCE optional	} |
--	{ ID id-DL-CCTrCH-InformationModifyList-RL-ReconfPrepTDD	CRITICALITY notify	TYPE DL-CCTrCH-InformationModifyList-RL-ReconfPrepTDD	PRESENCE optional	} |
--	{ ID id-DL-CCTrCH-InformationDeleteList-RL-ReconfPrepTDD	CRITICALITY notify	TYPE DL-CCTrCH-InformationDeleteList-RL-ReconfPrepTDD	PRESENCE optional	} |
--	{ ID id-TDD-DCHs-to-Modify		CRITICALITY reject	TYPE TDD-DCHs-to-Modify		PRESENCE optional	} |
--	{ ID id-DCHs-to-Add-TDD		CRITICALITY reject	TYPE DCH-TDD-Information		PRESENCE optional	} |
--	{ ID id-DCH-DeleteList-RL-ReconfPrepTDD		CRITICALITY reject	TYPE DCH-DeleteList-RL-ReconfPrepTDD		PRESENCE optional	}|
--	{ ID id-DSCH-ModifyList-RL-ReconfPrepTDD	CRITICALITY reject	TYPE DSCH-ModifyList-RL-ReconfPrepTDD		PRESENCE optional	} |
--	{ ID id-DSCHs-to-Add-TDD		CRITICALITY reject	TYPE DSCH-TDD-Information			PRESENCE optional	} |
--	{ ID id-DSCH-DeleteList-RL-ReconfPrepTDD	CRITICALITY reject	TYPE DSCH-DeleteList-RL-ReconfPrepTDD		PRESENCE optional	} |
--	{ ID id-USCH-ModifyList-RL-ReconfPrepTDD	CRITICALITY reject	TYPE USCH-ModifyList-RL-ReconfPrepTDD		PRESENCE optional	} |
--	{ ID id-USCHs-to-Add		CRITICALITY reject	TYPE USCH-Information			PRESENCE optional	} |
--	{ ID id-USCH-DeleteList-RL-ReconfPrepTDD	CRITICALITY reject	TYPE USCH-DeleteList-RL-ReconfPrepTDD		PRESENCE optional	},
--	...
--}

--UL-CCTrCH-InformationAddList-RL-ReconfPrepTDD		::= SEQUENCE (SIZE (0..maxNrOfCCTrCHs)) OF ProtocolIE-Single-Container { {UL-CCTrCH-AddInformation-RL-ReconfPrepTDD-IEs} }
UL-CCTrCH-InformationAddList-RL-ReconfPrepTDD		::= SEQUENCE (SIZE (0..16)) OF ProtocolIE-Single-Container

--UL-CCTrCH-AddInformation-RL-ReconfPrepTDD-IEs RNSAP-PROTOCOL-IES ::= {
--	{ ID id-UL-CCTrCH-AddInformation-RL-ReconfPrepTDD	CRITICALITY notify	TYPE UL-CCTrCH-AddInformation-RL-ReconfPrepTDD	PRESENCE mandatory	}
--}

UL-CCTrCH-AddInformation-RL-ReconfPrepTDD ::= SEQUENCE {
	cCTrCH-ID					CCTrCH-ID,
	tFCS						TFCS,
	tFCI-Coding					TFCI-Coding,
	punctureLimit					PunctureLimit,
--	iE-Extensions					ProtocolExtensionContainer { {UL-CCTrCH-AddInformation-RL-ReconfPrepTDD-ExtIEs} } OPTIONAL,
	iE-Extensions					ProtocolExtensionContainer OPTIONAL,
	...
}

--UL-CCTrCH-AddInformation-RL-ReconfPrepTDD-ExtIEs RNSAP-PROTOCOL-EXTENSION ::= {
--	{ ID id-UL-SIRTarget		CRITICALITY reject		EXTENSION		UL-SIR		PRESENCE optional}|
	-- This IE shall be mandatory for 1.28Mcps TDD, not applicable for 3.84Mcps TDD.
--{ ID id-TDD-TPC-UplinkStepSize-InformationAdd-LCR-RL-ReconfPrepTDD	CRITICALITY reject	EXTENSION TDD-TPC-UplinkStepSize-LCR	PRESENCE optional	},
	-- Mandatory for 1.28Mcps TDD, not applicable to 3.84Mcps TDD
--	...
--}

--UL-CCTrCH-InformationModifyList-RL-ReconfPrepTDD		::= SEQUENCE (SIZE (0..maxNrOfCCTrCHs)) OF ProtocolIE-Single-Container { {UL-CCTrCH-ModifyInformation-RL-ReconfPrepTDD-IEs} }
UL-CCTrCH-InformationModifyList-RL-ReconfPrepTDD		::= SEQUENCE (SIZE (0..16)) OF ProtocolIE-Single-Container

--UL-CCTrCH-ModifyInformation-RL-ReconfPrepTDD-IEs RNSAP-PROTOCOL-IES ::= {
--	{ ID id-UL-CCTrCH-ModifyInformation-RL-ReconfPrepTDD	CRITICALITY notify	TYPE UL-CCTrCH-ModifyInformation-RL-ReconfPrepTDD	PRESENCE mandatory	}
--}

UL-CCTrCH-ModifyInformation-RL-ReconfPrepTDD ::= SEQUENCE {
	cCTrCH-ID					CCTrCH-ID,
	tFCS						TFCS		OPTIONAL,
	tFCI-Coding					TFCI-Coding				OPTIONAL,
	punctureLimit					PunctureLimit				OPTIONAL,
--	iE-Extensions					ProtocolExtensionContainer { {UL-CCTrCH-ModifyInformation-RL-ReconfPrepTDD-ExtIEs} } OPTIONAL,
	iE-Extensions					ProtocolExtensionContainer OPTIONAL,
	...
}

--UL-CCTrCH-ModifyInformation-RL-ReconfPrepTDD-ExtIEs RNSAP-PROTOCOL-EXTENSION ::= {
--	{ ID id-UL-SIRTarget		CRITICALITY reject		EXTENSION		UL-SIR		PRESENCE optional}|
	-- This IE shall be applicable for 1.28Mcps TDD only.
--{ ID id-TDD-TPC-UplinkStepSize-InformationModify-LCR-RL-ReconfPrepTDD	CRITICALITY reject	EXTENSION	TDD-TPC-UplinkStepSize-LCR		PRESENCE optional	},
	-- Applicable to 1.28Mcps TDD only
--	...
--}

--UL-CCTrCH-InformationDeleteList-RL-ReconfPrepTDD		::= SEQUENCE (SIZE (0..maxNrOfCCTrCHs)) OF ProtocolIE-Single-Container { {UL-CCTrCH-DeleteInformation-RL-ReconfPrepTDD-IEs} }
UL-CCTrCH-InformationDeleteList-RL-ReconfPrepTDD		::= SEQUENCE (SIZE (0..16)) OF ProtocolIE-Single-Container

--UL-CCTrCH-DeleteInformation-RL-ReconfPrepTDD-IEs RNSAP-PROTOCOL-IES ::= {
--	{ ID id-UL-CCTrCH-DeleteInformation-RL-ReconfPrepTDD	CRITICALITY notify	TYPE UL-CCTrCH-DeleteInformation-RL-ReconfPrepTDD	PRESENCE mandatory	}
--}

UL-CCTrCH-DeleteInformation-RL-ReconfPrepTDD ::= SEQUENCE {
	cCTrCH-ID					CCTrCH-ID,
--	iE-Extensions					ProtocolExtensionContainer { {UL-CCTrCH-DeleteInformation-RL-ReconfPrepTDD-ExtIEs} } OPTIONAL,
	iE-Extensions					ProtocolExtensionContainer OPTIONAL,
	...
}

--UL-CCTrCH-DeleteInformation-RL-ReconfPrepTDD-ExtIEs RNSAP-PROTOCOL-EXTENSION ::= {
--	...
--}

--DL-CCTrCH-InformationAddList-RL-ReconfPrepTDD		::= SEQUENCE (SIZE (0..maxNrOfCCTrCHs)) OF ProtocolIE-Single-Container { {DL-CCTrCH-AddInformation-RL-ReconfPrepTDD-IEs} }
DL-CCTrCH-InformationAddList-RL-ReconfPrepTDD		::= SEQUENCE (SIZE (0..16)) OF ProtocolIE-Single-Container

--DL-CCTrCH-AddInformation-RL-ReconfPrepTDD-IEs RNSAP-PROTOCOL-IES ::= {
--	{ ID id-DL-CCTrCH-InformationAddItem-RL-ReconfPrepTDD	CRITICALITY notify	TYPE DL-CCTrCH-InformationAddItem-RL-ReconfPrepTDD	PRESENCE mandatory	}
--}

DL-CCTrCH-InformationAddItem-RL-ReconfPrepTDD ::= SEQUENCE {
	cCTrCH-ID					CCTrCH-ID,
	tFCS						TFCS,
	tFCI-Coding					TFCI-Coding,
	punctureLimit					PunctureLimit,
	cCTrCH-TPCList					CCTrCH-TPCAddList-RL-ReconfPrepTDD	OPTIONAL,
--	iE-Extensions					ProtocolExtensionContainer { {DL-CCTrCH-InformationAddItem-RL-ReconfPrepTDD-ExtIEs} } OPTIONAL,
	iE-Extensions					ProtocolExtensionContainer OPTIONAL,
	...
}

--DL-CCTrCH-InformationAddItem-RL-ReconfPrepTDD-ExtIEs RNSAP-PROTOCOL-EXTENSION ::= {
--{ ID id-TDD-TPC-DownlinkStepSize-InformationAdd-RL-ReconfPrepTDD	CRITICALITY reject	EXTENSION	TDD-TPC-DownlinkStepSize	PRESENCE optional	},
--	...
--}

--CCTrCH-TPCAddList-RL-ReconfPrepTDD ::= SEQUENCE (SIZE (1..maxNrOfCCTrCHs)) OF CCTrCH-TPCAddItem-RL-ReconfPrepTDD
CCTrCH-TPCAddList-RL-ReconfPrepTDD ::= SEQUENCE (SIZE (1..16)) OF CCTrCH-TPCAddItem-RL-ReconfPrepTDD

CCTrCH-TPCAddItem-RL-ReconfPrepTDD	 ::= SEQUENCE {
	cCTrCH-ID						CCTrCH-ID,
--	iE-Extensions					ProtocolExtensionContainer { { CCTrCH-TPCAddItem-RL-ReconfPrepTDD-ExtIEs} } OPTIONAL,
	iE-Extensions					ProtocolExtensionContainer OPTIONAL,
	...
}

--CCTrCH-TPCAddItem-RL-ReconfPrepTDD-ExtIEs RNSAP-PROTOCOL-EXTENSION ::= {
--	...
--}

--DL-CCTrCH-InformationModifyList-RL-ReconfPrepTDD		::= SEQUENCE (SIZE (0..maxNrOfCCTrCHs)) OF ProtocolIE-Single-Container { {DL-CCTrCH-ModifyInformation-RL-ReconfPrepTDD-IEs} }
DL-CCTrCH-InformationModifyList-RL-ReconfPrepTDD		::= SEQUENCE (SIZE (0..16)) OF ProtocolIE-Single-Container

--DL-CCTrCH-ModifyInformation-RL-ReconfPrepTDD-IEs RNSAP-PROTOCOL-IES ::= {
--	{ ID id-DL-CCTrCH-InformationModifyItem-RL-ReconfPrepTDD	CRITICALITY notify	TYPE DL-CCTrCH-InformationModifyItem-RL-ReconfPrepTDD	PRESENCE mandatory	}
--}

DL-CCTrCH-InformationModifyItem-RL-ReconfPrepTDD ::= SEQUENCE {
	cCTrCH-ID					CCTrCH-ID,
	tFCS						TFCS		OPTIONAL,
	tFCI-Coding					TFCI-Coding				OPTIONAL,
	punctureLimit					PunctureLimit				OPTIONAL,
	cCTrCH-TPCList					CCTrCH-TPCModifyList-RL-ReconfPrepTDD		OPTIONAL,
--	iE-Extensions					ProtocolExtensionContainer { {DL-CCTrCH-InformationModifyItem-RL-ReconfPrepTDD-ExtIEs} } OPTIONAL,
	iE-Extensions					ProtocolExtensionContainer OPTIONAL,
	...
}

--DL-CCTrCH-InformationModifyItem-RL-ReconfPrepTDD-ExtIEs RNSAP-PROTOCOL-EXTENSION ::= {
--{ ID id-TDD-TPC-DownlinkStepSize-InformationModify-RL-ReconfPrepTDD	CRITICALITY reject		EXTENSION	TDD-TPC-DownlinkStepSize	PRESENCE optional},
--	...
--}

--CCTrCH-TPCModifyList-RL-ReconfPrepTDD ::= SEQUENCE (SIZE (1..maxNrOfCCTrCHs)) OF CCTrCH-TPCModifyItem-RL-ReconfPrepTDD
CCTrCH-TPCModifyList-RL-ReconfPrepTDD ::= SEQUENCE (SIZE (1..16)) OF CCTrCH-TPCModifyItem-RL-ReconfPrepTDD

CCTrCH-TPCModifyItem-RL-ReconfPrepTDD	 ::= SEQUENCE {
	cCTrCH-ID						CCTrCH-ID,
--	iE-Extensions					ProtocolExtensionContainer { { CCTrCH-TPCModifyItem-RL-ReconfPrepTDD-ExtIEs} } OPTIONAL,
	iE-Extensions					ProtocolExtensionContainer OPTIONAL,
	...
}

--CCTrCH-TPCModifyItem-RL-ReconfPrepTDD-ExtIEs RNSAP-PROTOCOL-EXTENSION ::= {
--	...
--}

--DL-CCTrCH-InformationDeleteList-RL-ReconfPrepTDD		::= SEQUENCE (SIZE (0..maxNrOfCCTrCHs)) OF ProtocolIE-Single-Container { {DL-CCTrCH-DeleteInformation-RL-ReconfPrepTDD-IEs} }
DL-CCTrCH-InformationDeleteList-RL-ReconfPrepTDD		::= SEQUENCE (SIZE (0..16)) OF ProtocolIE-Single-Container

--DL-CCTrCH-DeleteInformation-RL-ReconfPrepTDD-IEs RNSAP-PROTOCOL-IES ::= {
--	{ ID id-DL-CCTrCH-InformationDeleteItem-RL-ReconfPrepTDD	CRITICALITY notify	TYPE DL-CCTrCH-InformationDeleteItem-RL-ReconfPrepTDD	PRESENCE mandatory	}
--}

DL-CCTrCH-InformationDeleteItem-RL-ReconfPrepTDD ::= SEQUENCE {
	cCTrCH-ID					CCTrCH-ID,
--	iE-Extensions					ProtocolExtensionContainer { {DL-CCTrCH-InformationDeleteItem-RL-ReconfPrepTDD-ExtIEs} } OPTIONAL,
	iE-Extensions					ProtocolExtensionContainer OPTIONAL,
	...
}

--DL-CCTrCH-InformationDeleteItem-RL-ReconfPrepTDD-ExtIEs RNSAP-PROTOCOL-EXTENSION ::= {
--	...
--}

--DCH-DeleteList-RL-ReconfPrepTDD				::= SEQUENCE (SIZE (0..maxNrOfDCHs)) OF DCH-DeleteItem-RL-ReconfPrepTDD
DCH-DeleteList-RL-ReconfPrepTDD				::= SEQUENCE (SIZE (0..128)) OF DCH-DeleteItem-RL-ReconfPrepTDD

DCH-DeleteItem-RL-ReconfPrepTDD ::= SEQUENCE {
	dCH-ID						DCH-ID,
--	iE-Extensions				ProtocolExtensionContainer { {DCH-DeleteItem-RL-ReconfPrepTDD-ExtIEs} } OPTIONAL,
	iE-Extensions				ProtocolExtensionContainer OPTIONAL,
	...
}

--DCH-DeleteItem-RL-ReconfPrepTDD-ExtIEs RNSAP-PROTOCOL-EXTENSION ::= {
--	...
--}

--DSCH-ModifyList-RL-ReconfPrepTDD ::= SEQUENCE (SIZE(0..maxNoOfDSCHs)) OF DSCH-ModifyItem-RL-ReconfPrepTDD
DSCH-ModifyList-RL-ReconfPrepTDD ::= SEQUENCE (SIZE(0..128)) OF DSCH-ModifyItem-RL-ReconfPrepTDD

DSCH-ModifyItem-RL-ReconfPrepTDD ::= SEQUENCE {
	dSCH-ID								DSCH-ID,
	dl-ccTrCHID							CCTrCH-ID						OPTIONAL,
	trChSourceStatisticsDescriptor		TrCH-SrcStatisticsDescr	OPTIONAL,
	transportFormatSet					TransportFormatSet				OPTIONAL,
	allocationRetentionPriority 		AllocationRetentionPriority		OPTIONAL,
	schedulingPriorityIndicator			SchedulingPriorityIndicator		OPTIONAL,
	bLER								BLER							OPTIONAL,
	transportBearerRequestIndicator		TransportBearerRequestIndicator,
--	iE-Extensions					ProtocolExtensionContainer { {DSCH-ModifyItem-RL-ReconfPrepTDD-ExtIEs} } OPTIONAL,
	iE-Extensions					ProtocolExtensionContainer OPTIONAL,
	...
}

--DSCH-ModifyItem-RL-ReconfPrepTDD-ExtIEs RNSAP-PROTOCOL-EXTENSION ::= {
--	{ ID id-TrafficClass			CRITICALITY ignore	EXTENSION TrafficClass				PRESENCE optional	}|
--	{ ID id-BindingID						CRITICALITY	ignore		EXTENSION 	BindingID	             PRESENCE  	optional	}|
	-- Shall be ignored if bearer establishment with ALCAP.
  --  { ID id-TransportLayerAddress			CRITICALITY	ignore		EXTENSION 	TransportLayerAddress		PRESENCE 	optional	},
	-- Shall be ignored if bearer establishment with ALCAP.
--	...
--}

--DSCH-DeleteList-RL-ReconfPrepTDD ::= SEQUENCE (SIZE(0..maxNoOfDSCHs)) OF DSCH-DeleteItem-RL-ReconfPrepTDD
DSCH-DeleteList-RL-ReconfPrepTDD ::= SEQUENCE (SIZE(0..128)) OF DSCH-DeleteItem-RL-ReconfPrepTDD

DSCH-DeleteItem-RL-ReconfPrepTDD ::= SEQUENCE {
	dSCH-ID								DSCH-ID,
--	iE-Extensions					ProtocolExtensionContainer { {DSCH-DeleteItem-RL-ReconfPrepTDD-ExtIEs} } OPTIONAL,
	iE-Extensions					ProtocolExtensionContainer OPTIONAL,
	...
}

--DSCH-DeleteItem-RL-ReconfPrepTDD-ExtIEs RNSAP-PROTOCOL-EXTENSION ::= {
--	...
--}

--USCH-ModifyList-RL-ReconfPrepTDD ::= SEQUENCE (SIZE(0..maxNoOfUSCHs)) OF USCH-ModifyItem-RL-ReconfPrepTDD
USCH-ModifyList-RL-ReconfPrepTDD ::= SEQUENCE (SIZE(0..10)) OF USCH-ModifyItem-RL-ReconfPrepTDD

USCH-ModifyItem-RL-ReconfPrepTDD ::= SEQUENCE {
	uSCH-ID								USCH-ID,
	ul-ccTrCHID							CCTrCH-ID						OPTIONAL,
	trChSourceStatisticsDescriptor		TrCH-SrcStatisticsDescr	OPTIONAL,
	transportFormatSet					TransportFormatSet				OPTIONAL,
	allocationRetentionPriority 		AllocationRetentionPriority		OPTIONAL,
	schedulingPriorityIndicator			SchedulingPriorityIndicator		OPTIONAL,
	bLER								BLER							OPTIONAL,
	transportBearerRequestIndicator		TransportBearerRequestIndicator,
	rb-Info								RB-Info							OPTIONAL,
--	iE-Extensions						ProtocolExtensionContainer { {USCH-ModifyItem-RL-ReconfPrepTDD-ExtIEs} } OPTIONAL,
	iE-Extensions						ProtocolExtensionContainer OPTIONAL,
	...
}

--USCH-ModifyItem-RL-ReconfPrepTDD-ExtIEs RNSAP-PROTOCOL-EXTENSION ::= {
--	{ ID id-TrafficClass			CRITICALITY ignore	EXTENSION TrafficClass				PRESENCE optional	}|
--	{ ID id-BindingID				CRITICALITY	ignore	EXTENSION 	BindingID	PRESENCE 		optional	}|
	-- Shall be ignored if bearer establishment with ALCAP.
--	{ ID id-TransportLayerAddress			CRITICALITY	ignore		EXTENSION 	TransportLayerAddress		PRESENCE 	optional	}|
	-- Shall be ignored if bearer establishment with ALCAP.
--	{ ID id-TnlQos						CRITICALITY 	ignore		EXTENSION 	TnlQos		PRESENCE 		optional	},
--	...
--}

--USCH-DeleteList-RL-ReconfPrepTDD ::= SEQUENCE (SIZE(0..maxNoOfUSCHs)) OF USCH-DeleteItem-RL-ReconfPrepTDD
USCH-DeleteList-RL-ReconfPrepTDD ::= SEQUENCE (SIZE(0..10)) OF USCH-DeleteItem-RL-ReconfPrepTDD

USCH-DeleteItem-RL-ReconfPrepTDD ::= SEQUENCE {
	uSCH-ID								USCH-ID,
--	iE-Extensions					ProtocolExtensionContainer { {USCH-DeleteItem-RL-ReconfPrepTDD-ExtIEs} } OPTIONAL,
	iE-Extensions					ProtocolExtensionContainer OPTIONAL,
	...
}

--USCH-DeleteItem-RL-ReconfPrepTDD-ExtIEs RNSAP-PROTOCOL-EXTENSION ::= {
--	...
--}

--RadioLinkReconfigurationPrepareTDD-Extensions RNSAP-PROTOCOL-EXTENSION ::= {
--	{ ID id-PrimaryCCPCH-RSCP-RL-ReconfPrepTDD					CRITICALITY ignore		EXTENSION 	PrimaryCCPCH-RSCP	PRESENCE optional	}|
--	{ ID id-DL-TimeSlot-ISCP-Info-RL-ReconfPrepTDD				CRITICALITY ignore		EXTENSION 	DL-TimeSlot-ISCP-Info	PRESENCE optional	}|
--	{ ID id-DL-Timeslot-ISCP-LCR-Information-RL-ReconfPrepTDD	CRITICALITY ignore		EXTENSION 	DL-TimeSlot-ISCP-LCR-Information	PRESENCE optional	}|
--	{ ID id-HSDSCH-TDD-Information								CRITICALITY reject		EXTENSION HSDSCH-TDD-Information		PRESENCE optional}|
--	{ ID id-HSDSCH-Information-to-Modify						CRITICALITY reject		EXTENSION HSDSCH-Information-to-Modify		PRESENCE optional}|
--	{ ID id-HSDSCH-MACdFlows-to-Add				CRITICALITY reject		EXTENSION HSDSCH-MACdFlows-Information			PRESENCE optional}|
--	{ ID id-HSDSCH-MACdFlows-to-Delete			CRITICALITY reject		EXTENSION HSDSCH-MACdFlows-to-Delete	PRESENCE optional}|
--	{ ID id-HSPDSCH-RL-ID						CRITICALITY reject		EXTENSION RL-ID					PRESENCE optional}|
--	{ ID id-PDSCH-RL-ID				CRITICALITY ignore			EXTENSION RL-ID		PRESENCE optional }|
--	{ ID id-UL-Synchronisation-Parameters-LCR			CRITICALITY	ignore		EXTENSION 	UL-Synchronisation-Parameters-LCR		PRESENCE 	optional	}|
	-- Mandatory for 1.28Mcps TDD, Not Applicable to 3.84Mcps TDD
--	{ ID id-RL-Information-RL-ReconfPrepTDD		CRITICALITY	ignore		EXTENSION 	RL-Information-RL-ReconfPrepTDD		PRESENCE 	optional	}|
--	{ ID id-PrimaryCCPCH-RSCP-Delta		CRITICALITY	ignore		EXTENSION 	PrimaryCCPCH-RSCP-Delta		PRESENCE 	optional	},
--	...
--}


--RL-Information-RL-ReconfPrepTDD ::= SEQUENCE (SIZE (1..maxNrOfRLs)) OF RL-InformationIE-RL-ReconfPrepTDD
RL-Information-RL-ReconfPrepTDD ::= SEQUENCE (SIZE (1..16)) OF RL-InformationIE-RL-ReconfPrepTDD

RL-InformationIE-RL-ReconfPrepTDD ::= SEQUENCE {
	rL-ID								RL-ID,
	rL-Specific-DCH-Info				RL-Specific-DCH-Info			OPTIONAL,
--	iE-Extensions						ProtocolExtensionContainer { { RL-InformationIE-RL-ReconfPrepTDD-ExtIEs} }		OPTIONAL,
	iE-Extensions						ProtocolExtensionContainer OPTIONAL,
	...
}

--RL-InformationIE-RL-ReconfPrepTDD-ExtIEs RNSAP-PROTOCOL-EXTENSION ::= {
--	...
--}

-- **************************************************************
--
-- RADIO LINK RECONFIGURATION READY FDD
--
-- **************************************************************

--RadioLinkReconfigurationReadyFDD ::= SEQUENCE {
--	protocolIEs                     ProtocolIE-Container       {{RadioLinkReconfigurationReadyFDD-IEs}},
--	protocolExtensions              ProtocolExtensionContainer {{RadioLinkReconfigurationReadyFDD-Extensions}}                   OPTIONAL,
--	...
--}
RadioLinkReconfigurationReadyFDD ::= SEQUENCE {
	protocolIEs                     ProtocolIE-Container,
	protocolExtensions              ProtocolExtensionContainer OPTIONAL,
	...
}

--RadioLinkReconfigurationReadyFDD-IEs RNSAP-PROTOCOL-IES ::= {
--	{ ID id-RL-InformationResponseList-RL-ReconfReadyFDD	CRITICALITY ignore	TYPE RL-InformationResponseList-RL-ReconfReadyFDD		PRESENCE optional	} |
--	{ ID id-CriticalityDiagnostics			CRITICALITY ignore	TYPE CriticalityDiagnostics			PRESENCE optional	},
--	...
--}

--RL-InformationResponseList-RL-ReconfReadyFDD		::= SEQUENCE (SIZE (0..maxNrOfRLs)) OF ProtocolIE-Single-Container { {RL-InformationResponse-RL-ReconfReadyFDD-IEs} }
RL-InformationResponseList-RL-ReconfReadyFDD		::= SEQUENCE (SIZE (0..16)) OF ProtocolIE-Single-Container

--RL-InformationResponse-RL-ReconfReadyFDD-IEs RNSAP-PROTOCOL-IES ::= {
--	{ ID id-RL-InformationResponseItem-RL-ReconfReadyFDD	CRITICALITY ignore	TYPE RL-InformationResponseItem-RL-ReconfReadyFDD		PRESENCE mandatory	}
--}

RL-InformationResponseItem-RL-ReconfReadyFDD ::= SEQUENCE {
	rL-ID								RL-ID,
	max-UL-SIR							UL-SIR			OPTIONAL,
	min-UL-SIR							UL-SIR			OPTIONAL,
	maximumDLTxPower					DL-Power		OPTIONAL,
	minimumDLTxPower					DL-Power		OPTIONAL,
	not-Used-secondary-CCPCH-Info				NULL		OPTIONAL,
	dl-CodeInformationList				DL-CodeInformationList-RL-ReconfReadyFDD		OPTIONAL,
	dCHInformationResponse				DCH-InformationResponseList-RL-ReconfReadyFDD	OPTIONAL,
	not-Used-dSCHsToBeAddedOrModified	NULL			OPTIONAL,
--	iE-Extensions						ProtocolExtensionContainer { {RL-InformationResponseItem-RL-ReconfReadyFDD-ExtIEs} } OPTIONAL,
	iE-Extensions						ProtocolExtensionContainer OPTIONAL,
	...
}

--RL-InformationResponseItem-RL-ReconfReadyFDD-ExtIEs RNSAP-PROTOCOL-EXTENSION ::= {
--	{ ID id-DL-PowerBalancing-UpdatedIndicator			CRITICALITY ignore	EXTENSION DL-PowerBalancing-UpdatedIndicator		PRESENCE optional}|
--	{ ID id-Primary-CPICH-Usage-For-Channel-Estimation	CRITICALITY ignore	EXTENSION Primary-CPICH-Usage-For-Channel-Estimation	PRESENCE optional }|
--	{ ID id-Secondary-CPICH-Information-Change			CRITICALITY ignore	EXTENSION Secondary-CPICH-Information-Change				PRESENCE optional }|
--	{ ID id-EDCH-FDD-InformationResponse				CRITICALITY ignore	EXTENSION EDCH-FDD-InformationResponse						PRESENCE optional }|
--	{ ID id-EDCH-RLSet-Id								CRITICALITY ignore	EXTENSION RL-Set-ID													PRESENCE optional }|
--	{ ID id-EDCH-FDD-DL-ControlChannelInformation		CRITICALITY ignore	EXTENSION EDCH-FDD-DL-ControlChannelInformation			PRESENCE optional },
--...
--}

--DL-CodeInformationList-RL-ReconfReadyFDD ::= ProtocolIE-Single-Container {{ DL-CodeInformationListIEs-RL-ReconfReadyFDD }}
DL-CodeInformationList-RL-ReconfReadyFDD ::= ProtocolIE-Single-Container

--DL-CodeInformationListIEs-RL-ReconfReadyFDD RNSAP-PROTOCOL-IES ::= {
--	{ ID id-FDD-DL-CodeInformation   CRITICALITY ignore	TYPE FDD-DL-CodeInformation		PRESENCE mandatory }
--}

--DCH-InformationResponseList-RL-ReconfReadyFDD				::= ProtocolIE-Single-Container { {DCH-InformationResponseListIEs-RL-ReconfReadyFDD} }
DCH-InformationResponseList-RL-ReconfReadyFDD				::= ProtocolIE-Single-Container

--DCH-InformationResponseListIEs-RL-ReconfReadyFDD RNSAP-PROTOCOL-IES ::= {
--	{ ID id-DCH-InformationResponse		CRITICALITY ignore	TYPE DCH-InformationResponse		PRESENCE mandatory	}
--}

--RadioLinkReconfigurationReadyFDD-Extensions RNSAP-PROTOCOL-EXTENSION ::= {
--	{ ID id-HSDSCH-RNTI							CRITICALITY ignore		EXTENSION HSDSCH-RNTI									PRESENCE optional }|
--	{ ID id-HSDSCH-FDD-Information-Response		CRITICALITY ignore		EXTENSION HSDSCH-FDD-Information-Response		PRESENCE optional }|
--	{ ID id-MAChs-ResetIndicator				CRITICALITY ignore		EXTENSION MAChs-ResetIndicator						PRESENCE optional },
--	...
--}

-- **************************************************************
--
-- RADIO LINK RECONFIGURATION READY TDD
--
-- **************************************************************

--RadioLinkReconfigurationReadyTDD ::= SEQUENCE {
--	protocolIEs                     ProtocolIE-Container       {{RadioLinkReconfigurationReadyTDD-IEs}},
--	protocolExtensions              ProtocolExtensionContainer {{RadioLinkReconfigurationReadyTDD-Extensions}}                   OPTIONAL,
--	...
--}
RadioLinkReconfigurationReadyTDD ::= SEQUENCE {
	protocolIEs                     ProtocolIE-Container,
	protocolExtensions              ProtocolExtensionContainer OPTIONAL,
	...
}

--RadioLinkReconfigurationReadyTDD-IEs RNSAP-PROTOCOL-IES ::= {
--	{ ID id-RL-InformationResponse-RL-ReconfReadyTDD
--							CRITICALITY ignore	TYPE RL-InformationResponse-RL-ReconfReadyTDD	PRESENCE optional	} |
	--This RL-InformationResponse-RL-ReconfReadyTDD is for the first RL repetition in the list.
	--Repetitions 2 and on are defined in Multiple-RL-InformationResponse-RL-ReconfReadyTDD.
--	{ ID id-CriticalityDiagnostics			CRITICALITY ignore	TYPE CriticalityDiagnostics			PRESENCE optional	},
--	...
--}

RL-InformationResponse-RL-ReconfReadyTDD ::= SEQUENCE {
	rL-ID							RL-ID,
	max-UL-SIR						UL-SIR			OPTIONAL,
	min-UL-SIR						UL-SIR			OPTIONAL,
	maximumDLTxPower				DL-Power		OPTIONAL,
	minimumDLTxPower				DL-Power		OPTIONAL,
	secondary-CCPCH-Info-TDD		Secondary-CCPCH-Info-TDD	OPTIONAL,
	ul-CCTrCH-Information			UL-CCTrCH-InformationList-RL-ReconfReadyTDD 	OPTIONAL,
	dl-CCTrCH-Information			DL-CCTrCH-InformationList-RL-ReconfReadyTDD	OPTIONAL,
	dCHInformationResponse			DCH-InformationResponseList-RL-ReconfReadyTDD	OPTIONAL,
	dSCHsToBeAddedOrModified		DSCHToBeAddedOrModified-RL-ReconfReadyTDD	OPTIONAL,
	uSCHsToBeAddedOrModified		USCHToBeAddedOrModified-RL-ReconfReadyTDD	OPTIONAL,
--	iE-Extensions					ProtocolExtensionContainer { {RL-InformationResponse-RL-ReconfReadyTDD-ExtIEs} } OPTIONAL,
	iE-Extensions					ProtocolExtensionContainer OPTIONAL,
	...
}

--RL-InformationResponse-RL-ReconfReadyTDD-ExtIEs RNSAP-PROTOCOL-EXTENSION ::= {
--	{ ID id-UL-TimingAdvanceCtrl-LCR			CRITICALITY ignore	EXTENSION	UL-TimingAdvanceCtrl-LCR		PRESENCE optional },
	--For 1.28Mcps TDD only
--	...
--}

--UL-CCTrCH-InformationList-RL-ReconfReadyTDD 		::= ProtocolIE-Single-Container {{UL-CCTrCHInformationListIEs-RL-ReconfReadyTDD}}
UL-CCTrCH-InformationList-RL-ReconfReadyTDD 		::= ProtocolIE-Single-Container

--UL-CCTrCHInformationListIEs-RL-ReconfReadyTDD RNSAP-PROTOCOL-IES ::= {
--	{ ID id-UL-CCTrCH-InformationListIE-RL-ReconfReadyTDD   CRITICALITY ignore	TYPE UL-CCTrCHInformationListIE-RL-ReconfReadyTDD		PRESENCE mandatory }
--}

--UL-CCTrCHInformationListIE-RL-ReconfReadyTDD ::= SEQUENCE (SIZE (0..maxNrOfCCTrCHs)) OF UL-CCTrCH-InformationItem-RL-ReconfReadyTDD
UL-CCTrCHInformationListIE-RL-ReconfReadyTDD ::= SEQUENCE (SIZE (0..16)) OF UL-CCTrCH-InformationItem-RL-ReconfReadyTDD

UL-CCTrCH-InformationItem-RL-ReconfReadyTDD ::= SEQUENCE {
	cCTrCH-ID						CCTrCH-ID,
	ul-DPCH-AddInformation			UL-DPCH-InformationAddList-RL-ReconfReadyTDD			OPTIONAL,
	--For 3.84Mcps TDD only
	ul-DPCH-ModifyInformation		UL-DPCH-InformationModifyList-RL-ReconfReadyTDD				OPTIONAL,
	--For 3.84Mcps TDD only
	ul-DPCH-DeleteInformation		UL-DPCH-InformationDeleteList-RL-ReconfReadyTDD				OPTIONAL,
--	iE-Extensions					ProtocolExtensionContainer { {UL-CCTrCH-InformationItem-RL-ReconfReadyTDD-ExtIEs} } OPTIONAL,
	iE-Extensions					ProtocolExtensionContainer OPTIONAL,
	...
}

--UL-CCTrCH-InformationItem-RL-ReconfReadyTDD-ExtIEs RNSAP-PROTOCOL-EXTENSION ::= {
--	{ ID id-UL-DPCH-LCR-InformationAddListIE-RL-ReconfReadyTDD   CRITICALITY ignore		EXTENSION 	UL-DPCH-LCR-InformationAddList-RL-ReconfReadyTDD		PRESENCE optional },
	--For 1.28Mcps TDD only
--	...
--}

UL-DPCH-LCR-InformationAddList-RL-ReconfReadyTDD ::= SEQUENCE {
	repetitionPeriod				RepetitionPeriod,
	repetitionLength				RepetitionLength,
	tDD-DPCHOffset					TDD-DPCHOffset,
	uL-TimeslotLCR-Info             UL-TimeslotLCR-Information,
--	iE-Extensions					ProtocolExtensionContainer { {UL-DPCH-LCR-InformationAddItem-RL-ReconfReadyTDD-ExtIEs} } OPTIONAL,
	iE-Extensions					ProtocolExtensionContainer OPTIONAL,
	...
}

--UL-DPCH-LCR-InformationAddItem-RL-ReconfReadyTDD-ExtIEs RNSAP-PROTOCOL-EXTENSION ::= {
--	...
--}

--UL-DPCH-InformationAddList-RL-ReconfReadyTDD ::= ProtocolIE-Single-Container {{UL-DPCH-InformationAddListIEs-RL-ReconfReadyTDD}}
UL-DPCH-InformationAddList-RL-ReconfReadyTDD ::= ProtocolIE-Single-Container

--UL-DPCH-InformationAddListIEs-RL-ReconfReadyTDD RNSAP-PROTOCOL-IES ::= {
--	{ ID id-UL-DPCH-InformationAddListIE-RL-ReconfReadyTDD   CRITICALITY ignore	TYPE UL-DPCH-InformationAddListIE-RL-ReconfReadyTDD		PRESENCE optional }
--}

UL-DPCH-InformationAddListIE-RL-ReconfReadyTDD ::= SEQUENCE {
	repetitionPeriod				RepetitionPeriod,
	repetitionLength				RepetitionLength,
	tDD-DPCHOffset					TDD-DPCHOffset,
	rxTimingDeviationForTA			RxTimingDeviationForTA			OPTIONAL,
	uL-Timeslot-Information			UL-Timeslot-Information,
--	iE-Extensions					ProtocolExtensionContainer { {UL-DPCH-InformationAddItem-RL-ReconfReadyTDD-ExtIEs} } OPTIONAL,
	iE-Extensions					ProtocolExtensionContainer OPTIONAL,
	...
}

--UL-DPCH-InformationAddItem-RL-ReconfReadyTDD-ExtIEs RNSAP-PROTOCOL-EXTENSION ::= {
--	...
--}

--UL-DPCH-InformationModifyList-RL-ReconfReadyTDD ::= ProtocolIE-Single-Container {{UL-DPCH-InformationModifyListIEs-RL-ReconfReadyTDD}}
UL-DPCH-InformationModifyList-RL-ReconfReadyTDD ::= ProtocolIE-Single-Container

--UL-DPCH-InformationModifyListIEs-RL-ReconfReadyTDD RNSAP-PROTOCOL-IES ::= {
--	{ ID id-UL-DPCH-InformationModifyListIE-RL-ReconfReadyTDD   CRITICALITY ignore	TYPE UL-DPCH-InformationModifyListIE-RL-ReconfReadyTDD		PRESENCE mandatory }
--}

UL-DPCH-InformationModifyListIE-RL-ReconfReadyTDD::= SEQUENCE {
	repetitionPeriod				RepetitionPeriod			OPTIONAL,
	repetitionLength				RepetitionLength			OPTIONAL,
	tDD-DPCHOffset					TDD-DPCHOffset				OPTIONAL,
	uL-Timeslot-InformationModifyList-RL-ReconfReadyTDD			UL-Timeslot-InformationModifyList-RL-ReconfReadyTDD			OPTIONAL,
	--For 3.84Mcps TDD only
--	iE-Extensions					ProtocolExtensionContainer { {UL-DPCH-InformationModifyItem-RL-ReconfReadyTDD-ExtIEs} } OPTIONAL,
	iE-Extensions					ProtocolExtensionContainer OPTIONAL,
	...
}

--UL-DPCH-InformationModifyItem-RL-ReconfReadyTDD-ExtIEs RNSAP-PROTOCOL-EXTENSION ::= {
--	{ ID id-UL-Timeslot-LCR-InformationModifyList-RL-ReconfReadyTDD   CRITICALITY ignore	EXTENSION  UL-TimeslotLCR-InformationModifyList-RL-ReconfReadyTDD		PRESENCE optional },
	--For 1.28Mcps TDD only
--	...
--}

--UL-TimeslotLCR-InformationModifyList-RL-ReconfReadyTDD::= SEQUENCE ( SIZE (1..maxNrOfTsLCR)) OF UL-TimeslotLCR-InformationModifyItem-RL-ReconfReadyTDD
UL-TimeslotLCR-InformationModifyList-RL-ReconfReadyTDD::= SEQUENCE ( SIZE (1..6)) OF UL-TimeslotLCR-InformationModifyItem-RL-ReconfReadyTDD

UL-TimeslotLCR-InformationModifyItem-RL-ReconfReadyTDD ::= SEQUENCE {
	timeSlotLCR						TimeSlotLCR,
	midambleShiftLCR				MidambleShiftLCR			OPTIONAL,
	tFCI-Presence					TFCI-Presence			OPTIONAL,
	tDD-uL-Code-LCR-Information			TDD-UL-Code-LCR-InformationModifyList-RL-ReconfReadyTDD			OPTIONAL,
--	iE-Extensions					ProtocolExtensionContainer { {UL-TimeslotLCR-InformationModifyItem-RL-ReconfReadyTDD-ExtIEs} } OPTIONAL,
	iE-Extensions					ProtocolExtensionContainer OPTIONAL,
	...
}

--TDD-UL-Code-LCR-InformationModifyList-RL-ReconfReadyTDD::= SEQUENCE ( SIZE (1..maxNrOfDPCHsLCR)) OF TDD-UL-Code-LCR-InformationModifyItem-RL-ReconfReadyTDD
TDD-UL-Code-LCR-InformationModifyList-RL-ReconfReadyTDD::= SEQUENCE ( SIZE (1..240)) OF TDD-UL-Code-LCR-InformationModifyItem-RL-ReconfReadyTDD

TDD-UL-Code-LCR-InformationModifyItem-RL-ReconfReadyTDD ::= SEQUENCE {
	dPCH-ID							DPCH-ID,
	tDD-ChannelisationCodeLCR			TDD-ChannelisationCodeLCR		OPTIONAL,
--	iE-Extensions					ProtocolExtensionContainer { {TDD-UL-Code-LCR-InformationModifyItem-RL-ReconfReadyTDD-ExtIEs} } OPTIONAL,
	iE-Extensions					ProtocolExtensionContainer OPTIONAL,
	...
}

--TDD-UL-Code-LCR-InformationModifyItem-RL-ReconfReadyTDD-ExtIEs RNSAP-PROTOCOL-EXTENSION ::= {
--{ ID id-TDD-UL-DPCH-TimeSlotFormatModifyItem-LCR-RL-ReconfReadyTDD	 CRITICALITY	reject	 EXTENSION TDD-UL-DPCH-TimeSlotFormat-LCR   PRESENCE  optional},
--	...
--}

--UL-TimeslotLCR-InformationModifyItem-RL-ReconfReadyTDD-ExtIEs RNSAP-PROTOCOL-EXTENSION ::= {
--	...
--}

--UL-Timeslot-InformationModifyList-RL-ReconfReadyTDD::= SEQUENCE ( SIZE (1..maxNrOfTS)) OF UL-Timeslot-InformationModifyItem-RL-ReconfReadyTDD
UL-Timeslot-InformationModifyList-RL-ReconfReadyTDD::= SEQUENCE ( SIZE (1..15)) OF UL-Timeslot-InformationModifyItem-RL-ReconfReadyTDD

UL-Timeslot-InformationModifyItem-RL-ReconfReadyTDD ::= SEQUENCE {
	timeSlot						TimeSlot,
	midambleShiftAndBurstType					MidambleShiftAndBurstType			OPTIONAL,
	tFCI-Presence					TFCI-Presence			OPTIONAL,
	uL-Code-Information			TDD-UL-Code-InformationModifyList-RL-ReconfReadyTDD			OPTIONAL,
--	iE-Extensions					ProtocolExtensionContainer { {UL-Timeslot-InformationModifyItem-RL-ReconfReadyTDD-ExtIEs} } OPTIONAL,
	iE-Extensions					ProtocolExtensionContainer OPTIONAL,
	...
}

--UL-Timeslot-InformationModifyItem-RL-ReconfReadyTDD-ExtIEs RNSAP-PROTOCOL-EXTENSION ::= {
--	...
--}

--TDD-UL-Code-InformationModifyList-RL-ReconfReadyTDD::= SEQUENCE ( SIZE (1..maxNrOfDPCHs)) OF TDD-UL-Code-InformationModifyItem-RL-ReconfReadyTDD
TDD-UL-Code-InformationModifyList-RL-ReconfReadyTDD::= SEQUENCE ( SIZE (1..240)) OF TDD-UL-Code-InformationModifyItem-RL-ReconfReadyTDD

TDD-UL-Code-InformationModifyItem-RL-ReconfReadyTDD ::= SEQUENCE {
	dPCH-ID							DPCH-ID,
	tDD-ChannelisationCode			TDD-ChannelisationCode		OPTIONAL,
--	iE-Extensions					ProtocolExtensionContainer { {TDD-UL-Code-InformationModifyItem-RL-ReconfReadyTDD-ExtIEs} } OPTIONAL,
	iE-Extensions					ProtocolExtensionContainer OPTIONAL,
	...
}

--TDD-UL-Code-InformationModifyItem-RL-ReconfReadyTDD-ExtIEs RNSAP-PROTOCOL-EXTENSION ::= {
--	...
--}

--UL-DPCH-InformationDeleteList-RL-ReconfReadyTDD ::= ProtocolIE-Single-Container {{UL-DPCH-InformationDeleteListIEs-RL-ReconfReadyTDD}}
UL-DPCH-InformationDeleteList-RL-ReconfReadyTDD ::= ProtocolIE-Single-Container

--UL-DPCH-InformationDeleteListIEs-RL-ReconfReadyTDD RNSAP-PROTOCOL-IES ::= {
--	{ ID id-UL-DPCH-InformationDeleteListIE-RL-ReconfReadyTDD   CRITICALITY ignore	TYPE UL-DPCH-InformationDeleteListIE-RL-ReconfReadyTDD		PRESENCE mandatory }
--}

--UL-DPCH-InformationDeleteListIE-RL-ReconfReadyTDD ::= SEQUENCE (SIZE (0..maxNrOfDPCHs)) OF UL-DPCH-InformationDeleteItem-RL-ReconfReadyTDD
UL-DPCH-InformationDeleteListIE-RL-ReconfReadyTDD ::= SEQUENCE (SIZE (0..240)) OF UL-DPCH-InformationDeleteItem-RL-ReconfReadyTDD

UL-DPCH-InformationDeleteItem-RL-ReconfReadyTDD ::= SEQUENCE {
	dPCH-ID						DPCH-ID,
--	iE-Extensions					ProtocolExtensionContainer { {UL-DPCH-InformationDeleteList-RL-ReconfReadyTDD-ExtIEs} } OPTIONAL,
	iE-Extensions					ProtocolExtensionContainer OPTIONAL,
	...
}

--UL-DPCH-InformationDeleteList-RL-ReconfReadyTDD-ExtIEs RNSAP-PROTOCOL-EXTENSION ::= {
--	...
--}

--DL-CCTrCH-InformationList-RL-ReconfReadyTDD 		::= ProtocolIE-Single-Container {{DL-CCTrCHInformationListIEs-RL-ReconfReadyTDD}} 
DL-CCTrCH-InformationList-RL-ReconfReadyTDD 		::= ProtocolIE-Single-Container

--DL-CCTrCHInformationListIEs-RL-ReconfReadyTDD RNSAP-PROTOCOL-IES ::= {
--	{ ID id-DL-CCTrCH-InformationListIE-RL-ReconfReadyTDD   CRITICALITY ignore	TYPE DL-CCTrCHInformationListIE-RL-ReconfReadyTDD		PRESENCE mandatory }
--}

--DL-CCTrCHInformationListIE-RL-ReconfReadyTDD ::= SEQUENCE (SIZE (0..maxNrOfCCTrCHs)) OF DL-CCTrCH-InformationItem-RL-ReconfReadyTDD
DL-CCTrCHInformationListIE-RL-ReconfReadyTDD ::= SEQUENCE (SIZE (0..16)) OF DL-CCTrCH-InformationItem-RL-ReconfReadyTDD

DL-CCTrCH-InformationItem-RL-ReconfReadyTDD ::= SEQUENCE {
	cCTrCH-ID						CCTrCH-ID,
	dl-DPCH-AddInformation			DL-DPCH-InformationAddList-RL-ReconfReadyTDD			OPTIONAL,
	--For 3.84Mcps TDD only
	dl-DPCH-ModifyInformation		DL-DPCH-InformationModifyList-RL-ReconfReadyTDD			OPTIONAL,
	--For 3.84Mcps TDD only
	dl-DPCH-DeleteInformation		DL-DPCH-InformationDeleteList-RL-ReconfReadyTDD			OPTIONAL,
--	iE-Extensions					ProtocolExtensionContainer { {DL-CCTrCH-InformationItem-RL-ReconfReadyTDD-ExtIEs} } OPTIONAL,
	iE-Extensions					ProtocolExtensionContainer OPTIONAL,
	...
}

--DL-CCTrCH-InformationItem-RL-ReconfReadyTDD-ExtIEs RNSAP-PROTOCOL-EXTENSION ::= {
--	{ ID id-DL-DPCH-LCR-InformationAddListIE-RL-ReconfReadyTDD   CRITICALITY ignore			EXTENSION	 DL-DPCH-LCR-InformationAddList-RL-ReconfReadyTDD		PRESENCE  optional}|
	--For 1.28Mcps TDD only
--	{ ID id-CCTrCH-Maximum-DL-Power-RL-ReconfReadyTDD		CRITICALITY ignore	EXTENSION DL-Power	PRESENCE optional	}|
	-- Applicable to 3.84Mcps TDD only, this is a DCH type CCTrCH power
--	{ ID id-CCTrCH-Minimum-DL-Power-RL-ReconfReadyTDD		CRITICALITY ignore	EXTENSION DL-Power	PRESENCE optional	},
	-- Applicable to 3.84Mcps TDD only, this is a DCH type CCTrCH power
--	...
--}

DL-DPCH-LCR-InformationAddList-RL-ReconfReadyTDD ::= SEQUENCE {
	repetitionPeriod				RepetitionPeriod,
	repetitionLength				RepetitionLength,
	tDD-DPCHOffset					TDD-DPCHOffset,
	dL-TimeslotLCR-Info             DL-TimeslotLCR-Information,
--	iE-Extensions					ProtocolExtensionContainer { {DL-DPCH-LCR-InformationAddItem-RL-ReconfReadyTDD-ExtIEs} } OPTIONAL,
	iE-Extensions					ProtocolExtensionContainer OPTIONAL,
	...
}

--DL-DPCH-LCR-InformationAddItem-RL-ReconfReadyTDD-ExtIEs RNSAP-PROTOCOL-EXTENSION ::= {
--	...
--}

--DL-DPCH-InformationAddList-RL-ReconfReadyTDD ::= ProtocolIE-Single-Container {{DL-DPCH-InformationAddListIEs-RL-ReconfReadyTDD}}
DL-DPCH-InformationAddList-RL-ReconfReadyTDD ::= ProtocolIE-Single-Container

--DL-DPCH-InformationAddListIEs-RL-ReconfReadyTDD RNSAP-PROTOCOL-IES ::= {
--	{ ID id-DL-DPCH-InformationAddListIE-RL-ReconfReadyTDD   CRITICALITY ignore	TYPE DL-DPCH-InformationAddListIE-RL-ReconfReadyTDD		PRESENCE mandatory }
--}

DL-DPCH-InformationAddListIE-RL-ReconfReadyTDD ::= SEQUENCE {
	repetitionPeriod				RepetitionPeriod,
	repetitionLength				RepetitionLength,
	tDD-DPCHOffset					TDD-DPCHOffset,
	dL-Timeslot-Information			DL-Timeslot-Information,
--	iE-Extensions					ProtocolExtensionContainer { {DL-DPCH-InformationAddItem-RL-ReconfReadyTDD-ExtIEs} } OPTIONAL,
	iE-Extensions					ProtocolExtensionContainer OPTIONAL,
	...
}

--DL-DPCH-InformationAddItem-RL-ReconfReadyTDD-ExtIEs RNSAP-PROTOCOL-EXTENSION ::= {
--	...
--}

--DL-DPCH-InformationModifyList-RL-ReconfReadyTDD ::= ProtocolIE-Single-Container {{DL-DPCH-InformationModifyListIEs-RL-ReconfReadyTDD}}
DL-DPCH-InformationModifyList-RL-ReconfReadyTDD ::= ProtocolIE-Single-Container

--DL-DPCH-InformationModifyListIEs-RL-ReconfReadyTDD RNSAP-PROTOCOL-IES ::= {
--	{ ID id-DL-DPCH-InformationModifyListIE-RL-ReconfReadyTDD   CRITICALITY ignore	TYPE DL-DPCH-InformationModifyListIE-RL-ReconfReadyTDD		PRESENCE mandatory }
--}

DL-DPCH-InformationModifyListIE-RL-ReconfReadyTDD ::= SEQUENCE {
	repetitionPeriod				RepetitionPeriod			OPTIONAL,
	repetitionLength				RepetitionLength			OPTIONAL,
	tDD-DPCHOffset					TDD-DPCHOffset				OPTIONAL,
	dL-Timeslot-InformationModifyList-RL-ReconfReadyTDD			DL-Timeslot-InformationModifyList-RL-ReconfReadyTDD			OPTIONAL,
	--For 3.84Mcps TDD only
--	iE-Extensions					ProtocolExtensionContainer { {DL-DPCH-InformationModifyItem-RL-ReconfReadyTDD-ExtIEs} } OPTIONAL,
	iE-Extensions					ProtocolExtensionContainer OPTIONAL,
	...
}

--DL-DPCH-InformationModifyItem-RL-ReconfReadyTDD-ExtIEs RNSAP-PROTOCOL-EXTENSION ::= {
--	{ ID id-DL-Timeslot-LCR-InformationModifyList-RL-ReconfReadyTDD   CRITICALITY ignore	EXTENSION  DL-TimeslotLCR-InformationModifyList-RL-ReconfReadyTDD		PRESENCE optional },
	--For 1.28Mcps TDD only
--	...
--}

--DL-TimeslotLCR-InformationModifyList-RL-ReconfReadyTDD::= SEQUENCE ( SIZE (1..maxNrOfTsLCR)) OF DL-TimeslotLCR-InformationModifyItem-RL-ReconfReadyTDD
DL-TimeslotLCR-InformationModifyList-RL-ReconfReadyTDD::= SEQUENCE ( SIZE (1..6)) OF DL-TimeslotLCR-InformationModifyItem-RL-ReconfReadyTDD

DL-TimeslotLCR-InformationModifyItem-RL-ReconfReadyTDD ::= SEQUENCE {
	timeSlotLCR						TimeSlotLCR,
	midambleShiftLCR				MidambleShiftLCR			OPTIONAL,
	tFCI-Presence					TFCI-Presence			OPTIONAL,
	tDD-dL-Code-LCR-Information		TDD-DL-Code-LCR-InformationModifyList-RL-ReconfReadyTDD			OPTIONAL,
--	iE-Extensions					ProtocolExtensionContainer { {DL-TimeslotLCR-InformationModifyItem-RL-ReconfReadyTDD-ExtIEs} } OPTIONAL,
	iE-Extensions					ProtocolExtensionContainer OPTIONAL,
	...
}

--TDD-DL-Code-LCR-InformationModifyList-RL-ReconfReadyTDD::= SEQUENCE ( SIZE (1..maxNrOfDPCHsLCR)) OF TDD-DL-Code-LCR-InformationModifyItem-RL-ReconfReadyTDD
TDD-DL-Code-LCR-InformationModifyList-RL-ReconfReadyTDD::= SEQUENCE ( SIZE (1..240)) OF TDD-DL-Code-LCR-InformationModifyItem-RL-ReconfReadyTDD

TDD-DL-Code-LCR-InformationModifyItem-RL-ReconfReadyTDD ::= SEQUENCE {
	dPCH-ID							DPCH-ID,
	tDD-ChannelisationCodeLCR		TDD-ChannelisationCodeLCR		OPTIONAL,
--	iE-Extensions					ProtocolExtensionContainer { {TDD-DL-Code-LCR-InformationModifyItem-RL-ReconfReadyTDD-ExtIEs} } OPTIONAL,
	iE-Extensions					ProtocolExtensionContainer OPTIONAL,
	...
}

--TDD-DL-Code-LCR-InformationModifyItem-RL-ReconfReadyTDD-ExtIEs RNSAP-PROTOCOL-EXTENSION ::= {
--	...
--}

--DL-TimeslotLCR-InformationModifyItem-RL-ReconfReadyTDD-ExtIEs RNSAP-PROTOCOL-EXTENSION ::= {
--	{ ID id-Maximum-DL-Power-TimeslotLCR-InformationModifyItem-RL-ReconfReadyTDD   CRITICALITY ignore	EXTENSION   DL-Power		PRESENCE optional }|
--	{ ID id-Minimum-DL-Power-TimeslotLCR-InformationModifyItem-RL-ReconfReadyTDD   CRITICALITY ignore	EXTENSION   DL-Power		PRESENCE optional },
--	...
--}

--DL-Timeslot-InformationModifyList-RL-ReconfReadyTDD::= SEQUENCE ( SIZE (1..maxNrOfTS)) OF DL-Timeslot-InformationModifyItem-RL-ReconfReadyTDD
DL-Timeslot-InformationModifyList-RL-ReconfReadyTDD::= SEQUENCE ( SIZE (1..15)) OF DL-Timeslot-InformationModifyItem-RL-ReconfReadyTDD

DL-Timeslot-InformationModifyItem-RL-ReconfReadyTDD ::= SEQUENCE {
	timeSlot						TimeSlot,
	midambleShiftAndBurstType		MidambleShiftAndBurstType			OPTIONAL,
	tFCI-Presence					TFCI-Presence			OPTIONAL,
	dL-Code-Information				TDD-DL-Code-InformationModifyList-RL-ReconfReadyTDD			OPTIONAL,
--	iE-Extensions					ProtocolExtensionContainer { {DL-Timeslot-InformationModifyItem-RL-ReconfReadyTDD-ExtIEs} } OPTIONAL,
	iE-Extensions					ProtocolExtensionContainer OPTIONAL,
	...
}

--DL-Timeslot-InformationModifyItem-RL-ReconfReadyTDD-ExtIEs RNSAP-PROTOCOL-EXTENSION ::= {
--	...
--}

--TDD-DL-Code-InformationModifyList-RL-ReconfReadyTDD::= SEQUENCE ( SIZE (1..maxNrOfDPCHs)) OF TDD-DL-Code-InformationModifyItem-RL-ReconfReadyTDD
TDD-DL-Code-InformationModifyList-RL-ReconfReadyTDD::= SEQUENCE ( SIZE (1..240)) OF TDD-DL-Code-InformationModifyItem-RL-ReconfReadyTDD

TDD-DL-Code-InformationModifyItem-RL-ReconfReadyTDD ::= SEQUENCE {
	dPCH-ID							DPCH-ID,
	tDD-ChannelisationCode			TDD-ChannelisationCode		OPTIONAL,
--	iE-Extensions					ProtocolExtensionContainer { {TDD-DL-Code-InformationModifyItem-RL-ReconfReadyTDD-ExtIEs} } OPTIONAL,
	iE-Extensions					ProtocolExtensionContainer OPTIONAL,
	...
}

--TDD-DL-Code-InformationModifyItem-RL-ReconfReadyTDD-ExtIEs RNSAP-PROTOCOL-EXTENSION ::= {
--{ ID id-TDD-DL-DPCH-TimeSlotFormatModifyItem-LCR-RL-ReconfReadyTDD	 CRITICALITY	reject	 EXTENSION TDD-DL-DPCH-TimeSlotFormat-LCR   PRESENCE  optional},
--	...
--}

--DL-DPCH-InformationDeleteList-RL-ReconfReadyTDD ::= ProtocolIE-Single-Container {{DL-DPCH-InformationDeleteListIEs-RL-ReconfReadyTDD}}
DL-DPCH-InformationDeleteList-RL-ReconfReadyTDD ::= ProtocolIE-Single-Container

--DL-DPCH-InformationDeleteListIEs-RL-ReconfReadyTDD RNSAP-PROTOCOL-IES ::= {
--	{ ID id-DL-DPCH-InformationDeleteListIE-RL-ReconfReadyTDD   CRITICALITY ignore	TYPE DL-DPCH-InformationDeleteListIE-RL-ReconfReadyTDD		PRESENCE mandatory }
--}

--DL-DPCH-InformationDeleteListIE-RL-ReconfReadyTDD ::= SEQUENCE (SIZE (0..maxNrOfDPCHs)) OF DL-DPCH-InformationDeleteItem-RL-ReconfReadyTDD
DL-DPCH-InformationDeleteListIE-RL-ReconfReadyTDD ::= SEQUENCE (SIZE (0..240)) OF DL-DPCH-InformationDeleteItem-RL-ReconfReadyTDD

DL-DPCH-InformationDeleteItem-RL-ReconfReadyTDD ::= SEQUENCE {
	dPCH-ID						DPCH-ID,
--	iE-Extensions					ProtocolExtensionContainer { {DL-DPCH-InformationDeleteList-RL-ReconfReadyTDD-ExtIEs} } OPTIONAL,
	iE-Extensions					ProtocolExtensionContainer OPTIONAL,
	...
}

--DL-DPCH-InformationDeleteList-RL-ReconfReadyTDD-ExtIEs RNSAP-PROTOCOL-EXTENSION ::= {
--	...
--}

--DCH-InformationResponseList-RL-ReconfReadyTDD				::= ProtocolIE-Single-Container { {DCH-InformationResponseListIEs-RL-ReconfReadyTDD} }
DCH-InformationResponseList-RL-ReconfReadyTDD				::= ProtocolIE-Single-Container

--DCH-InformationResponseListIEs-RL-ReconfReadyTDD RNSAP-PROTOCOL-IES ::= {
--	{ ID id-DCH-InformationResponse		CRITICALITY ignore	TYPE DCH-InformationResponse		PRESENCE mandatory	}
--}

--DSCHToBeAddedOrModified-RL-ReconfReadyTDD			::= ProtocolIE-Single-Container { {DSCHToBeAddedOrModifiedIEs-RL-ReconfReadyTDD} }
DSCHToBeAddedOrModified-RL-ReconfReadyTDD			::= ProtocolIE-Single-Container

--DSCHToBeAddedOrModifiedIEs-RL-ReconfReadyTDD RNSAP-PROTOCOL-IES ::= {
--	{ ID id-DSCHToBeAddedOrModifiedList-RL-ReconfReadyTDD	CRITICALITY ignore	TYPE DSCHToBeAddedOrModifiedList-RL-ReconfReadyTDD		PRESENCE mandatory	}
--}

--DSCHToBeAddedOrModifiedList-RL-ReconfReadyTDD ::= SEQUENCE (SIZE (0..maxNoOfDSCHs)) OF DSCHToBeAddedOrModifiedItem-RL-ReconfReadyTDD
DSCHToBeAddedOrModifiedList-RL-ReconfReadyTDD ::= SEQUENCE (SIZE (0..10)) OF DSCHToBeAddedOrModifiedItem-RL-ReconfReadyTDD

DSCHToBeAddedOrModifiedItem-RL-ReconfReadyTDD ::= SEQUENCE {
	dsch-ID					DSCH-ID,
	transportFormatManagement	TransportFormatManagement,
	dSCH-FlowControlInformation	DSCH-FlowControlInformation,
	bindingID				BindingID	OPTIONAL,
	transportLayerAddress	TransportLayerAddress	OPTIONAL,
--	iE-Extensions			ProtocolExtensionContainer { {DSCHToBeAddedOrModifiedItem-RL-ReconfReadyTDD-ExtIEs} } OPTIONAL,
	iE-Extensions			ProtocolExtensionContainer OPTIONAL,
	...
}

--DSCHToBeAddedOrModifiedItem-RL-ReconfReadyTDD-ExtIEs RNSAP-PROTOCOL-EXTENSION ::= {
--	...
--}

--USCHToBeAddedOrModified-RL-ReconfReadyTDD			::= ProtocolIE-Single-Container { {USCHToBeAddedOrModifiedIEs-RL-ReconfReadyTDD} }USCHToBeAddedOrModifiedIEs-RL-ReconfReadyTDD RNSAP-PROTOCOL-IES ::= {
USCHToBeAddedOrModified-RL-ReconfReadyTDD			::= ProtocolIE-Single-Container

--	{ ID id-USCHToBeAddedOrModifiedList-RL-ReconfReadyTDD	CRITICALITY ignore	TYPE USCHToBeAddedOrModifiedList-RL-ReconfReadyTDD		PRESENCE mandatory	}
--}

--USCHToBeAddedOrModifiedList-RL-ReconfReadyTDD ::= SEQUENCE (SIZE (0..maxNoOfUSCHs)) OF USCHToBeAddedOrModifiedItem-RL-ReconfReadyTDD
USCHToBeAddedOrModifiedList-RL-ReconfReadyTDD ::= SEQUENCE (SIZE (0..10)) OF USCHToBeAddedOrModifiedItem-RL-ReconfReadyTDD

USCHToBeAddedOrModifiedItem-RL-ReconfReadyTDD ::= SEQUENCE {
	uSCH-ID					USCH-ID,
	transportFormatManagement	TransportFormatManagement,
	bindingID				BindingID	OPTIONAL,
	transportLayerAddress	TransportLayerAddress	OPTIONAL,
--	iE-Extensions			ProtocolExtensionContainer { {USCHToBeAddedOrModifiedItem-RL-ReconfReadyTDD-ExtIEs} } OPTIONAL,
	iE-Extensions			ProtocolExtensionContainer OPTIONAL,
	...
}

--USCHToBeAddedOrModifiedItem-RL-ReconfReadyTDD-ExtIEs RNSAP-PROTOCOL-EXTENSION ::= {
--	...
--}

--RadioLinkReconfigurationReadyTDD-Extensions RNSAP-PROTOCOL-EXTENSION ::= {
--	{ ID id-HSDSCH-RNTI							CRITICALITY ignore		EXTENSION HSDSCH-RNTI									PRESENCE optional }|
--	{ ID id-DSCH-RNTI							CRITICALITY ignore		EXTENSION DSCH-RNTI										PRESENCE optional }|
--	{ ID id-HSDSCH-TDD-Information-Response		CRITICALITY ignore		EXTENSION HSDSCH-TDD-Information-Response		PRESENCE optional }|
--	{ ID id-MAChs-ResetIndicator				CRITICALITY ignore		EXTENSION MAChs-ResetIndicator						PRESENCE optional }|
--	{ ID id-Multiple-RL-InformationResponse-RL-ReconfReadyTDD	CRITICALITY	ignore		EXTENSION 	Multiple-RL-InformationResponse-RL-ReconfReadyTDD		PRESENCE 	optional},
-- This is for RL repetitions 2 and on in RL list.
--	...
--}

--Multiple-RL-InformationResponse-RL-ReconfReadyTDD ::= SEQUENCE (SIZE (1..maxNrOfRLs-1)) OF RL-InformationResponse-RL-ReconfReadyTDD
Multiple-RL-InformationResponse-RL-ReconfReadyTDD ::= SEQUENCE (SIZE (1..15)) OF RL-InformationResponse-RL-ReconfReadyTDD


-- **************************************************************
--
-- RADIO LINK RECONFIGURATION COMMIT
--
-- **************************************************************
--RadioLinkReconfigurationCommit ::= SEQUENCE {
--	protocolIEs                     ProtocolIE-Container       {{RadioLinkReconfigurationCommit-IEs}},
--	protocolExtensions              ProtocolExtensionContainer {{RadioLinkReconfigurationCommit-Extensions}}                   OPTIONAL,
--	...
--}
RadioLinkReconfigurationCommit ::= SEQUENCE {
	protocolIEs                     ProtocolIE-Container,
	protocolExtensions              ProtocolExtensionContainer OPTIONAL,
	...
}
--RadioLinkReconfigurationCommit-IEs RNSAP-PROTOCOL-IES ::= {
--	{ ID id-CFN					CRITICALITY ignore	TYPE CFN					PRESENCE mandatory	}|
--	{ ID id-Active-Pattern-Sequence-Information		CRITICALITY ignore	TYPE Active-Pattern-Sequence-Information		 PRESENCE optional  },
	--FDD only
--	...
--}

--RadioLinkReconfigurationCommit-Extensions RNSAP-PROTOCOL-EXTENSION ::= {
--	...
--}

-- **************************************************************
--
-- RADIO LINK RECONFIGURATION FAILURE
--
-- **************************************************************

--RadioLinkReconfigurationFailure ::= SEQUENCE {
--	protocolIEs                     ProtocolIE-Container       {{RadioLinkReconfigurationFailure-IEs}},
--	protocolExtensions              ProtocolExtensionContainer {{RadioLinkReconfigurationFailure-Extensions}}                   OPTIONAL,
--	...
--}
RadioLinkReconfigurationFailure ::= SEQUENCE {
	protocolIEs                     ProtocolIE-Container,
	protocolExtensions              ProtocolExtensionContainer OPTIONAL,
	...
}

--RadioLinkReconfigurationFailure-IEs RNSAP-PROTOCOL-IES ::= {
--	{ ID id-CauseLevel-RL-ReconfFailure		CRITICALITY ignore	TYPE CauseLevel-RL-ReconfFailure	PRESENCE mandatory	} |
--	{ ID id-CriticalityDiagnostics			CRITICALITY ignore	TYPE CriticalityDiagnostics			PRESENCE optional	},
--	...
--}

CauseLevel-RL-ReconfFailure ::= CHOICE {
	generalCause		GeneralCauseList-RL-ReconfFailure,
	rLSpecificCause		RLSpecificCauseList-RL-ReconfFailure,
	...
}

GeneralCauseList-RL-ReconfFailure ::= SEQUENCE {
	cause										Cause,
--	iE-Extensions								ProtocolExtensionContainer { { GeneralCauseItem-RL-ReconfFailure-ExtIEs} }			OPTIONAL,
	iE-Extensions								ProtocolExtensionContainer OPTIONAL,
	...
 }

--GeneralCauseItem-RL-ReconfFailure-ExtIEs  RNSAP-PROTOCOL-EXTENSION ::= {
--	...
--}

RLSpecificCauseList-RL-ReconfFailure ::= SEQUENCE {
	rL-ReconfigurationFailureList-RL-ReconfFailure		RL-ReconfigurationFailureList-RL-ReconfFailure		OPTIONAL,
--	iE-Extensions										ProtocolExtensionContainer { { RLSpecificCauseItem-RL-ReconfFailure-ExtIEs} }			OPTIONAL,
	iE-Extensions										ProtocolExtensionContainer OPTIONAL,
	...
 }

--RLSpecificCauseItem-RL-ReconfFailure-ExtIEs  RNSAP-PROTOCOL-EXTENSION ::= {
--	...
--}

--RL-ReconfigurationFailureList-RL-ReconfFailure ::= SEQUENCE (SIZE (0..maxNrOfRLs)) OF ProtocolIE-Single-Container { {RL-ReconfigurationFailure-RL-ReconfFailure-IEs} }
RL-ReconfigurationFailureList-RL-ReconfFailure ::= SEQUENCE (SIZE (0..16)) OF ProtocolIE-Single-Container 

--RL-ReconfigurationFailure-RL-ReconfFailure-IEs RNSAP-PROTOCOL-IES ::= {
--	{ ID id-RL-ReconfigurationFailure-RL-ReconfFail	CRITICALITY ignore	TYPE RL-ReconfigurationFailure-RL-ReconfFail	PRESENCE mandatory	}
--}

RL-ReconfigurationFailure-RL-ReconfFail ::= SEQUENCE {
	rL-ID						RL-ID,
	cause						Cause,
--	iE-Extensions					ProtocolExtensionContainer { {RL-ReconfigurationFailure-RL-ReconfFailure-ExtIEs} } OPTIONAL,
	iE-Extensions					ProtocolExtensionContainer OPTIONAL,
	...
}

--RL-ReconfigurationFailure-RL-ReconfFailure-ExtIEs RNSAP-PROTOCOL-EXTENSION ::= {
--	...
--}

--RadioLinkReconfigurationFailure-Extensions RNSAP-PROTOCOL-EXTENSION ::= {
--	...
--}

-- **************************************************************
--
-- RADIO LINK RECONFIGURATION CANCEL
--
-- **************************************************************

--RadioLinkReconfigurationCancel ::= SEQUENCE {
--	protocolIEs                     ProtocolIE-Container       {{RadioLinkReconfigurationCancel-IEs}},
--	protocolExtensions              ProtocolExtensionContainer {{RadioLinkReconfigurationCancel-Extensions}}                   OPTIONAL,
--	...
--}

RadioLinkReconfigurationCancel ::= SEQUENCE {
	protocolIEs                     ProtocolIE-Container,
	protocolExtensions              ProtocolExtensionContainer OPTIONAL,
	...
}
--RadioLinkReconfigurationCancel-IEs RNSAP-PROTOCOL-IES ::= {
--	...
--}

--RadioLinkReconfigurationCancel-Extensions RNSAP-PROTOCOL-EXTENSION ::= {
--	...
--}

-- **************************************************************
--
-- RADIO LINK RECONFIGURATION REQUEST FDD
--
-- **************************************************************
--RadioLinkReconfigurationRequestFDD ::= SEQUENCE {
--	protocolIEs                     ProtocolIE-Container       {{RadioLinkReconfigurationRequestFDD-IEs}},
--	protocolExtensions              ProtocolExtensionContainer {{RadioLinkReconfigurationRequestFDD-Extensions}}                   OPTIONAL,
--	...
--}
RadioLinkReconfigurationRequestFDD ::= SEQUENCE {
	protocolIEs                     ProtocolIE-Container,
	protocolExtensions              ProtocolExtensionContainer OPTIONAL,
	...
}

--RadioLinkReconfigurationRequestFDD-IEs RNSAP-PROTOCOL-IES ::= {
--	{ ID id-AllowedQueuingTime			CRITICALITY reject	TYPE AllowedQueuingTime				PRESENCE optional	} |
--	{ ID id-UL-DPCH-Information-RL-ReconfRqstFDD			CRITICALITY reject	TYPE UL-DPCH-Information-RL-ReconfRqstFDD	PRESENCE optional	} |
--	{ ID id-DL-DPCH-Information-RL-ReconfRqstFDD			CRITICALITY reject	TYPE DL-DPCH-Information-RL-ReconfRqstFDD	PRESENCE optional	} |
--	{ ID id-FDD-DCHs-to-Modify		CRITICALITY reject	TYPE FDD-DCHs-to-Modify		PRESENCE optional	} |
--	{ ID id-DCHs-to-Add-FDD		CRITICALITY reject	TYPE DCH-FDD-Information		PRESENCE optional	} |
--	{ ID id-DCH-DeleteList-RL-ReconfRqstFDD		CRITICALITY reject	TYPE DCH-DeleteList-RL-ReconfRqstFDD		PRESENCE optional	}|
--	{ ID id-Transmission-Gap-Pattern-Sequence-Information	CRITICALITY reject	TYPE Transmission-Gap-Pattern-Sequence-Information PRESENCE optional },
--	...
--}

UL-DPCH-Information-RL-ReconfRqstFDD ::= SEQUENCE {
	tFCS							TFCS	OPTIONAL,
--	iE-Extensions					ProtocolExtensionContainer { {UL-DPCH-Information-RL-ReconfRqstFDD-ExtIEs} } OPTIONAL,
	iE-Extensions					ProtocolExtensionContainer OPTIONAL,
	...
}

--UL-DPCH-Information-RL-ReconfRqstFDD-ExtIEs RNSAP-PROTOCOL-EXTENSION ::= {
--	{ ID id-UL-DPDCHIndicatorEDCH	CRITICALITY reject		EXTENSION UL-DPDCHIndicatorEDCH	PRESENCE conditional	},
	-- This IE shall be present if E-DPCH Information IE is present.
--...
--}

DL-DPCH-Information-RL-ReconfRqstFDD ::= SEQUENCE {
	tFCS							TFCS	OPTIONAL,
	tFCI-SignallingMode				TFCI-SignallingMode	OPTIONAL,
	limitedPowerIncrease			LimitedPowerIncrease	OPTIONAL,
--	iE-Extensions					ProtocolExtensionContainer { {DL-DPCH-Information-RL-ReconfRqstFDD-ExtIEs} } OPTIONAL,
	iE-Extensions					ProtocolExtensionContainer OPTIONAL,
	...
}

--DL-DPCH-Information-RL-ReconfRqstFDD-ExtIEs RNSAP-PROTOCOL-EXTENSION ::= {
--	...
--}

--DCH-DeleteList-RL-ReconfRqstFDD				::= SEQUENCE (SIZE (0..maxNrOfDCHs)) OF DCH-DeleteItem-RL-ReconfRqstFDD
DCH-DeleteList-RL-ReconfRqstFDD				::= SEQUENCE (SIZE (0..128)) OF DCH-DeleteItem-RL-ReconfRqstFDD

DCH-DeleteItem-RL-ReconfRqstFDD ::= SEQUENCE {
	dCH-ID							DCH-ID,
--	iE-Extensions					ProtocolExtensionContainer { {DCH-DeleteItem-RL-ReconfRqstFDD-ExtIEs} } OPTIONAL,
	iE-Extensions					ProtocolExtensionContainer OPTIONAL,
	...
}

--DCH-DeleteItem-RL-ReconfRqstFDD-ExtIEs RNSAP-PROTOCOL-EXTENSION ::= {
--	...
--}

--RadioLinkReconfigurationRequestFDD-Extensions RNSAP-PROTOCOL-EXTENSION ::= {
--	{ ID id-RL-ReconfigurationRequestFDD-RL-InformationList	CRITICALITY	ignore	EXTENSION RL-ReconfigurationRequestFDD-RL-InformationList		PRESENCE 	optional}|
--	{ ID id-DL-ReferencePowerInformation					CRITICALITY ignore	EXTENSION DL-ReferencePowerInformation				PRESENCE optional	}|
--	{ ID id-HSDSCH-FDD-Information					CRITICALITY reject	EXTENSION HSDSCH-FDD-Information			PRESENCE optional}|
--	{ ID id-HSDSCH-Information-to-Modify-Unsynchronised	CRITICALITY reject		EXTENSION HSDSCH-Information-to-Modify-Unsynchronised	PRESENCE optional}|
--	{ ID id-HSDSCH-MACdFlows-to-Add					CRITICALITY reject		EXTENSION HSDSCH-MACdFlows-Information			PRESENCE optional}|
--	{ ID id-HSDSCH-MACdFlows-to-Delete				CRITICALITY reject		EXTENSION HSDSCH-MACdFlows-to-Delete			PRESENCE optional}|
--	{ ID id-HSPDSCH-RL-ID							CRITICALITY reject		EXTENSION RL-ID											PRESENCE optional}|
--	{ ID id-EDPCH-Information-RLReconfRequest-FDD	CRITICALITY	reject		EXTENSION EDPCH-Information-RLReconfRequest-FDD		PRESENCE optional}|
--	{ ID id-EDCH-FDD-Information					CRITICALITY	reject		EXTENSION EDCH-FDD-Information						PRESENCE optional}|
--	{ ID id-EDCH-FDD-Information-To-Modify			CRITICALITY	reject		EXTENSION EDCH-FDD-Information-To-Modify		PRESENCE optional}|
--	{ ID id-EDCH-MACdFlows-To-Delete				CRITICALITY	reject		EXTENSION EDCH-MACdFlows-To-Delete				PRESENCE optional}|
--	{ ID id-Serving-EDCHRL-Id						CRITICALITY	reject		EXTENSION EDCH-Serving-RL							PRESENCE optional},
--	...
--}

--RL-ReconfigurationRequestFDD-RL-InformationList ::= SEQUENCE (SIZE (0..maxNrOfRLs)) OF ProtocolIE-Single-Container { 
--	{RL-ReconfigurationRequestFDD-RL-Information-ListItem} }

RL-ReconfigurationRequestFDD-RL-InformationList ::= SEQUENCE (SIZE (0..16)) OF ProtocolIE-Single-Container

--RL-ReconfigurationRequestFDD-RL-Information-ListItem RNSAP-PROTOCOL-IES ::= {
--	{ ID id-RL-ReconfigurationRequestFDD-RL-Information-IEs	CRITICALITY ignore	TYPE RL-ReconfigurationRequestFDD-RL-Information-IEs	PRESENCE optional	}
--}

RL-ReconfigurationRequestFDD-RL-Information-IEs ::= SEQUENCE {
	rL-ID					RL-ID,
	rL-Specific-DCH-Info	RL-Specific-DCH-Info OPTIONAL,
--	iE-Extensions			ProtocolExtensionContainer { { RL-ReconfigurationRequestFDD-RL-Information-ExtIEs} } OPTIONAL,
	iE-Extensions			ProtocolExtensionContainer OPTIONAL,
	...
}

--RL-ReconfigurationRequestFDD-RL-Information-ExtIEs RNSAP-PROTOCOL-EXTENSION ::= {
--	{ ID id-RL-Specific-EDCH-Information		CRITICALITY reject		EXTENSION RL-Specific-EDCH-Information 		PRESENCE optional }|
--	{ ID id-EDCH-RL-Indication					CRITICALITY reject		EXTENSION EDCH-RL-Indication						PRESENCE optional }|
--	{ ID id-EDCH-MACdFlows-To-Add				CRITICALITY reject		EXTENSION RL-Specific-EDCH-Information 		PRESENCE optional },
--	...
--}

-- **************************************************************
--
-- RADIO LINK RECONFIGURATION REQUEST TDD
--
-- **************************************************************

--RadioLinkReconfigurationRequestTDD ::= SEQUENCE {
--	protocolIEs                     ProtocolIE-Container       {{RadioLinkReconfigurationRequestTDD-IEs}},
--	protocolExtensions              ProtocolExtensionContainer {{RadioLinkReconfigurationRequestTDD-Extensions}}                   OPTIONAL,
--	...
--}
RadioLinkReconfigurationRequestTDD ::= SEQUENCE {
	protocolIEs                     ProtocolIE-Container,
	protocolExtensions              ProtocolExtensionContainer OPTIONAL,
	...
}

--RadioLinkReconfigurationRequestTDD-IEs RNSAP-PROTOCOL-IES ::= {
--	{ ID id-AllowedQueuingTime			CRITICALITY reject	TYPE AllowedQueuingTime				PRESENCE optional	} |
--	{ ID id-UL-CCTrCH-InformationModifyList-RL-ReconfRqstTDD	CRITICALITY notify	TYPE UL-CCTrCH-InformationModifyList-RL-ReconfRqstTDD	PRESENCE optional	} |
--	{ ID id-UL-CCTrCH-InformationDeleteList-RL-ReconfRqstTDD	CRITICALITY notify	TYPE UL-CCTrCH-InformationDeleteList-RL-ReconfRqstTDD	PRESENCE optional	} |
--	{ ID id-DL-CCTrCH-InformationModifyList-RL-ReconfRqstTDD	CRITICALITY notify	TYPE DL-CCTrCH-InformationModifyList-RL-ReconfRqstTDD	PRESENCE optional	} |
--	{ ID id-DL-CCTrCH-InformationDeleteList-RL-ReconfRqstTDD	CRITICALITY notify	TYPE DL-CCTrCH-InformationDeleteList-RL-ReconfRqstTDD	PRESENCE optional	} |
--	{ ID id-TDD-DCHs-to-Modify		CRITICALITY reject	TYPE TDD-DCHs-to-Modify		PRESENCE optional	} |
--	{ ID id-DCHs-to-Add-TDD		CRITICALITY reject	TYPE DCH-TDD-Information		PRESENCE optional	} |
--	{ ID id-DCH-DeleteList-RL-ReconfRqstTDD		CRITICALITY reject	TYPE DCH-DeleteList-RL-ReconfRqstTDD		PRESENCE optional	},
--	...
--}

--UL-CCTrCH-InformationModifyList-RL-ReconfRqstTDD		::= SEQUENCE (SIZE (0..maxNrOfCCTrCHs)) OF ProtocolIE-Single-Container { {UL-CCTrCH-InformationModifyList-RL-ReconfRqstTDD-IEs} }
UL-CCTrCH-InformationModifyList-RL-ReconfRqstTDD		::= SEQUENCE (SIZE (0..16)) OF ProtocolIE-Single-Container

--UL-CCTrCH-InformationModifyList-RL-ReconfRqstTDD-IEs RNSAP-PROTOCOL-IES ::= {
--	{ ID id-UL-CCTrCH-InformationModifyItem-RL-ReconfRqstTDD	CRITICALITY notify	TYPE UL-CCTrCH-InformationModifyItem-RL-ReconfRqstTDD	PRESENCE mandatory	}
--}

UL-CCTrCH-InformationModifyItem-RL-ReconfRqstTDD ::= SEQUENCE {
	cCTrCH-ID					CCTrCH-ID,
	tFCS						TFCS		OPTIONAL,
--	iE-Extensions					ProtocolExtensionContainer { {UL-CCTrCH-InformationModifyItem-RL-ReconfRqstTDD-ExtIEs} } OPTIONAL,
	iE-Extensions					ProtocolExtensionContainer OPTIONAL,
	...
}

--UL-CCTrCH-InformationModifyItem-RL-ReconfRqstTDD-ExtIEs RNSAP-PROTOCOL-EXTENSION ::= {
--{ ID id-UL-SIRTarget      CRITICALITY reject      EXTENSION       UL-SIR      PRESENCE	optional   },
    -- Applicable to 1.28Mcps TDD only
--	...
--}

--UL-CCTrCH-InformationDeleteList-RL-ReconfRqstTDD		::= SEQUENCE (SIZE (0..maxNrOfCCTrCHs)) OF ProtocolIE-Single-Container { {UL-CCTrCH-InformationDeleteList-RL-ReconfRqstTDD-IEs} }
UL-CCTrCH-InformationDeleteList-RL-ReconfRqstTDD		::= SEQUENCE (SIZE (0..16)) OF ProtocolIE-Single-Container

--UL-CCTrCH-InformationDeleteList-RL-ReconfRqstTDD-IEs RNSAP-PROTOCOL-IES ::= {
--	{ ID id-UL-CCTrCH-InformationDeleteItem-RL-ReconfRqstTDD	CRITICALITY notify	TYPE UL-CCTrCH-InformationDeleteItem-RL-ReconfRqstTDD	PRESENCE mandatory	}
--}

UL-CCTrCH-InformationDeleteItem-RL-ReconfRqstTDD ::= SEQUENCE {
	cCTrCH-ID					CCTrCH-ID,
--	iE-Extensions					ProtocolExtensionContainer { {UL-CCTrCH-InformationDeleteItem-RL-ReconfRqstTDD-ExtIEs} } OPTIONAL,
	iE-Extensions					ProtocolExtensionContainer OPTIONAL,
	...
}

--UL-CCTrCH-InformationDeleteItem-RL-ReconfRqstTDD-ExtIEs RNSAP-PROTOCOL-EXTENSION ::= {
--	...
--}

--DL-CCTrCH-InformationModifyList-RL-ReconfRqstTDD		::= SEQUENCE (SIZE (0..maxNrOfCCTrCHs)) OF ProtocolIE-Single-Container { {DL-CCTrCH-InformationModifyList-RL-ReconfRqstTDD-IEs} }
DL-CCTrCH-InformationModifyList-RL-ReconfRqstTDD		::= SEQUENCE (SIZE (0..16)) OF ProtocolIE-Single-Container

--DL-CCTrCH-InformationModifyList-RL-ReconfRqstTDD-IEs RNSAP-PROTOCOL-IES ::= {
--	{ ID id-DL-CCTrCH-InformationModifyItem-RL-ReconfRqstTDD	CRITICALITY notify	TYPE DL-CCTrCH-InformationModifyItem-RL-ReconfRqstTDD	PRESENCE mandatory	}
--}

DL-CCTrCH-InformationModifyItem-RL-ReconfRqstTDD ::= SEQUENCE {
	cCTrCH-ID					CCTrCH-ID,
	tFCS						TFCS		OPTIONAL,
--	iE-Extensions					ProtocolExtensionContainer { {DL-CCTrCH-InformationModifyItem-RL-ReconfRqstTDD-ExtIEs} } OPTIONAL,
	iE-Extensions					ProtocolExtensionContainer OPTIONAL,
	...
}

--DL-CCTrCH-InformationModifyItem-RL-ReconfRqstTDD-ExtIEs RNSAP-PROTOCOL-EXTENSION ::= {
--	...
--}

--DL-CCTrCH-InformationDeleteList-RL-ReconfRqstTDD		::= SEQUENCE (SIZE (0..maxNrOfCCTrCHs)) OF ProtocolIE-Single-Container { {DL-CCTrCH-InformationDeleteList-RL-ReconfRqstTDD-IEs} }
DL-CCTrCH-InformationDeleteList-RL-ReconfRqstTDD		::= SEQUENCE (SIZE (0..16)) OF ProtocolIE-Single-Container

--DL-CCTrCH-InformationDeleteList-RL-ReconfRqstTDD-IEs RNSAP-PROTOCOL-IES ::= {
--	{ ID id-DL-CCTrCH-InformationDeleteItem-RL-ReconfRqstTDD	CRITICALITY notify	TYPE DL-CCTrCH-InformationDeleteItem-RL-ReconfRqstTDD	PRESENCE mandatory	}
--}

DL-CCTrCH-InformationDeleteItem-RL-ReconfRqstTDD ::= SEQUENCE {
	cCTrCH-ID					CCTrCH-ID,
--	iE-Extensions					ProtocolExtensionContainer { {DL-CCTrCH-InformationDeleteItem-RL-ReconfRqstTDD-ExtIEs} } OPTIONAL,
	iE-Extensions					ProtocolExtensionContainer OPTIONAL,
	...
}

--DL-CCTrCH-InformationDeleteItem-RL-ReconfRqstTDD-ExtIEs RNSAP-PROTOCOL-EXTENSION ::= {
--	...
--}

--DCH-DeleteList-RL-ReconfRqstTDD				::= SEQUENCE (SIZE(0..maxNrOfDCHs)) OF DCH-DeleteItem-RL-ReconfRqstTDD
DCH-DeleteList-RL-ReconfRqstTDD				::= SEQUENCE (SIZE(0..128)) OF DCH-DeleteItem-RL-ReconfRqstTDD

DCH-DeleteItem-RL-ReconfRqstTDD ::= SEQUENCE {
	dCH-ID						DCH-ID,
--	iE-Extensions					ProtocolExtensionContainer { {DCH-DeleteItem-RL-ReconfRqstTDD-ExtIEs} } OPTIONAL,
	iE-Extensions					ProtocolExtensionContainer OPTIONAL,
	...
}

--DCH-DeleteItem-RL-ReconfRqstTDD-ExtIEs RNSAP-PROTOCOL-EXTENSION ::= {
--	...
--}

--RadioLinkReconfigurationRequestTDD-Extensions RNSAP-PROTOCOL-EXTENSION ::= {
--  { ID id-RL-ReconfigurationRequestTDD-RL-Information	CRITICALITY	ignore		EXTENSION 	Multiple-RL-ReconfigurationRequestTDD-RL-Information		PRESENCE 	optional}|
--	{ ID id-HSDSCH-TDD-Information				CRITICALITY reject		EXTENSION HSDSCH-TDD-Information		PRESENCE optional}|
--	{ ID id-HSDSCH-Information-to-Modify-Unsynchronised	CRITICALITY reject		EXTENSION HSDSCH-Information-to-Modify-Unsynchronised	PRESENCE optional}|
--	{ ID id-HSDSCH-MACdFlows-to-Add				CRITICALITY reject		EXTENSION HSDSCH-MACdFlows-Information			PRESENCE optional}|
--	{ ID id-HSDSCH-MACdFlows-to-Delete			CRITICALITY reject		EXTENSION HSDSCH-MACdFlows-to-Delete		PRESENCE optional}|
--	{ ID id-HSPDSCH-RL-ID						CRITICALITY reject		EXTENSION RL-ID											PRESENCE optional},
--	...
--}

--Multiple-RL-ReconfigurationRequestTDD-RL-Information ::= SEQUENCE (SIZE (1..maxNrOfRLs)) OF RL-ReconfigurationRequestTDD-RL-Information
Multiple-RL-ReconfigurationRequestTDD-RL-Information ::= SEQUENCE (SIZE (1..16)) OF RL-ReconfigurationRequestTDD-RL-Information

RL-ReconfigurationRequestTDD-RL-Information ::= SEQUENCE {
	rL-ID					RL-ID,
	rL-Specific-DCH-Info	RL-Specific-DCH-Info OPTIONAL,
--	iE-Extensions			ProtocolExtensionContainer { { RL-ReconfigurationRequestTDD-RL-Information-ExtIEs} } OPTIONAL,
	iE-Extensions			ProtocolExtensionContainer OPTIONAL,
	...
}

--RL-ReconfigurationRequestTDD-RL-Information-ExtIEs RNSAP-PROTOCOL-EXTENSION ::= {
--	{ ID	id-UL-Synchronisation-Parameters-LCR			CRITICALITY	ignore		EXTENSION 	UL-Synchronisation-Parameters-LCR		PRESENCE 	optional	},
	-- Mandatory for 1.28Mcps TDD, Not Applicable to 3.84Mcps TDD
--	...
--}

-- **************************************************************
--
-- RADIO LINK RECONFIGURATION RESPONSE FDD
--
-- **************************************************************

--RadioLinkReconfigurationResponseFDD ::= SEQUENCE {
--	protocolIEs                     ProtocolIE-Container       {{RadioLinkReconfigurationResponseFDD-IEs}},
--	protocolExtensions              ProtocolExtensionContainer {{RadioLinkReconfigurationResponseFDD-Extensions}}                   OPTIONAL,
--	...
--}
RadioLinkReconfigurationResponseFDD ::= SEQUENCE {
	protocolIEs                     ProtocolIE-Container,
	protocolExtensions              ProtocolExtensionContainer OPTIONAL,
	...
}
--RadioLinkReconfigurationResponseFDD-IEs RNSAP-PROTOCOL-IES ::= {
--	{ ID id-RL-InformationResponseList-RL-ReconfRspFDD		CRITICALITY ignore	TYPE RL-InformationResponseList-RL-ReconfRspFDD			PRESENCE optional	} |
--	{ ID id-CriticalityDiagnostics			CRITICALITY ignore	TYPE CriticalityDiagnostics			PRESENCE optional	},
--	...
--}

--RL-InformationResponseList-RL-ReconfRspFDD		::= SEQUENCE (SIZE (0..maxNrOfRLs)) OF ProtocolIE-Single-Container { {RL-InformationResponse-RL-ReconfRspFDD-IEs} }
RL-InformationResponseList-RL-ReconfRspFDD		::= SEQUENCE (SIZE (0..16)) OF ProtocolIE-Single-Container

--RL-InformationResponse-RL-ReconfRspFDD-IEs RNSAP-PROTOCOL-IES ::= {
--	{ ID id-RL-InformationResponseItem-RL-ReconfRspFDD		CRITICALITY ignore	TYPE RL-InformationResponseItem-RL-ReconfRspFDD		PRESENCE mandatory	}
--}

RL-InformationResponseItem-RL-ReconfRspFDD ::= SEQUENCE {
	rL-ID							RL-ID,
	max-UL-SIR						UL-SIR			OPTIONAL,
	min-UL-SIR						UL-SIR			OPTIONAL,
	maximumDLTxPower				DL-Power		OPTIONAL,
	minimumDLTxPower				DL-Power		OPTIONAL,
	not-Used-secondary-CCPCH-Info			NULL		OPTIONAL,
	dCHsInformationResponseList		DCH-InformationResponseList-RL-ReconfRspFDD	OPTIONAL,
	dL-CodeInformationList-RL-ReconfResp 	DL-CodeInformationList-RL-ReconfRspFDD	OPTIONAL,
--	iE-Extensions					ProtocolExtensionContainer { {RL-InformationResponseItem-RL-ReconfRspFDD-ExtIEs} } OPTIONAL,
	iE-Extensions					ProtocolExtensionContainer OPTIONAL,
	...
}

--RL-InformationResponseItem-RL-ReconfRspFDD-ExtIEs RNSAP-PROTOCOL-EXTENSION ::= {
--	{ ID id-DL-PowerBalancing-UpdatedIndicator	CRITICALITY ignore		EXTENSION		DL-PowerBalancing-UpdatedIndicator		PRESENCE optional}|
--	{ ID id-EDCH-FDD-InformationResponse			CRITICALITY ignore	EXTENSION EDCH-FDD-InformationResponse						PRESENCE optional }|
--	{ ID id-EDCH-RLSet-Id							CRITICALITY ignore	EXTENSION RL-Set-ID													PRESENCE optional }|
--	{ ID id-EDCH-FDD-DL-ControlChannelInformation	CRITICALITY ignore	EXTENSION EDCH-FDD-DL-ControlChannelInformation			PRESENCE optional },
--	...
--}

--DCH-InformationResponseList-RL-ReconfRspFDD				::= ProtocolIE-Single-Container { {DCH-InformationResponseListIEs-RL-ReconfRspFDD} }
DCH-InformationResponseList-RL-ReconfRspFDD				::= ProtocolIE-Single-Container

--DCH-InformationResponseListIEs-RL-ReconfRspFDD RNSAP-PROTOCOL-IES ::= {
--	{ ID id-DCH-InformationResponse		CRITICALITY ignore	TYPE DCH-InformationResponse		PRESENCE mandatory	}
--}

--DL-CodeInformationList-RL-ReconfRspFDD ::= ProtocolIE-Single-Container {{ DL-CodeInformationListIEs-RL-ReconfRspFDD }}
DL-CodeInformationList-RL-ReconfRspFDD ::= ProtocolIE-Single-Container

--DL-CodeInformationListIEs-RL-ReconfRspFDD RNSAP-PROTOCOL-IES ::= {
--	{ ID id-FDD-DL-CodeInformation   CRITICALITY ignore	TYPE FDD-DL-CodeInformation		PRESENCE optional }
--}

--RadioLinkReconfigurationResponseFDD-Extensions RNSAP-PROTOCOL-EXTENSION ::= {
--	{ ID id-HSDSCH-RNTI							CRITICALITY ignore		EXTENSION HSDSCH-RNTI									PRESENCE optional }|
--	{ ID id-HSDSCH-FDD-Information-Response		CRITICALITY ignore		EXTENSION HSDSCH-FDD-Information-Response		PRESENCE optional }|
--	{ ID id-MAChs-ResetIndicator				CRITICALITY ignore		EXTENSION MAChs-ResetIndicator						PRESENCE optional },
--	...
--}

-- **************************************************************
--
-- RADIO LINK RECONFIGURATION RESPONSE TDD
--
-- **************************************************************
--RadioLinkReconfigurationResponseTDD ::= SEQUENCE {
--	protocolIEs                     ProtocolIE-Container       {{RadioLinkReconfigurationResponseTDD-IEs}},
--	protocolExtensions              ProtocolExtensionContainer {{RadioLinkReconfigurationResponseTDD-Extensions}}                   OPTIONAL,
--	...
--}
RadioLinkReconfigurationResponseTDD ::= SEQUENCE {
	protocolIEs                     ProtocolIE-Container,
	protocolExtensions              ProtocolExtensionContainer OPTIONAL,
	...
}

--RadioLinkReconfigurationResponseTDD-IEs RNSAP-PROTOCOL-IES ::= {
--	{ ID id-RL-InformationResponse-RL-ReconfRspTDD		CRITICALITY ignore	TYPE RL-InformationResponse-RL-ReconfRspTDD			PRESENCE optional	} |
	--This RL-InformationResponse-RL-ReconfRspTDD is for the first RL repetition in the list.
	--Repetitions 2 and on are defined in Multiple-RL-InformationResponse-RL-ReconfRspTDD.
--	{ ID id-CriticalityDiagnostics			CRITICALITY ignore	TYPE CriticalityDiagnostics			PRESENCE optional	},
--	...
--}

RL-InformationResponse-RL-ReconfRspTDD ::= SEQUENCE {
	rL-ID							RL-ID,
	max-UL-SIR						UL-SIR			OPTIONAL,
	min-UL-SIR						UL-SIR			OPTIONAL,
	maximumDLTxPower				DL-Power		OPTIONAL,
	minimumDLTxPower				DL-Power		OPTIONAL,
	dCHsInformationResponseList		DCH-InformationResponseList-RL-ReconfRspTDD	OPTIONAL,
--	iE-Extensions					ProtocolExtensionContainer { {RL-InformationResponse-RL-ReconfRspTDD-ExtIEs} } OPTIONAL,
	iE-Extensions					ProtocolExtensionContainer OPTIONAL,
	...
}

--RL-InformationResponse-RL-ReconfRspTDD-ExtIEs RNSAP-PROTOCOL-EXTENSION ::= {
--	{ ID id-DL-CCTrCH-InformationList-RL-ReconfRspTDD	CRITICALITY ignore	EXTENSION DL-CCTrCH-InformationList-RL-ReconfRspTDD		PRESENCE optional }|
--	{ ID id-UL-TimingAdvanceCtrl-LCR					CRITICALITY ignore	EXTENSION UL-TimingAdvanceCtrl-LCR		PRESENCE optional },
	--For 1.28Mcps TDD only
--	...
--}

--DL-CCTrCH-InformationList-RL-ReconfRspTDD ::= SEQUENCE (SIZE (1..maxNrOfCCTrCHs)) OF DL-CCTrCH-InformationItem-RL-ReconfRspTDD
DL-CCTrCH-InformationList-RL-ReconfRspTDD ::= SEQUENCE (SIZE (1..16)) OF DL-CCTrCH-InformationItem-RL-ReconfRspTDD

DL-CCTrCH-InformationItem-RL-ReconfRspTDD ::= SEQUENCE {
	cCTrCH-ID									CCTrCH-ID,
	dl-DPCH-ModifyInformation-LCR				DL-DPCH-InformationModifyList-LCR-RL-ReconfRspTDD			OPTIONAL,
	--For 1.28Mcps TDD only
	cCTrCH-Maximum-DL-Power						DL-Power				OPTIONAL,
	--For 3.84Mcps TDD only, this is a DCH type CCTrCH power
	cCTrCH-Minimum-DL-Power						DL-Power				OPTIONAL,
	--For 3.84Mcps TDD only, this is a DCH type CCTrCH power
--	iE-Extensions								ProtocolExtensionContainer { { DL-CCTrCH-InformationItem-RL-ReconfRspTDD-ExtIEs} }		OPTIONAL,
	iE-Extensions								ProtocolExtensionContainer OPTIONAL,
	...
}

--DL-CCTrCH-InformationItem-RL-ReconfRspTDD-ExtIEs   RNSAP-PROTOCOL-EXTENSION ::= { 
--	...
--}

--DL-DPCH-InformationModifyList-LCR-RL-ReconfRspTDD  ::= ProtocolIE-Single-Container {{ DL-DPCH-InformationModifyListIEs-LCR-RL-ReconfRspTDD }}
DL-DPCH-InformationModifyList-LCR-RL-ReconfRspTDD  ::= ProtocolIE-Single-Container

--DL-DPCH-InformationModifyListIEs-LCR-RL-ReconfRspTDD RNSAP-PROTOCOL-IES ::= {
--	{ID id-DL-DPCH-InformationModifyItem-LCR-RL-ReconfRspTDD   CRITICALITY ignore	TYPE  DL-DPCH-InformationModifyItem-LCR-RL-ReconfRspTDD		PRESENCE optional },
--	...
--}

DL-DPCH-InformationModifyItem-LCR-RL-ReconfRspTDD  ::= SEQUENCE {
	dL-Timeslot-LCR-InformationModifyList-RL-ReconfRqstTDD		DL-Timeslot-LCR-InformationModifyList-RL-ReconfRspTDD			OPTIONAL, 
--	iE-Extensions	ProtocolExtensionContainer { { DL-DPCH-InformationModifyItem-LCR-RL-ReconfRspTDD-ExtIEs} }		OPTIONAL,
	iE-Extensions	ProtocolExtensionContainer OPTIONAL,
	...
}

--DL-DPCH-InformationModifyItem-LCR-RL-ReconfRspTDD-ExtIEs  RNSAP-PROTOCOL-EXTENSION ::= {
--	...
--}

--DL-Timeslot-LCR-InformationModifyList-RL-ReconfRspTDD ::= SEQUENCE (SIZE (1..maxNrOfDLTsLCR)) OF DL-Timeslot-LCR-InformationModifyItem-RL-ReconfRspTDD
DL-Timeslot-LCR-InformationModifyList-RL-ReconfRspTDD ::= SEQUENCE (SIZE (1..6)) OF DL-Timeslot-LCR-InformationModifyItem-RL-ReconfRspTDD

DL-Timeslot-LCR-InformationModifyItem-RL-ReconfRspTDD	 ::= SEQUENCE {
	timeSlotLCR								TimeSlotLCR,
	maxPowerLCR								DL-Power	OPTIONAL,
	minPowerLCR								DL-Power	OPTIONAL,
--	iE-Extensions							ProtocolExtensionContainer { { DL-Timeslot-LCR-InformationModifyItem-RL-ReconfRspTDD-ExtIEs} }		OPTIONAL,
	iE-Extensions							ProtocolExtensionContainer OPTIONAL,
	...
}

--DL-Timeslot-LCR-InformationModifyItem-RL-ReconfRspTDD-ExtIEs RNSAP-PROTOCOL-EXTENSION ::= {
--	...
--}

--DCH-InformationResponseList-RL-ReconfRspTDD				::= ProtocolIE-Single-Container { {DCH-InformationResponseListIEs-RL-ReconfRspTDD} }
DCH-InformationResponseList-RL-ReconfRspTDD				::= ProtocolIE-Single-Container

--DCH-InformationResponseListIEs-RL-ReconfRspTDD RNSAP-PROTOCOL-IES ::= {
--	{ ID id-DCH-InformationResponse	CRITICALITY ignore	TYPE DCH-InformationResponse	PRESENCE optional	}
--}

--RadioLinkReconfigurationResponseTDD-Extensions RNSAP-PROTOCOL-EXTENSION ::= {
--	{ ID id-HSDSCH-RNTI							CRITICALITY ignore		EXTENSION HSDSCH-RNTI									PRESENCE optional }|
--	{ ID id-HSDSCH-TDD-Information-Response		CRITICALITY ignore		EXTENSION HSDSCH-TDD-Information-Response		PRESENCE optional }|
--	{ ID id-MAChs-ResetIndicator				CRITICALITY ignore		EXTENSION MAChs-ResetIndicator						PRESENCE optional }|
--	{ ID id-RL-ReconfigurationResponseTDD-RL-Information	CRITICALITY	ignore		EXTENSION 	Multiple-RL-InformationResponse-RL-ReconfRspTDD		PRESENCE 	optional},
--	...
--}

--Multiple-RL-InformationResponse-RL-ReconfRspTDD ::= SEQUENCE (SIZE (1..maxNrOfRLs-1)) OF RL-InformationResponse-RL-ReconfRspTDD
Multiple-RL-InformationResponse-RL-ReconfRspTDD ::= SEQUENCE (SIZE (1..15)) OF RL-InformationResponse-RL-ReconfRspTDD
--Includes the 2nd through the max number of radio link information repetitions.

-- **************************************************************
--
-- RADIO LINK FAILURE INDICATION
--
-- **************************************************************

--RadioLinkFailureIndication ::= SEQUENCE {
--	protocolIEs                     ProtocolIE-Container       {{RadioLinkFailureIndication-IEs}},
--	protocolExtensions              ProtocolExtensionContainer {{RadioLinkFailureIndication-Extensions}}                   OPTIONAL,
--	...
--}
RadioLinkFailureIndication ::= SEQUENCE {
	protocolIEs                     ProtocolIE-Container,
	protocolExtensions              ProtocolExtensionContainer OPTIONAL,
	...
}

--RadioLinkFailureIndication-IEs RNSAP-PROTOCOL-IES ::= {
--	{ ID id-Reporting-Object-RL-FailureInd	CRITICALITY ignore	TYPE Reporting-Object-RL-FailureInd		PRESENCE mandatory	},
--	...
--}

Reporting-Object-RL-FailureInd ::= CHOICE {
	rL						RL-RL-FailureInd,
	rL-Set					RL-Set-RL-FailureInd,
	 --FDD only
	...,
	cCTrCH					CCTrCH-RL-FailureInd
	  --TDD only
}

RL-RL-FailureInd		 	::= SEQUENCE {
	rL-InformationList-RL-FailureInd		RL-InformationList-RL-FailureInd,
--	iE-Extensions							ProtocolExtensionContainer { { RLItem-RL-FailureInd-ExtIEs} } OPTIONAL,
	iE-Extensions							ProtocolExtensionContainer OPTIONAL,
	...
} 

--RLItem-RL-FailureInd-ExtIEs RNSAP-PROTOCOL-EXTENSION ::= {
--	...
--}

--RL-InformationList-RL-FailureInd		 	::= SEQUENCE (SIZE (1..maxNrOfRLs)) OF ProtocolIE-Single-Container { {RL-Information-RL-FailureInd-IEs} }
RL-InformationList-RL-FailureInd		 	::= SEQUENCE (SIZE (1..16)) OF ProtocolIE-Single-Container

--RL-Information-RL-FailureInd-IEs RNSAP-PROTOCOL-IES ::= {
--	{ ID id-RL-Information-RL-FailureInd		CRITICALITY ignore	TYPE RL-Information-RL-FailureInd		PRESENCE mandatory	}
--}

RL-Information-RL-FailureInd ::= SEQUENCE {
	rL-ID						RL-ID,
	cause						Cause,
--	iE-Extensions					ProtocolExtensionContainer { {RL-Information-RL-FailureInd-ExtIEs} } OPTIONAL,
	iE-Extensions					ProtocolExtensionContainer OPTIONAL,
	...
} 

--RL-Information-RL-FailureInd-ExtIEs RNSAP-PROTOCOL-EXTENSION ::= {
--	...
--}

RL-Set-RL-FailureInd		 	::= SEQUENCE {
	rL-Set-InformationList-RL-FailureInd	RL-Set-InformationList-RL-FailureInd,
--	iE-Extensions							ProtocolExtensionContainer { { RL-SetItem-RL-FailureInd-ExtIEs} } OPTIONAL,
	iE-Extensions							ProtocolExtensionContainer OPTIONAL,
	...
} 

--RL-SetItem-RL-FailureInd-ExtIEs RNSAP-PROTOCOL-EXTENSION ::= {
--	...
--}

--RL-Set-InformationList-RL-FailureInd		 	::= SEQUENCE (SIZE (1..maxNrOfRLSets)) OF ProtocolIE-Single-Container { {RL-Set-Information-RL-FailureInd-IEs} }
RL-Set-InformationList-RL-FailureInd		 	::= SEQUENCE (SIZE (1..16)) OF ProtocolIE-Single-Container

--RL-Set-Information-RL-FailureInd-IEs RNSAP-PROTOCOL-IES ::= {
--	{ ID id-RL-Set-Information-RL-FailureInd		CRITICALITY ignore	TYPE RL-Set-Information-RL-FailureInd		PRESENCE mandatory	}
--}

RL-Set-Information-RL-FailureInd ::= SEQUENCE {
	rL-Set-ID						RL-Set-ID,
	cause							Cause,
--	iE-Extensions					ProtocolExtensionContainer { {RL-Set-Information-RL-FailureInd-ExtIEs} } OPTIONAL,
	iE-Extensions					ProtocolExtensionContainer OPTIONAL,
	...
} 

--RL-Set-Information-RL-FailureInd-ExtIEs RNSAP-PROTOCOL-EXTENSION ::= {
--	...
--}

--RadioLinkFailureIndication-Extensions RNSAP-PROTOCOL-EXTENSION ::= {
--	...
--}

CCTrCH-RL-FailureInd ::= SEQUENCE {
	rL-ID										RL-ID,
	cCTrCH-InformationList-RL-FailureInd		CCTrCH-InformationList-RL-FailureInd,
--	iE-Extensions							ProtocolExtensionContainer { { CCTrCHItem-RL-FailureInd-ExtIEs } }		OPTIONAL,
	iE-Extensions							ProtocolExtensionContainer OPTIONAL,
	...
 }

--CCTrCHItem-RL-FailureInd-ExtIEs RNSAP-PROTOCOL-EXTENSION ::= {
--	...
--}

--CCTrCH-InformationList-RL-FailureInd ::= SEQUENCE (SIZE (1..maxNrOfCCTrCHs)) OF ProtocolIE-Single-Container {{ CCTrCH-InformationItemIE-RL-FailureInd}}
CCTrCH-InformationList-RL-FailureInd ::= SEQUENCE (SIZE (1..16)) OF ProtocolIE-Single-Container

--CCTrCH-InformationItemIE-RL-FailureInd RNSAP-PROTOCOL-IES ::= {
 --	{ ID	id-CCTrCH-InformationItem-RL-FailureInd			CRITICALITY		ignore			TYPE	CCTrCH-InformationItem-RL-FailureInd			PRESENCE	mandatory}
 --}

CCTrCH-InformationItem-RL-FailureInd ::= SEQUENCE {
 	cCTrCH-ID									CCTrCH-ID,
	cause										Cause,
--	iE-Extensions								ProtocolExtensionContainer { { CCTrCH-InformationItem-RL-FailureInd-ExtIEs } }		OPTIONAL,
	iE-Extensions								ProtocolExtensionContainer OPTIONAL,
	...
 }

--CCTrCH-InformationItem-RL-FailureInd-ExtIEs RNSAP-PROTOCOL-EXTENSION ::= {
--	...
--}

-- **************************************************************
--
-- RADIO LINK PREEMPTION REQUIRED INDICATION
--
-- **************************************************************
--RadioLinkPreemptionRequiredIndication ::= SEQUENCE {
--	protocolIEs                     ProtocolIE-Container       {{RadioLinkPreemptionRequiredIndication-IEs}},
--	protocolExtensions              ProtocolExtensionContainer {{RadioLinkPreemptionRequiredIndication-Extensions}}                   OPTIONAL,
--	...
--}
RadioLinkPreemptionRequiredIndication ::= SEQUENCE {
	protocolIEs                     ProtocolIE-Container,
	protocolExtensions              ProtocolExtensionContainer OPTIONAL,
	...
}
--RadioLinkPreemptionRequiredIndication-IEs RNSAP-PROTOCOL-IES ::= {
--	{ ID id-RL-InformationList-RL-PreemptRequiredInd	CRITICALITY ignore	TYPE RL-InformationList-RL-PreemptRequiredInd		PRESENCE optional	},
--	...
--}

--RL-InformationList-RL-PreemptRequiredInd			::= SEQUENCE (SIZE (1..maxNrOfRLs)) OF ProtocolIE-Single-Container { {RL-InformationItemIEs-RL-PreemptRequiredInd} }
RL-InformationList-RL-PreemptRequiredInd			::= SEQUENCE (SIZE (1..16)) OF ProtocolIE-Single-Container

--RL-InformationItemIEs-RL-PreemptRequiredInd RNSAP-PROTOCOL-IES ::= {
--	{ ID id-RL-InformationItem-RL-PreemptRequiredInd		CRITICALITY ignore	TYPE RL-InformationItem-RL-PreemptRequiredInd		PRESENCE mandatory	}
--}

RL-InformationItem-RL-PreemptRequiredInd::= SEQUENCE {
	rL-ID						RL-ID,
--	iE-Extensions				ProtocolExtensionContainer { {RL-Information-RL-PreemptRequiredInd-ExtIEs} } OPTIONAL,
	iE-Extensions				ProtocolExtensionContainer OPTIONAL,
	...
}

--RL-Information-RL-PreemptRequiredInd-ExtIEs RNSAP-PROTOCOL-EXTENSION ::= {
--	{ ID id-EDCH-MacdFlowSpecificInformationList-RL-PreemptRequiredInd  CRITICALITY ignore	EXTENSION EDCH-MacdFlowSpecificInformationList-RL-PreemptRequiredInd PRESENCE optional },
--	...
--}

--RadioLinkPreemptionRequiredIndication-Extensions RNSAP-PROTOCOL-EXTENSION ::= {
--	{ ID id-HSDSCHMacdFlowSpecificInformationList-RL-PreemptRequiredInd  CRITICALITY ignore	EXTENSION HSDSCHMacdFlowSpecificInformationList-RL-PreemptRequiredInd PRESENCE optional }, 
--	...
--}

--HSDSCHMacdFlowSpecificInformationList-RL-PreemptRequiredInd	::= SEQUENCE (SIZE (1.. maxNrOfMACdFlows)) OF ProtocolIE-Single-Container { {HSDSCHMacdFlowSpecificInformationItemIEs-RL-PreemptRequiredInd} }
HSDSCHMacdFlowSpecificInformationList-RL-PreemptRequiredInd	::= SEQUENCE (SIZE (1.. 8)) OF ProtocolIE-Single-Container

--HSDSCHMacdFlowSpecificInformationItemIEs-RL-PreemptRequiredInd RNSAP-PROTOCOL-IES ::= {
--	{ ID id-HSDSCHMacdFlowSpecificInformationItem-RL-PreemptRequiredInd		CRITICALITY ignore	TYPE HSDSCHMacdFlowSpecificInformationItem-RL-PreemptRequiredInd	PRESENCE mandatory	}
--}

HSDSCHMacdFlowSpecificInformationItem-RL-PreemptRequiredInd ::= SEQUENCE {
	hSDSCH-MACdFlow-ID						HSDSCH-MACdFlow-ID,
--	iE-Extensions				ProtocolExtensionContainer { { HSDSCHMacdFlowSpecificInformation-RL-PreemptRequiredInd-ExtIEs} } OPTIONAL,
	iE-Extensions				ProtocolExtensionContainer OPTIONAL,
	...
}

--HSDSCHMacdFlowSpecificInformation-RL-PreemptRequiredInd-ExtIEs RNSAP-PROTOCOL-EXTENSION ::= {
--	...
--}

--EDCH-MacdFlowSpecificInformationList-RL-PreemptRequiredInd	::= SEQUENCE (SIZE (1.. maxNrOfEDCHMACdFlows)) OF ProtocolIE-Single-Container { {EDCH-MacdFlowSpecificInformationItemIEs-RL-PreemptRequiredInd} }
EDCH-MacdFlowSpecificInformationList-RL-PreemptRequiredInd	::= SEQUENCE (SIZE (1.. 8)) OF ProtocolIE-Single-Container

--EDCH-MacdFlowSpecificInformationItemIEs-RL-PreemptRequiredInd RNSAP-PROTOCOL-IES ::= {
--	{ ID id-EDCH-MacdFlowSpecificInformationItem-RL-PreemptRequiredInd		CRITICALITY ignore	TYPE EDCH-MacdFlowSpecificInformationItem-RL-PreemptRequiredInd	PRESENCE mandatory	}
--}

EDCH-MacdFlowSpecificInformationItem-RL-PreemptRequiredInd ::= SEQUENCE {
	eDCH-MACdFlow-ID			EDCH-MACdFlow-ID,
--	iE-Extensions				ProtocolExtensionContainer { { EDCH-MacdFlowSpecificInformation-RL-PreemptRequiredInd-ExtIEs} } OPTIONAL,
	iE-Extensions				ProtocolExtensionContainer OPTIONAL,
	...
}

--EDCH-MacdFlowSpecificInformation-RL-PreemptRequiredInd-ExtIEs RNSAP-PROTOCOL-EXTENSION ::= {
--	...
--}


-- **************************************************************
--
-- RADIO LINK RESTORE INDICATION
--
-- **************************************************************

--RadioLinkRestoreIndication ::= SEQUENCE {
--	protocolIEs                     ProtocolIE-Container       {{RadioLinkRestoreIndication-IEs}},
--	protocolExtensions              ProtocolExtensionContainer {{RadioLinkRestoreIndication-Extensions}}                   OPTIONAL,
--	...
--}
RadioLinkRestoreIndication ::= SEQUENCE {
	protocolIEs                     ProtocolIE-Container,
	protocolExtensions              ProtocolExtensionContainer OPTIONAL,
	...
}

--RadioLinkRestoreIndication-IEs RNSAP-PROTOCOL-IES ::= {
--	{ ID id-Reporing-Object-RL-RestoreInd	CRITICALITY ignore	TYPE Reporting-Object-RL-RestoreInd		PRESENCE mandatory	},
--	...
--}

Reporting-Object-RL-RestoreInd ::= CHOICE {
	rL						RL-RL-RestoreInd, --TDD only
	rL-Set					RL-Set-RL-RestoreInd, --FDD only
	...,
	cCTrCH					CCTrCH-RL-RestoreInd  --TDD only
}

RL-RL-RestoreInd ::= SEQUENCE {
	rL-InformationList-RL-RestoreInd		RL-InformationList-RL-RestoreInd,
--	iE-Extensions							ProtocolExtensionContainer { { RLItem-RL-RestoreInd-ExtIEs} } OPTIONAL,
	iE-Extensions							ProtocolExtensionContainer OPTIONAL,
	...
} 

--RLItem-RL-RestoreInd-ExtIEs RNSAP-PROTOCOL-EXTENSION ::= {
--	...
--}

--RL-InformationList-RL-RestoreInd		 	::= SEQUENCE (SIZE (1..maxNrOfRLs)) OF ProtocolIE-Single-Container { {RL-Information-RL-RestoreInd-IEs} }
RL-InformationList-RL-RestoreInd		 	::= SEQUENCE (SIZE (1..16)) OF ProtocolIE-Single-Container

--RL-Information-RL-RestoreInd-IEs RNSAP-PROTOCOL-IES ::= {
--	{ ID id-RL-Information-RL-RestoreInd		CRITICALITY ignore	TYPE RL-Information-RL-RestoreInd		PRESENCE mandatory	}
--}

RL-Information-RL-RestoreInd ::= SEQUENCE {
	rL-ID						RL-ID,
--	iE-Extensions					ProtocolExtensionContainer { {RL-Information-RL-RestoreInd-ExtIEs} } OPTIONAL,
	iE-Extensions					ProtocolExtensionContainer OPTIONAL,
	...
} 

--RL-Information-RL-RestoreInd-ExtIEs RNSAP-PROTOCOL-EXTENSION ::= {
--	...
--}

RL-Set-RL-RestoreInd ::= SEQUENCE {
	rL-Set-InformationList-RL-RestoreInd	RL-Set-InformationList-RL-RestoreInd,
--	iE-Extensions							ProtocolExtensionContainer { { RL-SetItem-RL-RestoreInd-ExtIEs} } OPTIONAL,
	iE-Extensions							ProtocolExtensionContainer OPTIONAL,
	...
} 

--RL-SetItem-RL-RestoreInd-ExtIEs RNSAP-PROTOCOL-EXTENSION ::= {
--	...
--}

--RL-Set-InformationList-RL-RestoreInd		 	::= SEQUENCE (SIZE (1..maxNrOfRLSets)) OF ProtocolIE-Single-Container { {RL-Set-Information-RL-RestoreInd-IEs} }
RL-Set-InformationList-RL-RestoreInd		 	::= SEQUENCE (SIZE (1..16)) OF ProtocolIE-Single-Container

--RL-Set-Information-RL-RestoreInd-IEs RNSAP-PROTOCOL-IES ::= {
--	{ ID id-RL-Set-Information-RL-RestoreInd		CRITICALITY ignore	TYPE RL-Set-Information-RL-RestoreInd		PRESENCE mandatory	}
--}

RL-Set-Information-RL-RestoreInd ::= SEQUENCE {
	rL-Set-ID						RL-Set-ID,
--	iE-Extensions					ProtocolExtensionContainer { {RL-Set-Information-RL-RestoreInd-ExtIEs} } OPTIONAL,
	iE-Extensions					ProtocolExtensionContainer OPTIONAL,
	...
} 

--RL-Set-Information-RL-RestoreInd-ExtIEs RNSAP-PROTOCOL-EXTENSION ::= {
--	...
--}

--RadioLinkRestoreIndication-Extensions RNSAP-PROTOCOL-EXTENSION ::= {
--	...
--}

CCTrCH-RL-RestoreInd ::= SEQUENCE {
	rL-ID										RL-ID,
	cCTrCH-InformationList-RL-RestoreInd		CCTrCH-InformationList-RL-RestoreInd,
--	iE-Extensions							ProtocolExtensionContainer { { CCTrCHItem-RL-RestoreInd-ExtIEs } }		OPTIONAL,
	iE-Extensions							ProtocolExtensionContainer OPTIONAL,
	...
 }

--CCTrCHItem-RL-RestoreInd-ExtIEs RNSAP-PROTOCOL-EXTENSION ::= {
--	...
--}

--CCTrCH-InformationList-RL-RestoreInd ::= SEQUENCE (SIZE (1..maxNrOfCCTrCHs)) OF ProtocolIE-Single-Container {{ CCTrCH-InformationItemIE-RL-RestoreInd}}
CCTrCH-InformationList-RL-RestoreInd ::= SEQUENCE (SIZE (1..16)) OF ProtocolIE-Single-Container

--CCTrCH-InformationItemIE-RL-RestoreInd RNSAP-PROTOCOL-IES ::= {
--	{ ID	id-CCTrCH-InformationItem-RL-RestoreInd			CRITICALITY		ignore			TYPE	CCTrCH-InformationItem-RL-RestoreInd			PRESENCE	mandatory}
-- }

CCTrCH-InformationItem-RL-RestoreInd ::= SEQUENCE {
 	cCTrCH-ID										CCTrCH-ID,
--	iE-Extensions								ProtocolExtensionContainer { { CCTrCH-InformationItem-RL-RestoreInd-ExtIEs } }		OPTIONAL,
	iE-Extensions								ProtocolExtensionContainer OPTIONAL,
	...
 }

--CCTrCH-InformationItem-RL-RestoreInd-ExtIEs RNSAP-PROTOCOL-EXTENSION ::= {
--	...
--}

-- **************************************************************
--
-- DOWNLINK POWER CONTROL REQUEST
--
-- **************************************************************
--DL-PowerControlRequest ::= SEQUENCE {
--	protocolIEs                     ProtocolIE-Container       {{DL-PowerControlRequest-IEs}},
--	protocolExtensions              ProtocolExtensionContainer {{DL-PowerControlRequest-Extensions}}                   OPTIONAL,
--	...
--}
DL-PowerControlRequest ::= SEQUENCE {
	protocolIEs                     ProtocolIE-Container,
	protocolExtensions              ProtocolExtensionContainer OPTIONAL,
	...
}
--DL-PowerControlRequest-IEs RNSAP-PROTOCOL-IES ::= {
--	{ ID id-PowerAdjustmentType			CRITICALITY ignore	TYPE PowerAdjustmentType				PRESENCE mandatory} |
--  { ID id-DLReferencePower			CRITICALITY ignore	TYPE DL-Power							PRESENCE conditional} |
	-- This IE shall be present if Power Adjustment Type IE equals to 'Common'
--	{ ID id-InnerLoopDLPCStatus			CRITICALITY	ignore	TYPE InnerLoopDLPCStatus				PRESENCE	optional } |
--	{ ID id-DLReferencePowerList-DL-PC-Rqst		CRITICALITY ignore	TYPE DL-ReferencePowerInformationList-DL-PC-Rqst	PRESENCE conditional} |
	-- This IE shall be present if Power Adjustment Type IE equals to 'Individual'
--	{ ID id-MaxAdjustmentStep			CRITICALITY ignore	TYPE MaxAdjustmentStep			PRESENCE conditional	} |
	-- This IE shall be present if Power Adjustment Type IE equals to 'Common' or 'Individual'
--	{ ID id-AdjustmentPeriod			CRITICALITY ignore	TYPE AdjustmentPeriod			PRESENCE conditional	}|
	-- This IE shall be present if Power Adjustment Type IE equals to 'Common' or 'Individual'
--	{ ID id-AdjustmentRatio			CRITICALITY ignore	TYPE ScaledAdjustmentRatio			PRESENCE conditional	},
	-- This IE shall be present if Power Adjustment Type IE equals to 'Common' or 'Individual'
--	...
--}

--DL-ReferencePowerInformationList-DL-PC-Rqst 		::= SEQUENCE (SIZE (1..maxNrOfRLs)) OF ProtocolIE-Single-Container { {DL-ReferencePowerInformation-DL-PC-Rqst-IEs} }
DL-ReferencePowerInformationList-DL-PC-Rqst 		::= SEQUENCE (SIZE (1..16)) OF ProtocolIE-Single-Container

--DL-ReferencePowerInformation-DL-PC-Rqst-IEs RNSAP-PROTOCOL-IES ::= {
--	{ ID id-DL-ReferencePowerInformation-DL-PC-Rqst	CRITICALITY ignore	TYPE DL-ReferencePowerInformation-DL-PC-Rqst	PRESENCE mandatory	}
--}

DL-ReferencePowerInformation-DL-PC-Rqst ::= SEQUENCE {
	rL-ID						RL-ID,
	dl-Reference-Power					DL-Power,
--	iE-Extensions					ProtocolExtensionContainer { {DL-ReferencePowerInformation-DL-PC-Rqst-ExtIEs} } OPTIONAL,
	iE-Extensions					ProtocolExtensionContainer OPTIONAL,
	...
}

--DL-ReferencePowerInformation-DL-PC-Rqst-ExtIEs RNSAP-PROTOCOL-EXTENSION ::= {
--	...
--}

--DL-PowerControlRequest-Extensions RNSAP-PROTOCOL-EXTENSION ::= {
--	...
--}

-- **************************************************************
--
-- DOWNLINK POWER TIMESLOT CONTROL REQUEST TDD
--
-- **************************************************************

--DL-PowerTimeslotControlRequest ::= SEQUENCE {
--	protocolIEs                     ProtocolIE-Container       {{DL-PowerTimeslotControlRequest-IEs}},
--	protocolExtensions              ProtocolExtensionContainer {{DL-PowerTimeslotControlRequest-Extensions}}                   OPTIONAL,
--	...
--}
DL-PowerTimeslotControlRequest ::= SEQUENCE {
	protocolIEs                     ProtocolIE-Container,
	protocolExtensions              ProtocolExtensionContainer OPTIONAL,
	...
}

--DL-PowerTimeslotControlRequest-IEs RNSAP-PROTOCOL-IES ::= {
--	{ ID id-timeSlot-ISCP	CRITICALITY ignore	TYPE DL-TimeSlot-ISCP-Info	PRESENCE optional},
	--Mandatory for 3.84Mcps TDD only
--	...
--}

--DL-PowerTimeslotControlRequest-Extensions RNSAP-PROTOCOL-EXTENSION ::= {
--	{ ID id-timeSlot-ISCP-LCR-List-DL-PC-Rqst-TDD	CRITICALITY 	ignore	EXTENSION 	 DL-TimeSlot-ISCP-LCR-Information		PRESENCE optional}|
	--Mandatory for 1.28Mcps TDD only
--	{ ID id-PrimCCPCH-RSCP-DL-PC-RqstTDD			CRITICALITY ignore		EXTENSION PrimaryCCPCH-RSCP				PRESENCE optional }|
--	{ ID id-PrimaryCCPCH-RSCP-Delta		CRITICALITY	ignore		EXTENSION 	PrimaryCCPCH-RSCP-Delta		PRESENCE 	optional	},
--	...
--}

-- **************************************************************
--
-- PHYSICAL CHANNEL RECONFIGURATION REQUEST FDD
--
-- **************************************************************

--PhysicalChannelReconfigurationRequestFDD ::= SEQUENCE {
--	protocolIEs                     ProtocolIE-Container       {{PhysicalChannelReconfigurationRequestFDD-IEs}},
--	protocolExtensions              ProtocolExtensionContainer {{PhysicalChannelReconfigurationRequestFDD-Extensions}}                   OPTIONAL,
--	...
--}
PhysicalChannelReconfigurationRequestFDD ::= SEQUENCE {
	protocolIEs                     ProtocolIE-Container,
	protocolExtensions              ProtocolExtensionContainer OPTIONAL,
	...
}
--PhysicalChannelReconfigurationRequestFDD-IEs RNSAP-PROTOCOL-IES ::= {
--	{ ID id-RL-Information-PhyChReconfRqstFDD	CRITICALITY reject	TYPE RL-Information-PhyChReconfRqstFDD		PRESENCE mandatory	},
--	...
--}

RL-Information-PhyChReconfRqstFDD ::= SEQUENCE {
	rL-ID						RL-ID,
	dl-CodeInformation				DL-CodeInformationList-PhyChReconfRqstFDD,
--	iE-Extensions					ProtocolExtensionContainer { {RL-Information-PhyChReconfRqstFDD-ExtIEs} } OPTIONAL,
	iE-Extensions					ProtocolExtensionContainer OPTIONAL,
	...
}

--RL-Information-PhyChReconfRqstFDD-ExtIEs RNSAP-PROTOCOL-EXTENSION ::= {
--	...
--}

--DL-CodeInformationList-PhyChReconfRqstFDD 		::= ProtocolIE-Single-Container { {DL-CodeInformationListIEs-PhyChReconfRqstFDD} }
DL-CodeInformationList-PhyChReconfRqstFDD 		::= ProtocolIE-Single-Container

--DL-CodeInformationListIEs-PhyChReconfRqstFDD RNSAP-PROTOCOL-IES ::= {
--	{ ID id-FDD-DL-CodeInformation	CRITICALITY notify	TYPE FDD-DL-CodeInformation	PRESENCE mandatory	}
--}

--PhysicalChannelReconfigurationRequestFDD-Extensions RNSAP-PROTOCOL-EXTENSION ::= {
--	...
--}

-- **************************************************************
--
-- PHYSICAL CHANNEL RECONFIGURATION REQUEST TDD
--
-- **************************************************************

--PhysicalChannelReconfigurationRequestTDD ::= SEQUENCE {
--	protocolIEs                     ProtocolIE-Container       {{PhysicalChannelReconfigurationRequestTDD-IEs}},
--	protocolExtensions              ProtocolExtensionContainer {{PhysicalChannelReconfigurationRequestTDD-Extensions}}                   OPTIONAL,
--	...
--}
PhysicalChannelReconfigurationRequestTDD ::= SEQUENCE {
	protocolIEs                     ProtocolIE-Container,
	protocolExtensions              ProtocolExtensionContainer OPTIONAL,
	...
}

--PhysicalChannelReconfigurationRequestTDD-IEs RNSAP-PROTOCOL-IES ::= {
--	{ ID id-RL-Information-PhyChReconfRqstTDD	CRITICALITY reject	TYPE RL-Information-PhyChReconfRqstTDD		PRESENCE mandatory	},
--	...
--}

RL-Information-PhyChReconfRqstTDD ::= SEQUENCE {
	rL-ID						RL-ID,
	ul-CCTrCH-Information				UL-CCTrCH-InformationList-PhyChReconfRqstTDD	OPTIONAL,
	dl-CCTrCH-Information				DL-CCTrCH-InformationList-PhyChReconfRqstTDD	OPTIONAL,
--	iE-Extensions					ProtocolExtensionContainer { {RL-Information-PhyChReconfRqstTDD-ExtIEs} } OPTIONAL,
	iE-Extensions					ProtocolExtensionContainer OPTIONAL,
	...
}

--RL-Information-PhyChReconfRqstTDD-ExtIEs RNSAP-PROTOCOL-EXTENSION ::= {
--	{ ID id-HSPDSCH-Timeslot-InformationList-PhyChReconfRqstTDD		CRITICALITY reject	EXTENSION HSPDSCH-Timeslot-InformationList-PhyChReconfRqstTDD		PRESENCE optional } |
	--For 3.84Mcps TDD only
--	{ ID id-HSPDSCH-Timeslot-InformationListLCR-PhyChReconfRqstTDD	CRITICALITY reject	EXTENSION HSPDSCH-Timeslot-InformationListLCR-PhyChReconfRqstTDD	PRESENCE optional },
	--For 1.28Mcps TDD only
--	...
--}

--UL-CCTrCH-InformationList-PhyChReconfRqstTDD 		::= ProtocolIE-Single-Container { {UL-CCTrCH-InformationListIEs-PhyChReconfRqstTDD} }
UL-CCTrCH-InformationList-PhyChReconfRqstTDD 		::= ProtocolIE-Single-Container

--UL-CCTrCH-InformationListIEs-PhyChReconfRqstTDD RNSAP-PROTOCOL-IES ::= {
--	{ ID id-UL-CCTrCH-InformationListIE-PhyChReconfRqstTDD		CRITICALITY reject	TYPE UL-CCTrCH-InformationListIE-PhyChReconfRqstTDD		PRESENCE mandatory	}
--}

--UL-CCTrCH-InformationListIE-PhyChReconfRqstTDD ::= SEQUENCE (SIZE (1..maxNrOfCCTrCHs)) OF UL-CCTrCH-InformationItem-PhyChReconfRqstTDD
UL-CCTrCH-InformationListIE-PhyChReconfRqstTDD ::= SEQUENCE (SIZE (1..16)) OF UL-CCTrCH-InformationItem-PhyChReconfRqstTDD

UL-CCTrCH-InformationItem-PhyChReconfRqstTDD ::= SEQUENCE {
	cCTrCH-ID						CCTrCH-ID,
	ul-DPCH-Information				UL-DPCH-InformationList-PhyChReconfRqstTDD,
--	iE-Extensions					ProtocolExtensionContainer { {UL-CCTrCH-InformationItem-PhyChReconfRqstTDD-ExtIEs} } OPTIONAL,
	iE-Extensions					ProtocolExtensionContainer OPTIONAL,
	...
}

--UL-CCTrCH-InformationItem-PhyChReconfRqstTDD-ExtIEs RNSAP-PROTOCOL-EXTENSION ::= {
--	...
--}

--UL-DPCH-InformationList-PhyChReconfRqstTDD ::= ProtocolIE-Single-Container {{UL-DPCH-InformationListIEs-PhyChReconfRqstTDD}}
UL-DPCH-InformationList-PhyChReconfRqstTDD ::= ProtocolIE-Single-Container

--UL-DPCH-InformationListIEs-PhyChReconfRqstTDD RNSAP-PROTOCOL-IES ::= {
--	{ ID id-UL-DPCH-InformationItem-PhyChReconfRqstTDD   CRITICALITY notify	TYPE UL-DPCH-InformationItem-PhyChReconfRqstTDD		PRESENCE mandatory }
--}

UL-DPCH-InformationItem-PhyChReconfRqstTDD ::= SEQUENCE {
	repetitionPeriod				RepetitionPeriod		OPTIONAL,
	repetitionLength				RepetitionLength		OPTIONAL,
	tDD-DPCHOffset					TDD-DPCHOffset			OPTIONAL,
	uL-Timeslot-InformationList-PhyChReconfRqstTDD			UL-Timeslot-InformationList-PhyChReconfRqstTDD		OPTIONAL,
	--For 3.84Mcps TDD only
--	iE-Extensions					ProtocolExtensionContainer { {UL-DPCH-InformationItem-PhyChReconfRqstTDD-ExtIEs} } OPTIONAL,
	iE-Extensions					ProtocolExtensionContainer OPTIONAL,
	...
}

--UL-DPCH-InformationItem-PhyChReconfRqstTDD-ExtIEs RNSAP-PROTOCOL-EXTENSION ::= {
--	{ ID id-UL-Timeslot-LCR-InformationList-PhyChReconfRqstTDD   CRITICALITY reject		EXTENSION  UL-TimeslotLCR-InformationList-PhyChReconfRqstTDD		PRESENCE optional },
	--For 1.28Mcps TDD only
--	...
--}

--UL-TimeslotLCR-InformationList-PhyChReconfRqstTDD::= SEQUENCE ( SIZE (1..maxNrOfTsLCR)) OF UL-TimeslotLCR-InformationItem-PhyChReconfRqstTDD
UL-TimeslotLCR-InformationList-PhyChReconfRqstTDD::= SEQUENCE ( SIZE (1..6)) OF UL-TimeslotLCR-InformationItem-PhyChReconfRqstTDD

UL-TimeslotLCR-InformationItem-PhyChReconfRqstTDD ::= SEQUENCE {
	timeSlotLCR						TimeSlotLCR,
	midambleShiftLCR				MidambleShiftLCR		OPTIONAL,
	tFCI-Presence					TFCI-Presence		OPTIONAL,
	uL-Code-LCR-Information			TDD-UL-Code-LCR-Information		OPTIONAL,
--	iE-Extensions					ProtocolExtensionContainer { {UL-TimeslotLCR-InformationItem-PhyChReconfRqstTDD-ExtIEs} } OPTIONAL,
	iE-Extensions					ProtocolExtensionContainer OPTIONAL,
	...
}

--UL-TimeslotLCR-InformationItem-PhyChReconfRqstTDD-ExtIEs RNSAP-PROTOCOL-EXTENSION ::= {
--	...
--}

--UL-Timeslot-InformationList-PhyChReconfRqstTDD::= SEQUENCE ( SIZE (1..maxNrOfTS)) OF UL-Timeslot-InformationItem-PhyChReconfRqstTDD
UL-Timeslot-InformationList-PhyChReconfRqstTDD::= SEQUENCE ( SIZE (1..15)) OF UL-Timeslot-InformationItem-PhyChReconfRqstTDD

UL-Timeslot-InformationItem-PhyChReconfRqstTDD ::= SEQUENCE {
	timeSlot						TimeSlot,
	midambleShiftAndBurstType					MidambleShiftAndBurstType		OPTIONAL,
	tFCI-Presence					TFCI-Presence		OPTIONAL,
	uL-Code-Information			TDD-UL-Code-Information		OPTIONAL,
--	iE-Extensions					ProtocolExtensionContainer { {UL-Timeslot-InformationItem-PhyChReconfRqstTDD-ExtIEs} } OPTIONAL,
	iE-Extensions					ProtocolExtensionContainer OPTIONAL,
	...
}

--UL-Timeslot-InformationItem-PhyChReconfRqstTDD-ExtIEs RNSAP-PROTOCOL-EXTENSION ::= {
--	...
--}

--DL-CCTrCH-InformationList-PhyChReconfRqstTDD 		::= ProtocolIE-Single-Container { {DL-CCTrCH-InformationListIEs-PhyChReconfRqstTDD} }
DL-CCTrCH-InformationList-PhyChReconfRqstTDD 		::= ProtocolIE-Single-Container

--DL-CCTrCH-InformationListIEs-PhyChReconfRqstTDD RNSAP-PROTOCOL-IES ::= {
--	{ ID id-DL-CCTrCH-InformationListIE-PhyChReconfRqstTDD		CRITICALITY reject	TYPE DL-CCTrCH-InformationListIE-PhyChReconfRqstTDD		PRESENCE mandatory	}
--}

--DL-CCTrCH-InformationListIE-PhyChReconfRqstTDD ::= SEQUENCE (SIZE (1..maxNrOfCCTrCHs)) OF DL-CCTrCH-InformationItem-PhyChReconfRqstTDD
DL-CCTrCH-InformationListIE-PhyChReconfRqstTDD ::= SEQUENCE (SIZE (1..16)) OF DL-CCTrCH-InformationItem-PhyChReconfRqstTDD

DL-CCTrCH-InformationItem-PhyChReconfRqstTDD ::= SEQUENCE {
	cCTrCH-ID						CCTrCH-ID,
	dl-DPCH-Information				DL-DPCH-InformationList-PhyChReconfRqstTDD,
--	iE-Extensions					ProtocolExtensionContainer { {DL-CCTrCH-InformationItem-PhyChReconfRqstTDD-ExtIEs} } OPTIONAL,
	iE-Extensions					ProtocolExtensionContainer OPTIONAL,
	...
}

--DL-CCTrCH-InformationItem-PhyChReconfRqstTDD-ExtIEs RNSAP-PROTOCOL-EXTENSION ::= {
--	...
--}

--DL-DPCH-InformationList-PhyChReconfRqstTDD ::= ProtocolIE-Single-Container {{DL-DPCH-InformationListIEs-PhyChReconfRqstTDD}}
DL-DPCH-InformationList-PhyChReconfRqstTDD ::= ProtocolIE-Single-Container

--DL-DPCH-InformationListIEs-PhyChReconfRqstTDD RNSAP-PROTOCOL-IES ::= {
--	{ ID id-DL-DPCH-InformationItem-PhyChReconfRqstTDD   CRITICALITY notify	TYPE DL-DPCH-InformationItem-PhyChReconfRqstTDD		PRESENCE mandatory }
--}

DL-DPCH-InformationItem-PhyChReconfRqstTDD ::= SEQUENCE {
	repetitionPeriod				RepetitionPeriod		OPTIONAL,
	repetitionLength				RepetitionLength		OPTIONAL,
	tDD-DPCHOffset					TDD-DPCHOffset			OPTIONAL,
	dL-Timeslot-InformationList-PhyChReconfRqstTDD			DL-Timeslot-InformationList-PhyChReconfRqstTDD		OPTIONAL,
--	iE-Extensions					ProtocolExtensionContainer { {DL-DPCH-InformationItem-PhyChReconfRqstTDD-ExtIEs} } OPTIONAL,
	iE-Extensions					ProtocolExtensionContainer OPTIONAL,
	...
}

--DL-DPCH-InformationItem-PhyChReconfRqstTDD-ExtIEs RNSAP-PROTOCOL-EXTENSION ::= {
--	{ ID id-DL-Timeslot-LCR-InformationList-PhyChReconfRqstTDD   CRITICALITY reject		EXTENSION  DL-TimeslotLCR-InformationList-PhyChReconfRqstTDD		PRESENCE optional },
	--For 1.28Mcps TDD only
--	...
--}

--DL-TimeslotLCR-InformationList-PhyChReconfRqstTDD::= SEQUENCE ( SIZE (1..maxNrOfTsLCR)) OF DL-TimeslotLCR-InformationItem-PhyChReconfRqstTDD
DL-TimeslotLCR-InformationList-PhyChReconfRqstTDD::= SEQUENCE ( SIZE (1..6)) OF DL-TimeslotLCR-InformationItem-PhyChReconfRqstTDD

DL-TimeslotLCR-InformationItem-PhyChReconfRqstTDD ::= SEQUENCE {
	timeSlotLCR						TimeSlotLCR,
	midambleShiftLCR				MidambleShiftLCR		OPTIONAL,
	tFCI-Presence					TFCI-Presence		OPTIONAL,
	dL-Code-LCR-Information			TDD-DL-Code-LCR-Information		OPTIONAL,
--	iE-Extensions					ProtocolExtensionContainer { {DL-TimeslotLCR-InformationItem-PhyChReconfRqstTDD-ExtIEs} } OPTIONAL,
	iE-Extensions					ProtocolExtensionContainer OPTIONAL,
	...
}

--DL-TimeslotLCR-InformationItem-PhyChReconfRqstTDD-ExtIEs RNSAP-PROTOCOL-EXTENSION ::= {
--	...
--}

--DL-Timeslot-InformationList-PhyChReconfRqstTDD::= SEQUENCE ( SIZE (1..maxNrOfTS)) OF DL-Timeslot-InformationItem-PhyChReconfRqstTDD
DL-Timeslot-InformationList-PhyChReconfRqstTDD::= SEQUENCE ( SIZE (1..15)) OF DL-Timeslot-InformationItem-PhyChReconfRqstTDD

DL-Timeslot-InformationItem-PhyChReconfRqstTDD ::= SEQUENCE {
	timeSlot						TimeSlot,
	midambleShiftAndBurstType					MidambleShiftAndBurstType		OPTIONAL,
	tFCI-Presence					TFCI-Presence		OPTIONAL,
	dL-Code-Information			TDD-DL-Code-Information		OPTIONAL,
--	iE-Extensions					ProtocolExtensionContainer { {DL-Timeslot-InformationItem-PhyChReconfRqstTDD-ExtIEs} } OPTIONAL,
	iE-Extensions					ProtocolExtensionContainer OPTIONAL,
	...
}

--DL-Timeslot-InformationItem-PhyChReconfRqstTDD-ExtIEs RNSAP-PROTOCOL-EXTENSION ::= {
--	...
--}

--HSPDSCH-Timeslot-InformationList-PhyChReconfRqstTDD ::= SEQUENCE (SIZE (1..maxNrOfDLTs)) OF HSPDSCH-Timeslot-InformationItem-PhyChReconfRqstTDD
HSPDSCH-Timeslot-InformationList-PhyChReconfRqstTDD ::= SEQUENCE (SIZE (1..15)) OF HSPDSCH-Timeslot-InformationItem-PhyChReconfRqstTDD

HSPDSCH-Timeslot-InformationItem-PhyChReconfRqstTDD::= SEQUENCE {
	timeslot										TimeSlot,
	midambleShiftAndBurstType						MidambleShiftAndBurstType,
--	iE-Extensions									ProtocolExtensionContainer { { HSPDSCH-Timeslot-InformationItem-PhyChReconfRqstTDD-ExtIEs } }			OPTIONAL,
	iE-Extensions									ProtocolExtensionContainer OPTIONAL,
	...
}

--HSPDSCH-Timeslot-InformationItem-PhyChReconfRqstTDD-ExtIEs RNSAP-PROTOCOL-EXTENSION ::= {
--	...
--}

--HSPDSCH-Timeslot-InformationListLCR-PhyChReconfRqstTDD::= SEQUENCE (SIZE (1..maxNrOfDLTsLCR)) OF HSPDSCH-Timeslot-InformationItemLCR-PhyChReconfRqstTDD
HSPDSCH-Timeslot-InformationListLCR-PhyChReconfRqstTDD::= SEQUENCE (SIZE (1..6)) OF HSPDSCH-Timeslot-InformationItemLCR-PhyChReconfRqstTDD

HSPDSCH-Timeslot-InformationItemLCR-PhyChReconfRqstTDD::= SEQUENCE {
	timeslotLCR									TimeSlotLCR,
	midambleShiftLCR							MidambleShiftLCR,
--	iE-Extensions								ProtocolExtensionContainer { { HSPDSCH-Timeslot-InformationItemLCR-PhyChReconfRqstTDD-ExtIEs } }			OPTIONAL,
	iE-Extensions								ProtocolExtensionContainer OPTIONAL,
	...
}

--HSPDSCH-Timeslot-InformationItemLCR-PhyChReconfRqstTDD-ExtIEs RNSAP-PROTOCOL-EXTENSION ::= {
--	...
--}

--PhysicalChannelReconfigurationRequestTDD-Extensions RNSAP-PROTOCOL-EXTENSION ::= {
--	...
--}

-- **************************************************************
--
-- PHYSICAL CHANNEL RECONFIGURATION COMMAND
--
-- **************************************************************

--PhysicalChannelReconfigurationCommand ::= SEQUENCE {
--	protocolIEs                     ProtocolIE-Container       {{PhysicalChannelReconfigurationCommand-IEs}},
--	protocolExtensions              ProtocolExtensionContainer {{PhysicalChannelReconfigurationCommand-Extensions}}                   OPTIONAL,
--	...
--}
PhysicalChannelReconfigurationCommand ::= SEQUENCE {
	protocolIEs                     ProtocolIE-Container,
	protocolExtensions              ProtocolExtensionContainer OPTIONAL,
	...
}
--PhysicalChannelReconfigurationCommand-IEs RNSAP-PROTOCOL-IES ::= {
--	{ ID id-CFN					CRITICALITY ignore	TYPE CFN					PRESENCE mandatory	} |
--	{ ID id-CriticalityDiagnostics			CRITICALITY ignore	TYPE CriticalityDiagnostics			PRESENCE optional	},
--	...
--}

--PhysicalChannelReconfigurationCommand-Extensions RNSAP-PROTOCOL-EXTENSION ::= {
--	...
--}

-- **************************************************************
--
-- PHYSICAL CHANNEL RECONFIGURATION FAILURE
--
-- **************************************************************

--PhysicalChannelReconfigurationFailure ::= SEQUENCE {
--	protocolIEs                     ProtocolIE-Container       {{PhysicalChannelReconfigurationFailure-IEs}},
--	protocolExtensions              ProtocolExtensionContainer {{PhysicalChannelReconfigurationFailure-Extensions}}                   OPTIONAL,
--	...
--}
PhysicalChannelReconfigurationFailure ::= SEQUENCE {
	protocolIEs                     ProtocolIE-Container,
	protocolExtensions              ProtocolExtensionContainer OPTIONAL,
	...
}

--PhysicalChannelReconfigurationFailure-IEs RNSAP-PROTOCOL-IES ::= {
--	{ ID id-Cause					CRITICALITY ignore	TYPE Cause					PRESENCE mandatory	} |
--	{ ID id-CriticalityDiagnostics			CRITICALITY ignore	TYPE CriticalityDiagnostics			PRESENCE optional	},
--	...
--}

--PhysicalChannelReconfigurationFailure-Extensions RNSAP-PROTOCOL-EXTENSION ::= {
--	...
--}

-- **************************************************************
--
-- RADIO LINK CONGESTION INDICATION
--
-- **************************************************************

--RadioLinkCongestionIndication ::= SEQUENCE {
--	protocolIEs                     ProtocolIE-Container       {{RadioLinkCongestionIndication-IEs}},
--	protocolExtensions              ProtocolExtensionContainer {{RadioLinkCongestionIndication-Extensions}}                   OPTIONAL,
--	...
--}
RadioLinkCongestionIndication ::= SEQUENCE {
	protocolIEs                     ProtocolIE-Container,
	protocolExtensions              ProtocolExtensionContainer OPTIONAL,
	...
}

--RadioLinkCongestionIndication-IEs RNSAP-PROTOCOL-IES ::= {
--	{ ID id-CongestionCause						CRITICALITY ignore  TYPE CongestionCause						   PRESENCE optional }|
--	{ ID id-RL-InformationList-RL-CongestInd	CRITICALITY ignore	TYPE RL-InformationList-RL-CongestInd		PRESENCE mandatory },
--	...
--}

--RL-InformationList-RL-CongestInd			::= SEQUENCE (SIZE (1..maxNrOfRLs)) OF ProtocolIE-Single-Container { {RL-InformationItemIEs-RL-CongestInd} }
RL-InformationList-RL-CongestInd			::= SEQUENCE (SIZE (1..16)) OF ProtocolIE-Single-Container

--RL-InformationItemIEs-RL-CongestInd RNSAP-PROTOCOL-IES ::= {
--	{ ID id-RL-InformationItem-RL-CongestInd		CRITICALITY ignore	TYPE RL-InformationItem-RL-CongestInd		PRESENCE mandatory	}
--}

RL-InformationItem-RL-CongestInd ::= SEQUENCE {
	rL-ID								RL-ID,
	dCH-Rate-Information		DCH-Rate-Information-RL-CongestInd,
--	iE-Extensions				ProtocolExtensionContainer { {RL-Information-RL-CongestInd-ExtIEs} } OPTIONAL,
	iE-Extensions				ProtocolExtensionContainer OPTIONAL,
	...
}

--DCH-Rate-Information-RL-CongestInd ::= SEQUENCE (SIZE (1..maxNrOfDCHs)) OF ProtocolIE-Single-Container { {DCH-Rate-InformationItemIEs-RL-CongestInd} }
DCH-Rate-Information-RL-CongestInd ::= SEQUENCE (SIZE (1..128)) OF ProtocolIE-Single-Container

--DCH-Rate-InformationItemIEs-RL-CongestInd RNSAP-PROTOCOL-IES ::= {
--	{ ID id-DCH-Rate-InformationItem-RL-CongestInd		CRITICALITY ignore	TYPE DCH-Rate-InformationItem-RL-CongestInd		PRESENCE mandatory	}
--}

DCH-Rate-InformationItem-RL-CongestInd ::= SEQUENCE {
	dCH-ID						DCH-ID,
	allowed-Rate-Information	Allowed-Rate-Information OPTIONAL,
--	iE-Extensions				ProtocolExtensionContainer { {DCH-Rate-InformationItem-RL-CongestInd-ExtIEs} } OPTIONAL,
	iE-Extensions				ProtocolExtensionContainer OPTIONAL,
	...
}

--DCH-Rate-InformationItem-RL-CongestInd-ExtIEs RNSAP-PROTOCOL-EXTENSION ::= {
--	...
--}

--RL-Information-RL-CongestInd-ExtIEs RNSAP-PROTOCOL-EXTENSION ::= {
--	{ ID id-EDCH-MacdFlowSpecificInformationList-RL-CongestInd  CRITICALITY ignore	EXTENSION EDCH-MacdFlowSpecificInformationList-RL-CongestInd PRESENCE optional },
--	...
--}

--RadioLinkCongestionIndication-Extensions RNSAP-PROTOCOL-EXTENSION ::= {
--	...
--}

--EDCH-MacdFlowSpecificInformationList-RL-CongestInd	::= SEQUENCE (SIZE (1.. maxNrOfEDCHMACdFlows)) OF ProtocolIE-Single-Container { {EDCH-MacdFlowSpecificInformationItemIEs-RL-CongestInd} }
EDCH-MacdFlowSpecificInformationList-RL-CongestInd	::= SEQUENCE (SIZE (1.. 8)) OF ProtocolIE-Single-Container

--EDCH-MacdFlowSpecificInformationItemIEs-RL-CongestInd RNSAP-PROTOCOL-IES ::= {
--	{ ID id-EDCH-MacdFlowSpecificInformationItem-RL-CongestInd		CRITICALITY ignore	TYPE EDCH-MacdFlowSpecificInformationItem-RL-CongestInd	PRESENCE mandatory	}
--}

EDCH-MacdFlowSpecificInformationItem-RL-CongestInd ::= SEQUENCE {
	eDCH-MACdFlow-ID			EDCH-MACdFlow-ID,
--	iE-Extensions				ProtocolExtensionContainer { { EDCH-MacdFlowSpecificInformation-RL-CongestInd-ExtIEs} } OPTIONAL,
	iE-Extensions				ProtocolExtensionContainer OPTIONAL,
	...
}

--EDCH-MacdFlowSpecificInformation-RL-CongestInd-ExtIEs RNSAP-PROTOCOL-EXTENSION ::= {
--	...
--}

-- **************************************************************
--
-- UPLINK SIGNALLING TRANSFER INDICATION FDD
--
-- **************************************************************

--UplinkSignallingTransferIndicationFDD ::= SEQUENCE {
--	protocolIEs                     ProtocolIE-Container       {{UplinkSignallingTransferIndicationFDD-IEs}},
--	protocolExtensions              ProtocolExtensionContainer {{UplinkSignallingTransferIndicationFDD-Extensions}}                   OPTIONAL,
--	...
--}
UplinkSignallingTransferIndicationFDD ::= SEQUENCE {
	protocolIEs                     ProtocolIE-Container,
	protocolExtensions              ProtocolExtensionContainer OPTIONAL,
	...
}
--UplinkSignallingTransferIndicationFDD-IEs RNSAP-PROTOCOL-IES ::= {
--	{ ID id-UC-ID					CRITICALITY ignore	TYPE UC-ID					PRESENCE mandatory	} |
--	{ ID id-SAI					CRITICALITY ignore	TYPE SAI					PRESENCE mandatory	} |
--	{ ID id-GA-Cell				CRITICALITY ignore	TYPE GA-Cell				PRESENCE optional	} |
--	{ ID id-C-RNTI					CRITICALITY ignore	TYPE C-RNTI					PRESENCE mandatory	} |
--	{ ID id-S-RNTI					CRITICALITY ignore	TYPE S-RNTI					PRESENCE mandatory	} |
--	{ ID id-D-RNTI					CRITICALITY ignore	TYPE D-RNTI					PRESENCE optional	} |
--	{ ID id-PropagationDelay		CRITICALITY ignore	TYPE PropagationDelay		PRESENCE mandatory	} |
--	{ ID id-STTD-SupportIndicator				CRITICALITY ignore 	TYPE STTD-SupportIndicator	PRESENCE mandatory } |
--	{ ID id-ClosedLoopMode1-SupportIndicator	CRITICALITY ignore 	TYPE ClosedLoopMode1-SupportIndicator	PRESENCE mandatory } |
--	{ ID id-L3-Information				CRITICALITY ignore	TYPE L3-Information				PRESENCE mandatory	} |
--	{ ID id-CN-PS-DomainIdentifier			CRITICALITY ignore	TYPE CN-PS-DomainIdentifier			PRESENCE optional	} |
--	{ ID id-CN-CS-DomainIdentifier			CRITICALITY ignore	TYPE CN-CS-DomainIdentifier			PRESENCE optional	} |
--	{ ID id-URA-Information					CRITICALITY ignore	TYPE URA-Information					PRESENCE optional	},
--	...
--}

--UplinkSignallingTransferIndicationFDD-Extensions RNSAP-PROTOCOL-EXTENSION ::= {
--	{ ID id-GA-CellAdditionalShapes				CRITICALITY ignore	EXTENSION GA-CellAdditionalShapes				PRESENCE optional }|
--	{ ID id-DPC-Mode-Change-SupportIndicator	CRITICALITY ignore	EXTENSION DPC-Mode-Change-SupportIndicator	PRESENCE optional }|
--	{ ID id-CommonTransportChannelResourcesInitialisationNotRequired	CRITICALITY ignore	EXTENSION CommonTransportChannelResourcesInitialisationNotRequired	PRESENCE optional }|
--	{ ID id-CellCapabilityContainer-FDD			CRITICALITY ignore	EXTENSION CellCapabilityContainer-FDD			PRESENCE optional }|
--	{ ID id-SNA-Information						CRITICALITY ignore	EXTENSION SNA-Information							PRESENCE optional }|
--	{ ID id-CellPortionID						CRITICALITY ignore	EXTENSION CellPortionID 							PRESENCE optional }|
--	{ ID id-Active-MBMS-Bearer-ServiceFDD		CRITICALITY	ignore	EXTENSION Active-MBMS-Bearer-Service-ListFDD			PRESENCE optional},
--	...
--}

-- **************************************************************
--
-- UPLINK SIGNALLING TRANSFER INDICATION TDD
--
-- **************************************************************

--UplinkSignallingTransferIndicationTDD ::= SEQUENCE {
--	protocolIEs                     ProtocolIE-Container       {{UplinkSignallingTransferIndicationTDD-IEs}},
--	protocolExtensions              ProtocolExtensionContainer {{UplinkSignallingTransferIndicationTDD-Extensions}}                   OPTIONAL,
--	...
--}
UplinkSignallingTransferIndicationTDD ::= SEQUENCE {
	protocolIEs                     ProtocolIE-Container,
	protocolExtensions              ProtocolExtensionContainer OPTIONAL,
	...
}

--UplinkSignallingTransferIndicationTDD-IEs RNSAP-PROTOCOL-IES ::= {
--	{ ID id-UC-ID					CRITICALITY ignore	TYPE UC-ID					PRESENCE mandatory	} |
--	{ ID id-SAI					CRITICALITY ignore	TYPE SAI					PRESENCE mandatory	} |
--	{ ID id-GA-Cell				CRITICALITY ignore	TYPE GA-Cell				PRESENCE optional	} |
--	{ ID id-C-RNTI					CRITICALITY ignore	TYPE C-RNTI					PRESENCE mandatory	} |
--	{ ID id-S-RNTI					CRITICALITY ignore	TYPE S-RNTI					PRESENCE mandatory	} |
--	{ ID id-D-RNTI					CRITICALITY ignore	TYPE D-RNTI					PRESENCE optional	} |
--	{ ID id-RxTimingDeviationForTA			CRITICALITY ignore 	TYPE RxTimingDeviationForTA	PRESENCE mandatory } |
--	{ ID id-L3-Information				CRITICALITY ignore	TYPE L3-Information				PRESENCE mandatory	} |
--	{ ID id-CN-PS-DomainIdentifier			CRITICALITY ignore	TYPE CN-PS-DomainIdentifier			PRESENCE optional	} |
--	{ ID id-CN-CS-DomainIdentifier			CRITICALITY ignore	TYPE CN-CS-DomainIdentifier			PRESENCE optional	} |
--	{ ID id-URA-Information					CRITICALITY ignore	TYPE URA-Information					PRESENCE optional	},
--	...
--}

--UplinkSignallingTransferIndicationTDD-Extensions RNSAP-PROTOCOL-EXTENSION ::= {
--	{ ID id-GA-CellAdditionalShapes			CRITICALITY	ignore	EXTENSION	GA-CellAdditionalShapes		PRESENCE optional	}|
--	{ ID id-CommonTransportChannelResourcesInitialisationNotRequired	CRITICALITY ignore	EXTENSION CommonTransportChannelResourcesInitialisationNotRequired		PRESENCE optional	}|
--	{ ID id-CellCapabilityContainer-TDD		CRITICALITY	ignore	EXTENSION	CellCapabilityContainer-TDD		PRESENCE optional }|
		-- Applicable to 3.84Mcps TDD only
--	{ ID id-CellCapabilityContainer-TDD-LCR	CRITICALITY	ignore	EXTENSION	CellCapabilityContainer-TDD-LCR		PRESENCE optional }|
		-- Applicable to 1.28Mcps TDD only
--	{ ID id-SNA-Information					CRITICALITY ignore	EXTENSION	SNA-Information						PRESENCE optional }|
--	{ ID id-Active-MBMS-Bearer-ServiceTDD		CRITICALITY	ignore	EXTENSION Active-MBMS-Bearer-Service-ListTDD			PRESENCE optional},
--	...

--}

-- **************************************************************
--
-- DOWNLINK SIGNALLING TRANSFER REQUEST
--
-- **************************************************************

--DownlinkSignallingTransferRequest ::= SEQUENCE {
--	protocolIEs                     ProtocolIE-Container       {{DownlinkSignallingTransferRequest-IEs}},
--	protocolExtensions              ProtocolExtensionContainer {{DownlinkSignallingTransferRequest-Extensions}}                   OPTIONAL,
--	...
--}
DownlinkSignallingTransferRequest ::= SEQUENCE {
	protocolIEs                     ProtocolIE-Container,
	protocolExtensions              ProtocolExtensionContainer OPTIONAL,
	...
}
--DownlinkSignallingTransferRequest-IEs RNSAP-PROTOCOL-IES ::= {
--	{ ID id-C-ID					CRITICALITY ignore	TYPE C-ID					PRESENCE mandatory	} |
	-- May be a GERAN cell identifier
--	{ ID id-D-RNTI					CRITICALITY ignore	TYPE D-RNTI					PRESENCE mandatory	} |
--	{ ID id-L3-Information				CRITICALITY ignore	TYPE L3-Information				PRESENCE mandatory	} |
--	{ ID id-D-RNTI-ReleaseIndication		CRITICALITY ignore	TYPE D-RNTI-ReleaseIndication			PRESENCE mandatory	},
--	...
--}

--DownlinkSignallingTransferRequest-Extensions RNSAP-PROTOCOL-EXTENSION ::= {
--	{ ID id-URA-ID		CRITICALITY ignore		EXTENSION	URA-ID	PRESENCE optional}|
--	{ ID id-MBMS-Bearer-Service-List		CRITICALITY	ignore	EXTENSION MBMS-Bearer-Service-List			PRESENCE optional}|
--	{ ID id-Old-URA-ID		CRITICALITY	ignore		EXTENSION	URA-ID	PRESENCE optional}|
--	{ ID id-SRNC-ID		CRITICALITY  ignore		EXTENSION	RNC-ID	PRESENCE	conditional},
	-- This IE shall be present if the URA-ID IE or Old URA-ID IE is present.
--	...
--}

-- **************************************************************
--
-- RELOCATION COMMIT
--
-- **************************************************************

--RelocationCommit ::= SEQUENCE {
--	protocolIEs                     ProtocolIE-Container       {{RelocationCommit-IEs}},
--	protocolExtensions              ProtocolExtensionContainer {{RelocationCommit-Extensions}}                   OPTIONAL,
--	...
--}
RelocationCommit ::= SEQUENCE {
	protocolIEs                     ProtocolIE-Container,
	protocolExtensions              ProtocolExtensionContainer OPTIONAL,
	...
}
--RelocationCommit-IEs RNSAP-PROTOCOL-IES ::= {
--	{ ID id-D-RNTI					CRITICALITY ignore	TYPE D-RNTI					PRESENCE optional	} |
--	{ ID id-RANAP-RelocationInformation		CRITICALITY ignore	TYPE RANAP-RelocationInformation		PRESENCE optional	},
--	...
--}

--RelocationCommit-Extensions RNSAP-PROTOCOL-EXTENSION ::= {
--	...
--}

-- **************************************************************
--
-- PAGING REQUEST
--
-- **************************************************************

--PagingRequest ::= SEQUENCE {
--	protocolIEs                     ProtocolIE-Container       {{PagingRequest-IEs}},
--	protocolExtensions              ProtocolExtensionContainer {{PagingRequest-Extensions}}                   OPTIONAL,
--	...
--}
PagingRequest ::= SEQUENCE {
	protocolIEs                     ProtocolIE-Container,
	protocolExtensions              ProtocolExtensionContainer OPTIONAL,
	...
}
--PagingRequest-IEs RNSAP-PROTOCOL-IES ::= {
--	{ ID id-PagingArea-PagingRqst			CRITICALITY ignore	TYPE PagingArea-PagingRqst			PRESENCE mandatory	} |
--	{ ID id-SRNC-ID					CRITICALITY ignore	TYPE RNC-ID					PRESENCE mandatory	} |
 -- May be a BSC-Id.
--	{ ID id-S-RNTI					CRITICALITY ignore	TYPE S-RNTI					PRESENCE mandatory	} |
--	{ ID id-IMSI					CRITICALITY ignore	TYPE IMSI					PRESENCE mandatory	} |
--	{ ID id-DRXCycleLengthCoefficient				CRITICALITY ignore	TYPE DRXCycleLengthCoefficient				PRESENCE mandatory	}|
--	{ ID id-CNOriginatedPage-PagingRqst				CRITICALITY ignore  TYPE CNOriginatedPage-PagingRqst			PRESENCE optional		},
--	...
--}

PagingArea-PagingRqst ::= CHOICE {
	uRA						URA-PagingRqst, -- May be a GRA-ID.
	cell					Cell-PagingRqst, -- UTRAN only
	...
}

URA-PagingRqst ::= SEQUENCE {
	uRA-ID						URA-ID,
--	iE-Extensions				ProtocolExtensionContainer { { URAItem-PagingRqst-ExtIEs} } OPTIONAL,
	iE-Extensions				ProtocolExtensionContainer OPTIONAL,
	...
}

--URAItem-PagingRqst-ExtIEs RNSAP-PROTOCOL-EXTENSION ::= {
--	...
--}

Cell-PagingRqst ::= SEQUENCE {
	c-ID						C-ID,
--	iE-Extensions				ProtocolExtensionContainer { { CellItem-PagingRqst-ExtIEs} } OPTIONAL,
	iE-Extensions				ProtocolExtensionContainer OPTIONAL,
	...
}

--CellItem-PagingRqst-ExtIEs RNSAP-PROTOCOL-EXTENSION ::= {
--	...
--}

CNOriginatedPage-PagingRqst::= SEQUENCE {
	pagingCause					PagingCause,
	cNDomainType				CNDomainType,
	pagingRecordType			PagingRecordType,
--	iE-Extensions				ProtocolExtensionContainer { { CNOriginatedPage-PagingRqst-ExtIEs} } OPTIONAL,
	iE-Extensions				ProtocolExtensionContainer OPTIONAL,
	...
}

--CNOriginatedPage-PagingRqst-ExtIEs RNSAP-PROTOCOL-EXTENSION ::= {
--	...
--}

--PagingRequest-Extensions RNSAP-PROTOCOL-EXTENSION ::= {
--	...
--}
-- **************************************************************
--
-- DEDICATED MEASUREMENT INITIATION REQUEST
--
-- **************************************************************

--DedicatedMeasurementInitiationRequest ::= SEQUENCE {
--	protocolIEs                     ProtocolIE-Container       {{DedicatedMeasurementInitiationRequest-IEs}},
--	protocolExtensions              ProtocolExtensionContainer {{DedicatedMeasurementInitiationRequest-Extensions}}                   OPTIONAL,
--	...
--}
DedicatedMeasurementInitiationRequest ::= SEQUENCE {
	protocolIEs                     ProtocolIE-Container,
	protocolExtensions              ProtocolExtensionContainer OPTIONAL,
	...
}
--DedicatedMeasurementInitiationRequest-IEs RNSAP-PROTOCOL-IES ::= {
--	{ ID id-MeasurementID				CRITICALITY reject	TYPE MeasurementID				PRESENCE mandatory	} |
--	{ ID id-DedicatedMeasurementObjectType-DM-Rqst	CRITICALITY reject	TYPE DedicatedMeasurementObjectType-DM-Rqst	PRESENCE mandatory	} |

--	{ ID id-DedicatedMeasurementType			CRITICALITY reject	TYPE DedicatedMeasurementType			PRESENCE mandatory	} |
--	{ ID id-MeasurementFilterCoefficient		CRITICALITY reject	TYPE MeasurementFilterCoefficient			PRESENCE optional	} |
--	{ ID id-ReportCharacteristics			CRITICALITY reject	TYPE ReportCharacteristics			PRESENCE mandatory	}|
--  { ID id-CFNReportingIndicator           CRITICALITY reject  TYPE FNReportingIndicator         PRESENCE mandatory  }|
--    { ID id-CFN                             CRITICALITY reject  TYPE CFN                          PRESENCE optional   },
--	...
--}

DedicatedMeasurementObjectType-DM-Rqst ::= CHOICE {
	rL						RL-DM-Rqst,
	rLS						RL-Set-DM-Rqst,
	allRL					All-RL-DM-Rqst,
	allRLS					All-RL-Set-DM-Rqst,
	...
}

RL-DM-Rqst ::= SEQUENCE {
	rL-InformationList-DM-Rqst		RL-InformationList-DM-Rqst,
--	iE-Extensions					ProtocolExtensionContainer { { RLItem-DM-Rqst-ExtIEs} } OPTIONAL,
	iE-Extensions					ProtocolExtensionContainer OPTIONAL,
	...
	}

--RLItem-DM-Rqst-ExtIEs RNSAP-PROTOCOL-EXTENSION ::= {
--	...
--}

--RL-InformationList-DM-Rqst					::= SEQUENCE (SIZE (1..maxNrOfRLs)) OF ProtocolIE-Single-Container { {RL-Information-DM-Rqst-IEs} }
RL-InformationList-DM-Rqst					::= SEQUENCE (SIZE (1..16)) OF ProtocolIE-Single-Container

--RL-Information-DM-Rqst-IEs RNSAP-PROTOCOL-IES ::= {
--	{ ID id-RL-InformationItem-DM-Rqst		CRITICALITY reject	TYPE RL-InformationItem-DM-Rqst			PRESENCE mandatory	}
--}

RL-InformationItem-DM-Rqst ::= SEQUENCE {
	rL-ID						RL-ID,
	dPCH-ID						DPCH-ID		OPTIONAL,
--	iE-Extensions					ProtocolExtensionContainer { {RL-InformationItem-DM-Rqst-ExtIEs} } OPTIONAL,
	iE-Extensions					ProtocolExtensionContainer OPTIONAL,
	...
}

--RL-InformationItem-DM-Rqst-ExtIEs RNSAP-PROTOCOL-EXTENSION ::= {
--	{ ID id-HSSICH-Info-DM-Rqst		CRITICALITY reject				EXTENSION	HSSICH-Info-DM-Rqst		PRESENCE optional},
	-- TDD only
--	...
--}

--HSSICH-Info-DM-Rqst ::= SEQUENCE (SIZE (1..maxNrOfHSSICHs)) OF HS-SICH-ID
HSSICH-Info-DM-Rqst ::= SEQUENCE (SIZE (1..4)) OF HS-SICH-ID

RL-Set-DM-Rqst ::= SEQUENCE {
	rL-Set-InformationList-DM-Rqst	RL-Set-InformationList-DM-Rqst,
--	iE-Extensions					ProtocolExtensionContainer { { RL-SetItem-DM-Rqst-ExtIEs} } OPTIONAL,
	iE-Extensions					ProtocolExtensionContainer OPTIONAL,
	...
	}

--RL-SetItem-DM-Rqst-ExtIEs RNSAP-PROTOCOL-EXTENSION ::= {
--	...
--}

--RL-Set-InformationList-DM-Rqst					::= SEQUENCE (SIZE (1..maxNrOfRLSets)) OF ProtocolIE-Single-Container { {RL-Set-Information-DM-Rqst-IEs} }
RL-Set-InformationList-DM-Rqst					::= SEQUENCE (SIZE (1..16)) OF ProtocolIE-Single-Container

--RL-Set-Information-DM-Rqst-IEs RNSAP-PROTOCOL-IES ::= {
--	{ ID id-RL-Set-InformationItem-DM-Rqst		CRITICALITY reject	TYPE RL-Set-InformationItem-DM-Rqst			PRESENCE mandatory	}
--}

RL-Set-InformationItem-DM-Rqst ::= SEQUENCE {
	rL-Set-ID						RL-Set-ID,
--	iE-Extensions					ProtocolExtensionContainer { {RL-Set-InformationItem-DM-Rqst-ExtIEs} } OPTIONAL,
	iE-Extensions					ProtocolExtensionContainer OPTIONAL,
	...
}

--RL-Set-InformationItem-DM-Rqst-ExtIEs RNSAP-PROTOCOL-EXTENSION ::= {
--	...
--}

All-RL-DM-Rqst ::= NULL

All-RL-Set-DM-Rqst ::= NULL

--DedicatedMeasurementInitiationRequest-Extensions RNSAP-PROTOCOL-EXTENSION ::= {
--	{ ID id-PartialReportingIndicator		CRITICALITY ignore			EXTENSION	PartialReportingIndicator								PRESENCE optional	}|
--	{ ID	id-MeasurementRecoveryBehavior				CRITICALITY ignore				EXTENSION	MeasurementRecoveryBehavior		PRESENCE optional
--	},
--	...
--}

-- **************************************************************
--
-- DEDICATED MEASUREMENT INITIATION RESPONSE
--
-- **************************************************************

--DedicatedMeasurementInitiationResponse ::= SEQUENCE {
--	protocolIEs                     ProtocolIE-Container       {{DedicatedMeasurementInitiationResponse-IEs}},
--	protocolExtensions              ProtocolExtensionContainer {{DedicatedMeasurementInitiationResponse-Extensions}}                   OPTIONAL,
--	...
--}
DedicatedMeasurementInitiationResponse ::= SEQUENCE {
	protocolIEs                     ProtocolIE-Container,
	protocolExtensions              ProtocolExtensionContainer OPTIONAL,
	...
}

--DedicatedMeasurementInitiationResponse-IEs RNSAP-PROTOCOL-IES ::= {
--	{ ID id-MeasurementID				CRITICALITY ignore	TYPE MeasurementID				PRESENCE mandatory	} |
--	{ ID id-DedicatedMeasurementObjectType-DM-Rsp	CRITICALITY ignore	TYPE DedicatedMeasurementObjectType-DM-Rsp	PRESENCE optional	} |
--	{ ID id-CriticalityDiagnostics			CRITICALITY ignore	TYPE CriticalityDiagnostics			PRESENCE optional	},
--	...
--}

DedicatedMeasurementObjectType-DM-Rsp ::= CHOICE {
	rLs						RL-DM-Rsp,
	rLS						RL-Set-DM-Rsp,
	allRL					RL-DM-Rsp,
	allRLS					RL-Set-DM-Rsp,
	...
}

RL-DM-Rsp ::= SEQUENCE {
	rL-InformationList-DM-Rsp		RL-InformationList-DM-Rsp,
--	iE-Extensions					ProtocolExtensionContainer { { RLItem-DM-Rsp-ExtIEs} } OPTIONAL,
	iE-Extensions					ProtocolExtensionContainer OPTIONAL,
	...
}

--RLItem-DM-Rsp-ExtIEs RNSAP-PROTOCOL-EXTENSION ::= {
--	...
--}

RL-Set-DM-Rsp ::= SEQUENCE {
	rL-Set-InformationList-DM-Rsp	RL-Set-InformationList-DM-Rsp,
--	iE-Extensions					ProtocolExtensionContainer { { RL-SetItem-DM-Rsp-ExtIEs} } OPTIONAL,
	iE-Extensions					ProtocolExtensionContainer OPTIONAL,
	...
}

--RL-SetItem-DM-Rsp-ExtIEs RNSAP-PROTOCOL-EXTENSION ::= {
--	...
--}

--RL-InformationList-DM-Rsp					::= SEQUENCE (SIZE (1..maxNrOfRLs)) OF ProtocolIE-Single-Container { {RL-Information-DM-Rsp-IEs} }
RL-InformationList-DM-Rsp					::= SEQUENCE (SIZE (1..16)) OF ProtocolIE-Single-Container

--RL-Information-DM-Rsp-IEs RNSAP-PROTOCOL-IES ::= {
--	{ ID id-RL-InformationItem-DM-Rsp		CRITICALITY ignore	TYPE RL-InformationItem-DM-Rsp		PRESENCE mandatory	}
--}

RL-InformationItem-DM-Rsp ::= SEQUENCE {
	rL-ID						RL-ID,
	dPCH-ID						DPCH-ID				OPTIONAL,
	dedicatedMeasurementValue			DedicatedMeasurementValue,
    cFN                         CFN                 OPTIONAL,
--	iE-Extensions					ProtocolExtensionContainer { {RL-InformationItem-DM-Rsp-ExtIEs} } OPTIONAL,
	iE-Extensions					ProtocolExtensionContainer OPTIONAL,
	...
}

--RL-InformationItem-DM-Rsp-ExtIEs RNSAP-PROTOCOL-EXTENSION ::= {
--	{ID id-HSSICH-Info-DM		CRITICALITY reject				EXTENSION	HS-SICH-ID		PRESENCE optional}|
	-- TDD only
--	{ ID	id-multiple-DedicatedMeasurementValueList-TDD-DM-Rsp	CRITICALITY ignore	EXTENSION Multiple-DedicatedMeasurementValueList-TDD-DM-Rsp	PRESENCE optional	}|    
	-- Applicable to 3.84Mcps TDD only. This list of dedicated measurement values is used for the 2nd and beyond measurements of a RL when multiple dedicated measurement values need to be reported. 
--	{ ID	id-multiple-DedicatedMeasurementValueList-LCR-TDD-DM-Rsp	CRITICALITY ignore	EXTENSION Multiple-DedicatedMeasurementValueList-LCR-TDD-DM-Rsp	PRESENCE optional	},    
	-- Applicable to 1.28Mcps TDD only. This list of dedicated measurement values is used for the 2nd and beyond measurements of a RL when multiple dedicated measurement values need to be reported.
--	...
--}

--RL-Set-InformationList-DM-Rsp	::= SEQUENCE (SIZE (1..maxNrOfRLSets)) OF ProtocolIE-Single-Container { {RL-Set-Information-DM-Rsp-IEs} }
RL-Set-InformationList-DM-Rsp	::= SEQUENCE (SIZE (1..16)) OF ProtocolIE-Single-Container

--RL-Set-Information-DM-Rsp-IEs RNSAP-PROTOCOL-IES ::= {
--	{ ID id-RL-Set-InformationItem-DM-Rsp		CRITICALITY ignore	TYPE RL-Set-InformationItem-DM-Rsp		PRESENCE mandatory	}
--}

RL-Set-InformationItem-DM-Rsp ::= SEQUENCE {
	rL-Set-ID						RL-Set-ID,
	dedicatedMeasurementValue		DedicatedMeasurementValue,
    cFN                         	CFN         		        OPTIONAL,
--	iE-Extensions					ProtocolExtensionContainer { {RL-Set-InformationItem-DM-Rspns-ExtIEs} } OPTIONAL,
	iE-Extensions					ProtocolExtensionContainer OPTIONAL,
	...
}

--RL-Set-InformationItem-DM-Rspns-ExtIEs RNSAP-PROTOCOL-EXTENSION ::= {
--	...
--}

--DedicatedMeasurementInitiationResponse-Extensions RNSAP-PROTOCOL-EXTENSION ::= {
--	{ ID	id-MeasurementRecoverySupportIndicator		CRITICALITY ignore		EXTENSION	MeasurementRecoverySupportIndicator		PRESENCE optional
--	},
--	...
--}

--Multiple-DedicatedMeasurementValueList-TDD-DM-Rsp ::= SEQUENCE (SIZE (1.. maxNrOfDPCHsPerRL-1)) OF Multiple-DedicatedMeasurementValueItem-TDD-DM-Rsp
Multiple-DedicatedMeasurementValueList-TDD-DM-Rsp ::= SEQUENCE (SIZE (1.. 239)) OF Multiple-DedicatedMeasurementValueItem-TDD-DM-Rsp

Multiple-DedicatedMeasurementValueItem-TDD-DM-Rsp ::= SEQUENCE {
	dPCH-ID								DPCH-ID, 
	dedicatedMeasurementValue			DedicatedMeasurementValue,
--	iE-Extensions						ProtocolExtensionContainer { { Multiple-DedicatedMeasurementValueItem-TDD-DM-Rsp-ExtIEs} }		OPTIONAL,
	iE-Extensions						ProtocolExtensionContainer OPTIONAL,
	...

}

--Multiple-DedicatedMeasurementValueItem-TDD-DM-Rsp-ExtIEs RNSAP-PROTOCOL-EXTENSION ::= {
--	...
--}

--Multiple-DedicatedMeasurementValueList-LCR-TDD-DM-Rsp ::= SEQUENCE (SIZE (1.. maxNrOfDPCHsLCRPerRL-1)) OF Multiple-DedicatedMeasurementValueItem-LCR-TDD-DM-Rsp
Multiple-DedicatedMeasurementValueList-LCR-TDD-DM-Rsp ::= SEQUENCE (SIZE (1.. 239)) OF Multiple-DedicatedMeasurementValueItem-LCR-TDD-DM-Rsp

Multiple-DedicatedMeasurementValueItem-LCR-TDD-DM-Rsp ::= SEQUENCE {
	dPCH-ID								DPCH-ID, 
	dedicatedMeasurementValue			DedicatedMeasurementValue,
--	iE-Extensions						ProtocolExtensionContainer { { Multiple-DedicatedMeasurementValueItem-LCR-TDD-DM-Rsp-ExtIEs} }		OPTIONAL,
	iE-Extensions						ProtocolExtensionContainer OPTIONAL,
	...
}

--Multiple-DedicatedMeasurementValueItem-LCR-TDD-DM-Rsp-ExtIEs RNSAP-PROTOCOL-EXTENSION ::= {
--	...
--}

-- **************************************************************
--
-- DEDICATED MEASUREMENT INITIATION FAILURE
--
-- **************************************************************

--DedicatedMeasurementInitiationFailure ::= SEQUENCE {
--	protocolIEs                     ProtocolIE-Container       {{DedicatedMeasurementInitiationFailure-IEs}},
--	protocolExtensions              ProtocolExtensionContainer {{DedicatedMeasurementInitiationFailure-Extensions}}                   OPTIONAL,
--	...
--}
DedicatedMeasurementInitiationFailure ::= SEQUENCE {
	protocolIEs                     ProtocolIE-Container,
	protocolExtensions              ProtocolExtensionContainer OPTIONAL,
	...
}

--DedicatedMeasurementInitiationFailure-IEs RNSAP-PROTOCOL-IES ::= {
--	{ ID id-MeasurementID				CRITICALITY ignore	TYPE MeasurementID				PRESENCE mandatory	} |
--	{ ID id-Cause					CRITICALITY ignore	TYPE Cause					PRESENCE mandatory	} |
--	{ ID id-CriticalityDiagnostics			CRITICALITY ignore	TYPE CriticalityDiagnostics			PRESENCE optional	},
--	...
--}

--DedicatedMeasurementInitiationFailure-Extensions RNSAP-PROTOCOL-EXTENSION ::= {
--	{ ID id-DedicatedMeasurementObjectType-DM-Fail	CRITICALITY ignore	EXTENSION DedicatedMeasurementObjectType-DM-Fail	PRESENCE optional	},
--	...
--}

DedicatedMeasurementObjectType-DM-Fail ::= CHOICE {
	rL						RL-DM-Fail,
	rLS						RL-Set-DM-Fail,
	allRL					RL-DM-Fail,
	allRLS					RL-Set-DM-Fail,
	...
}

RL-DM-Fail ::= SEQUENCE {
	rL-unsuccessful-InformationRespList-DM-Fail		RL-Unsuccessful-InformationRespList-DM-Fail,
	rL-successful-InformationRespList-DM-Fail		RL-Successful-InformationRespList-DM-Fail			OPTIONAL,
--	iE-Extensions					ProtocolExtensionContainer { { RLItem-DM-Fail-ExtIEs} } OPTIONAL,
	iE-Extensions					ProtocolExtensionContainer OPTIONAL,
	...
}

--RLItem-DM-Fail-ExtIEs RNSAP-PROTOCOL-EXTENSION ::= {
--	...
--}

RL-Set-DM-Fail ::= SEQUENCE {
	rL-Set-unsuccessful-InformationRespList-DM-Fail	RL-Set-Unsuccessful-InformationRespList-DM-Fail,
	rL-Set-successful-InformationRespList-DM-Fail	RL-Set-Successful-InformationRespList-DM-Fail			OPTIONAL,
--	iE-Extensions					ProtocolExtensionContainer { { RL-SetItem-DM-Fail-ExtIEs} } OPTIONAL,
	iE-Extensions					ProtocolExtensionContainer OPTIONAL,
	...
}

--RL-SetItem-DM-Fail-ExtIEs RNSAP-PROTOCOL-EXTENSION ::= {
--	...
--}

--RL-Unsuccessful-InformationRespList-DM-Fail			::= SEQUENCE (SIZE (1..maxNrOfRLs)) OF ProtocolIE-Single-Container { {RL-Unsuccessful-InformationResp-DM-Fail-IEs} }
RL-Unsuccessful-InformationRespList-DM-Fail			::= SEQUENCE (SIZE (1..16)) OF ProtocolIE-Single-Container

--RL-Unsuccessful-InformationResp-DM-Fail-IEs RNSAP-PROTOCOL-IES ::= {
--	{ ID id-RL-Unsuccessful-InformationItem-DM-Fail		CRITICALITY ignore	TYPE RL-Unsuccessful-InformationItem-DM-Fail		PRESENCE mandatory	}
--}

RL-Unsuccessful-InformationItem-DM-Fail ::= SEQUENCE {
	rL-ID						RL-ID,
	individualcause				Cause	OPTIONAL,
--	iE-Extensions				ProtocolExtensionContainer { {RL-Unsuccessful-InformationItem-DM-Fail-ExtIEs} } OPTIONAL,
	iE-Extensions				ProtocolExtensionContainer OPTIONAL,
	...
}

--RL-Unsuccessful-InformationItem-DM-Fail-ExtIEs RNSAP-PROTOCOL-EXTENSION ::= {
--	...
--}

--RL-Successful-InformationRespList-DM-Fail			::= SEQUENCE (SIZE (1..maxNrOfRLs-1)) OF ProtocolIE-Single-Container { {RL-Successful-InformationResp-DM-Fail-IEs} }
RL-Successful-InformationRespList-DM-Fail			::= SEQUENCE (SIZE (1..15)) OF ProtocolIE-Single-Container

--RL-Successful-InformationResp-DM-Fail-IEs RNSAP-PROTOCOL-IES ::= {
--	{ ID id-RL-Successful-InformationItem-DM-Fail		CRITICALITY ignore	TYPE RL-Successful-InformationItem-DM-Fail		PRESENCE mandatory	}
--}

RL-Successful-InformationItem-DM-Fail ::= SEQUENCE {
	rL-ID						RL-ID,
	dPCH-ID						DPCH-ID				OPTIONAL,
	dedicatedMeasurementValue	DedicatedMeasurementValue,
    cFN                         CFN                 OPTIONAL,
--	iE-Extensions				ProtocolExtensionContainer { {RL-Successful-InformationItem-DM-Fail-ExtIEs} } OPTIONAL,
	iE-Extensions				ProtocolExtensionContainer OPTIONAL,
	...
}

--RL-Successful-InformationItem-DM-Fail-ExtIEs RNSAP-PROTOCOL-EXTENSION ::= {
--	{ID id-HSSICH-Info-DM		CRITICALITY reject				EXTENSION	HS-SICH-ID		PRESENCE optional},
	-- TDD only
--	...
--}

--RL-Set-Unsuccessful-InformationRespList-DM-Fail				::= SEQUENCE (SIZE (1..maxNrOfRLSets)) OF ProtocolIE-Single-Container { {RL-Set-Unsuccessful-InformationResp-DM-Fail-IEs} }
RL-Set-Unsuccessful-InformationRespList-DM-Fail				::= SEQUENCE (SIZE (1..16)) OF ProtocolIE-Single-Container

--RL-Set-Unsuccessful-InformationResp-DM-Fail-IEs RNSAP-PROTOCOL-IES ::= {
--	{ ID id-RL-Set-Unsuccessful-InformationItem-DM-Fail		CRITICALITY ignore	TYPE RL-Set-Unsuccessful-InformationItem-DM-Fail		PRESENCE mandatory	}
--}

RL-Set-Unsuccessful-InformationItem-DM-Fail ::= SEQUENCE {
	rL-Set-ID						RL-Set-ID,
	individualcause					Cause		OPTIONAL,
--	iE-Extensions					ProtocolExtensionContainer { {RL-Set-Unsuccessful-InformationItem-DM-Failns-ExtIEs} } OPTIONAL,
	iE-Extensions					ProtocolExtensionContainer OPTIONAL,
	...
}

--RL-Set-Unsuccessful-InformationItem-DM-Failns-ExtIEs RNSAP-PROTOCOL-EXTENSION ::= {
--	...
--}

--RL-Set-Successful-InformationRespList-DM-Fail				::= SEQUENCE (SIZE (1..maxNrOfRLSets-1)) OF ProtocolIE-Single-Container { {RL-Set-Successful-InformationResp-DM-Fail-IEs} }
RL-Set-Successful-InformationRespList-DM-Fail				::= SEQUENCE (SIZE (1..15)) OF ProtocolIE-Single-Container

--RL-Set-Successful-InformationResp-DM-Fail-IEs RNSAP-PROTOCOL-IES ::= {
--	{ ID id-RL-Set-Successful-InformationItem-DM-Fail		CRITICALITY ignore	TYPE RL-Set-Successful-InformationItem-DM-Fail		PRESENCE mandatory	}
--}

RL-Set-Successful-InformationItem-DM-Fail ::= SEQUENCE {
	rL-Set-ID						RL-Set-ID,
	dedicatedMeasurementValue		DedicatedMeasurementValue,
    cFN                         	CFN         		        OPTIONAL,
--	iE-Extensions					ProtocolExtensionContainer { {RL-Set-Successful-InformationItem-DM-Failns-ExtIEs} } OPTIONAL,
	iE-Extensions					ProtocolExtensionContainer OPTIONAL,
	...
}

--RL-Set-Successful-InformationItem-DM-Failns-ExtIEs RNSAP-PROTOCOL-EXTENSION ::= {
--	...
--}

-- **************************************************************
--
-- DEDICATED MEASUREMENT REPORT
--
-- **************************************************************

--DedicatedMeasurementReport ::= SEQUENCE {
--	protocolIEs                     ProtocolIE-Container       {{DedicatedMeasurementReport-IEs}},
--	protocolExtensions              ProtocolExtensionContainer {{DedicatedMeasurementReport-Extensions}}                   OPTIONAL,
--	...
--}

DedicatedMeasurementReport ::= SEQUENCE {
	protocolIEs                     ProtocolIE-Container,
	protocolExtensions              ProtocolExtensionContainer OPTIONAL,
	...
}
--DedicatedMeasurementReport-IEs RNSAP-PROTOCOL-IES ::= {
--	{ ID id-MeasurementID				CRITICALITY ignore	TYPE MeasurementID				PRESENCE mandatory	} |
--	{ ID id-DedicatedMeasurementObjectType-DM-Rprt	CRITICALITY ignore	TYPE DedicatedMeasurementObjectType-DM-Rprt	PRESENCE mandatory	},
--	...
--}

DedicatedMeasurementObjectType-DM-Rprt ::= CHOICE {
	rLs						RL-DM-Rprt,
	rLS						RL-Set-DM-Rprt,
	allRL					RL-DM-Rprt,
	allRLS					RL-Set-DM-Rprt,
	...
}

RL-DM-Rprt ::= SEQUENCE {
	rL-InformationList-DM-Rprt		RL-InformationList-DM-Rprt,
--	iE-Extensions					ProtocolExtensionContainer { { RLItem-DM-Rprt-ExtIEs} } OPTIONAL,
	iE-Extensions					ProtocolExtensionContainer OPTIONAL,
	...
}

--RLItem-DM-Rprt-ExtIEs RNSAP-PROTOCOL-EXTENSION ::= {
--	...
--}

RL-Set-DM-Rprt ::= SEQUENCE {
	rL-Set-InformationList-DM-Rprt	RL-Set-InformationList-DM-Rprt,
--	iE-Extensions					ProtocolExtensionContainer { { RL-SetItem-DM-Rprt-ExtIEs} } OPTIONAL,
	iE-Extensions					ProtocolExtensionContainer OPTIONAL,
	...
}

--RL-SetItem-DM-Rprt-ExtIEs RNSAP-PROTOCOL-EXTENSION ::= {
--	...
--}

--RL-InformationList-DM-Rprt					::= SEQUENCE (SIZE (1..maxNrOfRLs)) OF ProtocolIE-Single-Container { {RL-Information-DM-Rprt-IEs} }
RL-InformationList-DM-Rprt					::= SEQUENCE (SIZE (1..16)) OF ProtocolIE-Single-Container

--RL-Information-DM-Rprt-IEs RNSAP-PROTOCOL-IES ::= {
--	{ ID id-RL-InformationItem-DM-Rprt		CRITICALITY ignore	TYPE RL-InformationItem-DM-Rprt			PRESENCE mandatory	}
--}

RL-InformationItem-DM-Rprt ::= SEQUENCE {
	rL-ID						RL-ID,
	dPCH-ID						DPCH-ID				OPTIONAL,
	dedicatedMeasurementValueInformation	DedicatedMeasurementValueInformation,
--	iE-Extensions					ProtocolExtensionContainer { {RL-InformationItem-DM-Rprt-ExtIEs} } OPTIONAL,
	iE-Extensions					ProtocolExtensionContainer OPTIONAL,
	...
}

--RL-InformationItem-DM-Rprt-ExtIEs RNSAP-PROTOCOL-EXTENSION ::= {
--	{ID id-HSSICH-Info-DM-Rprt		CRITICALITY ignore				EXTENSION	HS-SICH-ID		PRESENCE optional},
	-- TDD only
--	...
--}

--RL-Set-InformationList-DM-Rprt					::= SEQUENCE (SIZE (1..maxNrOfRLSets)) OF ProtocolIE-Single-Container { {RL-Set-Information-DM-Rprt-IEs} }
RL-Set-InformationList-DM-Rprt					::= SEQUENCE (SIZE (1..16)) OF ProtocolIE-Single-Container

--RL-Set-Information-DM-Rprt-IEs RNSAP-PROTOCOL-IES ::= {
--	{ ID id-RL-Set-InformationItem-DM-Rprt		CRITICALITY ignore	TYPE RL-Set-InformationItem-DM-Rprt			PRESENCE mandatory	}
--}

RL-Set-InformationItem-DM-Rprt ::= SEQUENCE {
	rL-Set-ID						RL-Set-ID,
	dedicatedMeasurementValueInformation	DedicatedMeasurementValueInformation,
--	iE-Extensions					ProtocolExtensionContainer { {RL-Set-InformationItem-DM-Rprt-ExtIEs} } OPTIONAL,
	iE-Extensions					ProtocolExtensionContainer OPTIONAL,
	...
}

--RL-Set-InformationItem-DM-Rprt-ExtIEs RNSAP-PROTOCOL-EXTENSION ::= {
--	...
--}

--DedicatedMeasurementReport-Extensions RNSAP-PROTOCOL-EXTENSION ::= {
--	{ ID	id-MeasurementRecoveryReportingIndicator		CRITICALITY ignore		EXTENSION	MeasurementRecoveryReportingIndicator		PRESENCE optional },
--	...
--}

-- **************************************************************
--
-- DEDICATED MEASUREMENT TERMINATION REQUEST
--
-- **************************************************************

--DedicatedMeasurementTerminationRequest ::= SEQUENCE {
--	protocolIEs                     ProtocolIE-Container       {{DedicatedMeasurementTerminationRequest-IEs}},
--	protocolExtensions              ProtocolExtensionContainer {{DedicatedMeasurementTerminationRequest-Extensions}}                   OPTIONAL,
--	...
--}
DedicatedMeasurementTerminationRequest ::= SEQUENCE {
	protocolIEs                     ProtocolIE-Container,
	protocolExtensions              ProtocolExtensionContainer OPTIONAL,
	...
}

--DedicatedMeasurementTerminationRequest-IEs RNSAP-PROTOCOL-IES ::= {
--	{ ID id-MeasurementID				CRITICALITY ignore	TYPE MeasurementID				PRESENCE mandatory	},
--	...
--}

--DedicatedMeasurementTerminationRequest-Extensions RNSAP-PROTOCOL-EXTENSION ::= {
--	...
--}

-- **************************************************************
--
-- DEDICATED MEASUREMENT FAILURE INDICATION
--
-- **************************************************************

--DedicatedMeasurementFailureIndication ::= SEQUENCE {
--	protocolIEs                     ProtocolIE-Container       {{DedicatedMeasurementFailureIndication-IEs}},
--	protocolExtensions              ProtocolExtensionContainer {{DedicatedMeasurementFailureIndication-Extensions}}                   OPTIONAL,
--	...
--}
DedicatedMeasurementFailureIndication ::= SEQUENCE {
	protocolIEs                     ProtocolIE-Container,
	protocolExtensions              ProtocolExtensionContainer OPTIONAL,
	...
}

--DedicatedMeasurementFailureIndication-IEs RNSAP-PROTOCOL-IES ::= {
--	{ ID id-MeasurementID				CRITICALITY ignore	TYPE MeasurementID				PRESENCE mandatory	} |
--	{ ID id-Cause					CRITICALITY ignore	TYPE Cause					PRESENCE mandatory	},
--	...
--}

--DedicatedMeasurementFailureIndication-Extensions RNSAP-PROTOCOL-EXTENSION ::= {
--	{ ID id-DedicatedMeasurementObjectType-DM-Fail-Ind	CRITICALITY ignore	EXTENSION DedicatedMeasurementObjectType-DM-Fail-Ind	PRESENCE optional	},
--	...
--}

DedicatedMeasurementObjectType-DM-Fail-Ind ::= CHOICE {
	rL						RL-DM-Fail-Ind,
	rLS						RL-Set-DM-Fail-Ind,
	allRL					RL-DM-Fail-Ind,
	allRLS					RL-Set-DM-Fail-Ind,
	...
}

RL-DM-Fail-Ind ::= SEQUENCE {
	rL-unsuccessful-InformationRespList-DM-Fail-Ind		RL-Unsuccessful-InformationRespList-DM-Fail-Ind,
--	iE-Extensions										ProtocolExtensionContainer { { RLItem-DM-Fail-Ind-ExtIEs} } OPTIONAL,
	iE-Extensions										ProtocolExtensionContainer OPTIONAL,
	...
}

--RLItem-DM-Fail-Ind-ExtIEs RNSAP-PROTOCOL-EXTENSION ::= {
--	...
--}

RL-Set-DM-Fail-Ind ::= SEQUENCE {
	rL-Set-unsuccessful-InformationRespList-DM-Fail-Ind		RL-Set-Unsuccessful-InformationRespList-DM-Fail-Ind,
--	iE-Extensions											ProtocolExtensionContainer { { RL-SetItem-DM-Fail-Ind-ExtIEs} } OPTIONAL,
	iE-Extensions											ProtocolExtensionContainer OPTIONAL,
	...
}

--RL-SetItem-DM-Fail-Ind-ExtIEs RNSAP-PROTOCOL-EXTENSION ::= {
--	...
--}

--RL-Unsuccessful-InformationRespList-DM-Fail-Ind			::= SEQUENCE (SIZE (1..maxNrOfRLs)) OF ProtocolIE-Single-Container { {RL-Unsuccessful-InformationResp-DM-Fail-Ind-IEs} }
RL-Unsuccessful-InformationRespList-DM-Fail-Ind			::= SEQUENCE (SIZE (1..16)) OF ProtocolIE-Single-Container

--RL-Unsuccessful-InformationResp-DM-Fail-Ind-IEs RNSAP-PROTOCOL-IES ::= {
--	{ ID id-RL-Unsuccessful-InformationItem-DM-Fail-Ind		CRITICALITY ignore	TYPE RL-Unsuccessful-InformationItem-DM-Fail-Ind		PRESENCE mandatory	}
--}

RL-Unsuccessful-InformationItem-DM-Fail-Ind ::= SEQUENCE {
	rL-ID						RL-ID,
	individualcause				Cause		OPTIONAL,
--	iE-Extensions				ProtocolExtensionContainer { {RL-Unsuccessful-InformationItem-DM-Fail-Ind-ExtIEs} } OPTIONAL,
	iE-Extensions				ProtocolExtensionContainer OPTIONAL,
	...
}

--RL-Unsuccessful-InformationItem-DM-Fail-Ind-ExtIEs RNSAP-PROTOCOL-EXTENSION ::= {
--	...
--}

--RL-Set-Unsuccessful-InformationRespList-DM-Fail-Ind				::= SEQUENCE (SIZE (1..maxNrOfRLSets)) OF ProtocolIE-Single-Container { {RL-Set-Unsuccessful-InformationResp-DM-Fail-Ind-IEs} }
RL-Set-Unsuccessful-InformationRespList-DM-Fail-Ind				::= SEQUENCE (SIZE (1..16)) OF ProtocolIE-Single-Container 

--RL-Set-Unsuccessful-InformationResp-DM-Fail-Ind-IEs RNSAP-PROTOCOL-IES ::= {
--	{ ID id-RL-Set-Unsuccessful-InformationItem-DM-Fail-Ind		CRITICALITY ignore	TYPE RL-Set-Unsuccessful-InformationItem-DM-Fail-Ind		PRESENCE mandatory	}
--}

RL-Set-Unsuccessful-InformationItem-DM-Fail-Ind ::= SEQUENCE {
	rL-Set-ID						RL-Set-ID,
	individualcause					Cause		OPTIONAL,
--	iE-Extensions					ProtocolExtensionContainer { {RL-Set-Unsuccessful-InformationItem-DM-Fail-Indns-ExtIEs} } OPTIONAL,
	iE-Extensions					ProtocolExtensionContainer OPTIONAL,
	...
}

--RL-Set-Unsuccessful-InformationItem-DM-Fail-Indns-ExtIEs RNSAP-PROTOCOL-EXTENSION ::= {
--	...
--}

-- **************************************************************
--
-- COMMON TRANSPORT CHANNEL RESOURCES RELEASE REQUEST
--
-- **************************************************************
-- **************************************************************
--
-- COMMON TRANSPORT CHANNEL RESOURCES RELEASE REQUEST
--
-- **************************************************************

--CommonTransportChannelResourcesReleaseRequest ::= SEQUENCE {
--	protocolIEs                     ProtocolIE-Container       {{CommonTransportChannelResourcesReleaseRequest-IEs}},
--	protocolExtensions              ProtocolExtensionContainer {{CommonTransportChannelResourcesReleaseRequest-Extensions}}                   OPTIONAL,
--	...
--}
CommonTransportChannelResourcesReleaseRequest ::= SEQUENCE {
	protocolIEs                     ProtocolIE-Container,
	protocolExtensions              ProtocolExtensionContainer OPTIONAL,
	...
}

--CommonTransportChannelResourcesReleaseRequest-IEs RNSAP-PROTOCOL-IES ::= {
--	{ ID id-D-RNTI					CRITICALITY ignore	TYPE D-RNTI					PRESENCE mandatory	},
--	...
--}

--CommonTransportChannelResourcesReleaseRequest-Extensions RNSAP-PROTOCOL-EXTENSION ::= {
--	...
--}

-- **************************************************************
--
-- COMMON TRANSPORT CHANNEL RESOURCES REQUEST
--
-- **************************************************************

--CommonTransportChannelResourcesRequest ::= SEQUENCE {
--	protocolIEs                     ProtocolIE-Container       {{CommonTransportChannelResourcesRequest-IEs}},
--	protocolExtensions              ProtocolExtensionContainer {{CommonTransportChannelResourcesRequest-Extensions}}			OPTIONAL,
--	...
--}
CommonTransportChannelResourcesRequest ::= SEQUENCE {
	protocolIEs                     ProtocolIE-Container,
	protocolExtensions              ProtocolExtensionContainer OPTIONAL,
	...
}

--CommonTransportChannelResourcesRequest-IEs RNSAP-PROTOCOL-IES ::= {
--	{ ID id-D-RNTI					CRITICALITY reject	TYPE D-RNTI					PRESENCE mandatory	} |
--	{ ID id-C-ID					CRITICALITY reject	TYPE C-ID					PRESENCE optional	} |
--	{ ID id-TransportBearerRequestIndicator		CRITICALITY reject	TYPE TransportBearerRequestIndicator		PRESENCE mandatory	} |
--	{ ID id-TransportBearerID			CRITICALITY reject	TYPE TransportBearerID				PRESENCE mandatory	},
--	...
--}

--CommonTransportChannelResourcesRequest-Extensions RNSAP-PROTOCOL-EXTENSION ::= {
--	{ ID id-Permanent-NAS-UE-Identity				CRITICALITY ignore			EXTENSION Permanent-NAS-UE-Identity		PRESENCE optional	}|
--	{ ID id-BindingID						CRITICALITY	ignore		EXTENSION 	BindingID	PRESENCE 	optional	}|
	-- Shall be ignored if bearer establishment with ALCAP.
--    { ID id-TransportLayerAddress			CRITICALITY	ignore		EXTENSION 	TransportLayerAddress		PRESENCE 	optional	}|
	-- Shall be ignored if bearer establishment with ALCAP.
--	{ ID id-MBMS-Bearer-Service-List		CRITICALITY	notify 	EXTENSION MBMS-Bearer-Service-List			PRESENCE optional},
--	...}

-- **************************************************************
--
-- COMMON TRANSPORT CHANNEL RESOURCES RESPONSE FDD
--
-- **************************************************************

--CommonTransportChannelResourcesResponseFDD ::= SEQUENCE {
--	protocolIEs                     ProtocolIE-Container       {{CommonTransportChannelResourcesResponseFDD-IEs}},
--	protocolExtensions              ProtocolExtensionContainer {{CommonTransportChannelResourcesResponseFDD-Extensions}}			OPTIONAL,
--	...
--}
CommonTransportChannelResourcesResponseFDD ::= SEQUENCE {
	protocolIEs                     ProtocolIE-Container,
	protocolExtensions              ProtocolExtensionContainer OPTIONAL,
	...
}

--CommonTransportChannelResourcesResponseFDD-IEs RNSAP-PROTOCOL-IES ::= {
--	{ ID id-S-RNTI					CRITICALITY ignore	TYPE S-RNTI					PRESENCE mandatory	} |
--	{ ID id-C-RNTI					CRITICALITY ignore	TYPE C-RNTI					PRESENCE optional	} |
--	{ ID id-FACH-InfoForUESelectedS-CCPCH-CTCH-ResourceRspFDD	CRITICALITY ignore	TYPE FACH-InfoForUESelectedS-CCPCH-CTCH-ResourceRspFDD		PRESENCE mandatory	} |
--	{ ID id-TransportLayerAddress			CRITICALITY ignore	TYPE TransportLayerAddress			PRESENCE optional	} |
--	{ ID id-BindingID				CRITICALITY ignore	TYPE BindingID					PRESENCE optional	} |
--	{ ID id-CriticalityDiagnostics			CRITICALITY ignore	TYPE CriticalityDiagnostics			PRESENCE optional	},
--	...
--}

FACH-InfoForUESelectedS-CCPCH-CTCH-ResourceRspFDD ::= SEQUENCE {
	fACH-FlowControlInformation		FACH-FlowControlInformation-CTCH-ResourceRspFDD,
--	iE-Extensions					ProtocolExtensionContainer { {FACH-InfoForUESelectedS-CCPCH-CTCH-ResourceRspFDD-ExtIEs} } OPTIONAL,
	iE-Extensions					ProtocolExtensionContainer OPTIONAL,
	...
}

--FACH-InfoForUESelectedS-CCPCH-CTCH-ResourceRspFDD-ExtIEs RNSAP-PROTOCOL-EXTENSION ::= {
--	...
--}

--FACH-FlowControlInformation-CTCH-ResourceRspFDD ::= ProtocolIE-Single-Container {{ FACH-FlowControlInformationIEs-CTCH-ResourceRspFDD }}
FACH-FlowControlInformation-CTCH-ResourceRspFDD ::= ProtocolIE-Single-Container

--FACH-FlowControlInformationIEs-CTCH-ResourceRspFDD RNSAP-PROTOCOL-IES ::= {
--	{ ID id-FACH-FlowControlInformation	CRITICALITY ignore	TYPE	FACH-FlowControlInformation	PRESENCE mandatory	}
--}

--CommonTransportChannelResourcesResponseFDD-Extensions RNSAP-PROTOCOL-EXTENSION ::= {
--	{ ID id-C-ID								CRITICALITY ignore		EXTENSION 	C-ID											PRESENCE mandatory  }|
--	{ ID id-Active-MBMS-Bearer-ServiceFDD		CRITICALITY ignore		EXTENSION Active-MBMS-Bearer-Service-ListFDD		PRESENCE optional},
--	...
--}

-- **************************************************************
--
-- COMMON TRANSPORT CHANNEL RESOURCES RESPONSE TDD
--
-- **************************************************************

--CommonTransportChannelResourcesResponseTDD ::= SEQUENCE {
--	protocolIEs                     ProtocolIE-Container       {{CommonTransportChannelResourcesResponseTDD-IEs}},
--	protocolExtensions              ProtocolExtensionContainer {{CommonTransportChannelResourcesResponseTDD-Extensions}}			OPTIONAL,
--	...
--}
CommonTransportChannelResourcesResponseTDD ::= SEQUENCE {
	protocolIEs                     ProtocolIE-Container,
	protocolExtensions              ProtocolExtensionContainer OPTIONAL,
	...
}

--CommonTransportChannelResourcesResponseTDD-IEs RNSAP-PROTOCOL-IES ::= {
--	{ ID id-S-RNTI					CRITICALITY ignore	TYPE S-RNTI					PRESENCE mandatory	} |
--	{ ID id-C-RNTI					CRITICALITY ignore	TYPE C-RNTI					PRESENCE optional	} |
--	{ ID id-FACH-InfoForUESelectedS-CCPCH-CTCH-ResourceRspTDD	CRITICALITY ignore	TYPE FACH-InfoForUESelectedS-CCPCH-CTCH-ResourceRspTDD		PRESENCE mandatory	} |
--	{ ID id-TransportLayerAddress			CRITICALITY ignore	TYPE TransportLayerAddress			PRESENCE optional	} |
--	{ ID id-BindingID				CRITICALITY ignore	TYPE BindingID					PRESENCE optional	} |
--	{ ID id-CriticalityDiagnostics			CRITICALITY ignore	TYPE CriticalityDiagnostics			PRESENCE optional	},
--	...
--}

FACH-InfoForUESelectedS-CCPCH-CTCH-ResourceRspTDD ::= SEQUENCE {
	fACH-FlowControlInformation		FACH-FlowControlInformation-CTCH-ResourceRspTDD,
--	iE-Extensions					ProtocolExtensionContainer { {FACH-InfoForUESelectedS-CCPCH-CTCH-ResourceRspTDD-ExtIEs} } OPTIONAL,
	iE-Extensions					ProtocolExtensionContainer OPTIONAL,
	...
}

--FACH-InfoForUESelectedS-CCPCH-CTCH-ResourceRspTDD-ExtIEs RNSAP-PROTOCOL-EXTENSION ::= {
--	...
--}

--FACH-FlowControlInformation-CTCH-ResourceRspTDD ::= ProtocolIE-Single-Container {{ FACH-FlowControlInformationIEs-CTCH-ResourceRspTDD }}
FACH-FlowControlInformation-CTCH-ResourceRspTDD ::= ProtocolIE-Single-Container

--FACH-FlowControlInformationIEs-CTCH-ResourceRspTDD RNSAP-PROTOCOL-IES ::= {
--	{ ID id-FACH-FlowControlInformation	CRITICALITY ignore	TYPE	FACH-FlowControlInformation	PRESENCE mandatory	}
--}

--CommonTransportChannelResourcesResponseTDD-Extensions RNSAP-PROTOCOL-EXTENSION ::= {
--	{ ID id-C-ID								CRITICALITY ignore		EXTENSION 	C-ID											PRESENCE mandatory  }|
--	{ ID id-Active-MBMS-Bearer-ServiceTDD		CRITICALITY ignore		EXTENSION Active-MBMS-Bearer-Service-ListTDD		PRESENCE optional},
--	...
--}

-- **************************************************************
--
-- COMMON TRANSPORT CHANNEL RESOURCES FAILURE
--
-- **************************************************************

--CommonTransportChannelResourcesFailure ::= SEQUENCE {
--	protocolIEs                     ProtocolIE-Container       {{CommonTransportChannelResourcesFailure-IEs}},
--	protocolExtensions              ProtocolExtensionContainer {{CommonTransportChannelResourcesFailure-Extensions}}			OPTIONAL,
--	...
--}
CommonTransportChannelResourcesFailure ::= SEQUENCE {
	protocolIEs                     ProtocolIE-Container,
	protocolExtensions              ProtocolExtensionContainer OPTIONAL,
	...
}

--CommonTransportChannelResourcesFailure-IEs RNSAP-PROTOCOL-IES ::= {
--	{ ID id-S-RNTI					CRITICALITY ignore	TYPE S-RNTI					PRESENCE mandatory	} |
--	{ ID id-Cause					CRITICALITY ignore	TYPE Cause					PRESENCE mandatory	} |
--	{ ID id-CriticalityDiagnostics			CRITICALITY ignore	TYPE CriticalityDiagnostics			PRESENCE optional	},
--	...
--}

--CommonTransportChannelResourcesFailure-Extensions RNSAP-PROTOCOL-EXTENSION ::= {
--	...
--}

-- **************************************************************
--
-- COMPRESSED MODE COMMAND
--
-- **************************************************************

--CompressedModeCommand ::= SEQUENCE {
--	protocolIEs                     ProtocolIE-Container       {{CompressedModeCommand-IEs}},
--	protocolExtensions              ProtocolExtensionContainer {{CompressedModeCommand-Extensions}}                   OPTIONAL,
--	...
--}
CompressedModeCommand ::= SEQUENCE {
	protocolIEs                     ProtocolIE-Container,
	protocolExtensions              ProtocolExtensionContainer OPTIONAL,
	...
}

--CompressedModeCommand-IEs RNSAP-PROTOCOL-IES ::= {
--	{ ID id-Active-Pattern-Sequence-Information		CRITICALITY ignore	TYPE Active-Pattern-Sequence-Information		 PRESENCE mandatory  },
--	...
--}

--CompressedModeCommand-Extensions RNSAP-PROTOCOL-EXTENSION ::= {
--	...
--}

-- **************************************************************
--
-- ERROR INDICATION
--
-- **************************************************************

--ErrorIndication ::= SEQUENCE {
--	protocolIEs                     ProtocolIE-Container       {{ErrorIndication-IEs}},
--	protocolExtensions              ProtocolExtensionContainer {{ErrorIndication-Extensions}}                   	OPTIONAL,
--	...
--}
ErrorIndication ::= SEQUENCE {
	protocolIEs                     ProtocolIE-Container,
	protocolExtensions              ProtocolExtensionContainer OPTIONAL,
	...
}

--ErrorIndication-IEs RNSAP-PROTOCOL-IES ::= {
--	{ ID id-Cause					CRITICALITY ignore	TYPE Cause					PRESENCE optional} |
--	{ ID id-CriticalityDiagnostics			CRITICALITY ignore	TYPE CriticalityDiagnostics			PRESENCE optional	},
--	...
--}

--ErrorIndication-Extensions RNSAP-PROTOCOL-EXTENSION ::= {
--	{ ID id-S-RNTI					CRITICALITY ignore	EXTENSION S-RNTI					PRESENCE optional	} |
--	{ ID id-D-RNTI					CRITICALITY ignore	EXTENSION D-RNTI					PRESENCE optional	},
--	...
--}

-- **************************************************************
--
-- COMMON MEASUREMENT INITIATION REQUEST
--
-- **************************************************************

--CommonMeasurementInitiationRequest ::= SEQUENCE {
--	protocolIEs				ProtocolIE-Container	{{CommonMeasurementInitiationRequest-IEs}},
--	protocolExtensions		ProtocolExtensionContainer	{{CommonMeasurementInitiationRequest-Extensions}}		OPTIONAL,
--	...
--}
CommonMeasurementInitiationRequest ::= SEQUENCE {
	protocolIEs				ProtocolIE-Container,
	protocolExtensions		ProtocolExtensionContainer	OPTIONAL,
	...
}

--CommonMeasurementInitiationRequest-IEs RNSAP-PROTOCOL-IES ::= {
--	{ ID	id-MeasurementID								CRITICALITY	reject			TYPE	MeasurementID								PRESENCE	mandatory	}|
--	{ ID	id-CommonMeasurementObjectType-CM-Rqst			CRITICALITY	reject			TYPE 	CommonMeasurementObjectType-CM-Rqst		PRESENCE 	mandatory	}|

--	{ ID	id-CommonMeasurementType						CRITICALITY	reject			TYPE	CommonMeasurementType					PRESENCE	mandatory	}|
--	{ ID 	id-MeasurementFilterCoefficient					CRITICALITY	reject			TYPE	MeasurementFilterCoefficient			PRESENCE	optional	}|
	-- UTRAN only
--	{ ID	id-ReportCharacteristics						CRITICALITY	reject			TYPE	ReportCharacteristics					PRESENCE	mandatory	}|
--	{ ID	id-SFNReportingIndicator						CRITICALITY	reject			TYPE	FNReportingIndicator					PRESENCE	mandatory
--	} |
--	{ ID	id-SFN											CRITICALITY reject			TYPE	SFN											PRESENCE optional
--	}|
	-- UTRAN only
--	{ ID    id-CommonMeasurementAccuracy					CRITICALITY reject			TYPE	CommonMeasurementAccuracy				PRESENCE optional
--	},
	-- UTRAN only
--	...
--}

--CommonMeasurementInitiationRequest-Extensions RNSAP-PROTOCOL-EXTENSION ::= {
--	{ ID	id-MeasurementRecoveryBehavior				CRITICALITY ignore				EXTENSION	MeasurementRecoveryBehavior		PRESENCE optional
--	},
	-- UTRAN only
--	...
--}

CommonMeasurementObjectType-CM-Rqst ::= CHOICE {
	cell							Cell-CM-Rqst,
	...
}

Cell-CM-Rqst ::= SEQUENCE {
	uC-ID							UC-ID,
	-- May be a GERAN cell identifier
	timeSlot						TimeSlot		OPTIONAL,	--3.84Mcps TDD only
	timeSlotLCR						TimeSlotLCR		OPTIONAL,	--1.28Mcps TDD only
	neighbouringCellMeasurementInformation			NeighbouringCellMeasurementInfo		OPTIONAL,
	-- UTRAN only
--	iE-Extensions					ProtocolExtensionContainer  { { CellItem-CM-Rqst-ExtIEs} }		OPTIONAL,
	iE-Extensions					ProtocolExtensionContainer  OPTIONAL,
	...
}

--NeighbouringCellMeasurementInfo ::=	SEQUENCE (SIZE (1..maxNrOfMeasNCell)) OF
NeighbouringCellMeasurementInfo ::=	SEQUENCE (SIZE (1..96)) OF
		CHOICE {
				neighbouringFDDCellMeasurementInformation		NeighbouringFDDCellMeasurementInformation,
				neighbouringTDDCellMeasurementInformation		NeighbouringTDDCellMeasurementInformation,
				...,
				extension-neighbouringCellMeasurementInformation	Extension-neighbouringCellMeasurementInformation
			}

--Extension-neighbouringCellMeasurementInformation	::=	ProtocolIE-Single-Container {{ Extension-neighbouringCellMeasurementInformationIE }}
Extension-neighbouringCellMeasurementInformation	::=	ProtocolIE-Single-Container

--Extension-neighbouringCellMeasurementInformationIE RNSAP-PROTOCOL-IES ::= {
--	{ ID id-neighbouringTDDCellMeasurementInformationLCR	CRITICALITY reject	TYPE NeighbouringTDDCellMeasurementInformationLCR	PRESENCE mandatory },
--	...
--}

--CellItem-CM-Rqst-ExtIEs RNSAP-PROTOCOL-EXTENSION ::= {
--	...
--}

-- **************************************************************
--
-- COMMON MEASUREMENT INITIATION RESPONSE
--
-- **************************************************************
--CommonMeasurementInitiationResponse ::= SEQUENCE {
--	protocolIEs				ProtocolIE-Container	{{CommonMeasurementInitiationResponse-IEs}},
--	protocolExtensions		ProtocolExtensionContainer	{{CommonMeasurementInitiationResponse-Extensions}}		OPTIONAL,
--	...
--}
CommonMeasurementInitiationResponse ::= SEQUENCE {
	protocolIEs				ProtocolIE-Container,
	protocolExtensions		ProtocolExtensionContainer	OPTIONAL,
	...
}
--CommonMeasurementInitiationResponse-IEs RNSAP-PROTOCOL-IES ::= {
--	{ ID	id-MeasurementID							CRITICALITY	ignore			TYPE	MeasurementID									PRESENCE	mandatory	}|
--	{ ID	id-CommonMeasurementObjectType-CM-Rsp		CRITICALITY	ignore			TYPE	CommonMeasurementObjectType-CM-Rsp		PRESENCE	optional	}|
--	{ ID	id-SFN										CRITICALITY	ignore			TYPE	SFN													PRESENCE	optional	}|
	-- UTRAN only
--	{ ID	id-CriticalityDiagnostics					CRITICALITY	ignore			TYPE	CriticalityDiagnostics						PRESENCE	optional	}|
--	{ ID    id-CommonMeasurementAccuracy					CRITICALITY reject			TYPE	CommonMeasurementAccuracy				PRESENCE optional
--	},
	-- UTRAN only
--	...
--}

--CommonMeasurementInitiationResponse-Extensions RNSAP-PROTOCOL-EXTENSION ::= {
--	{ ID	id-MeasurementRecoverySupportIndicator		CRITICALITY ignore		EXTENSION	MeasurementRecoverySupportIndicator		PRESENCE optional
--	},
	-- UTRAN only
--	...
--}

CommonMeasurementObjectType-CM-Rsp ::= CHOICE {
	cell						Cell-CM-Rsp,
	...
 }

Cell-CM-Rsp ::= SEQUENCE {
	commonMeasurementValue						CommonMeasurementValue,
--	iE-Extensions								ProtocolExtensionContainer  { { CellItem-CM-Rsp-ExtIEs} }		OPTIONAL,
	iE-Extensions								ProtocolExtensionContainer OPTIONAL,
	...
 }

--CellItem-CM-Rsp-ExtIEs RNSAP-PROTOCOL-EXTENSION ::= {
--	...
--}

-- **************************************************************
--
-- COMMON MEASUREMENT INITIATION FAILURE
--
-- **************************************************************

--CommonMeasurementInitiationFailure ::= SEQUENCE {
--	protocolIEs				ProtocolIE-Container	{{CommonMeasurementInitiationFailure-IEs}},
--	protocolExtensions		ProtocolExtensionContainer	{{CommonMeasurementInitiationFailure-Extensions}}		OPTIONAL,
--	...
--}
CommonMeasurementInitiationFailure ::= SEQUENCE {
	protocolIEs				ProtocolIE-Container,
	protocolExtensions		ProtocolExtensionContainer	OPTIONAL,
	...
}

--CommonMeasurementInitiationFailure-IEs RNSAP-PROTOCOL-IES ::= {
--	{ ID	id-MeasurementID				CRITICALITY		ignore			TYPE	MeasurementID					PRESENCE	mandatory	}|
--	{ ID	id-Cause						CRITICALITY		ignore			TYPE	Cause							PRESENCE	mandatory	}|
--	{ ID	id-CriticalityDiagnostics		CRITICALITY		ignore			TYPE	CriticalityDiagnostics		PRESENCE	optional	},
--	...
--}

--CommonMeasurementInitiationFailure-Extensions RNSAP-PROTOCOL-EXTENSION ::= {
--	...
--}

-- **************************************************************
--
-- COMMON MEASUREMENT REPORT
--
-- **************************************************************

--CommonMeasurementReport ::= SEQUENCE {
--	protocolIEs				ProtocolIE-Container	{{CommonMeasurementReport-IEs}},
--	protocolExtensions		ProtocolExtensionContainer	{{CommonMeasurementReport-Extensions}}		OPTIONAL,
--	...
--}
CommonMeasurementReport ::= SEQUENCE {
	protocolIEs				ProtocolIE-Container,
	protocolExtensions		ProtocolExtensionContainer	OPTIONAL,
	...
}

--CommonMeasurementReport-IEs RNSAP-PROTOCOL-IES ::= {
--	{ ID	id-MeasurementID							CRITICALITY	ignore			TYPE	MeasurementID							PRESENCE	mandatory	}|
--	{ ID	id-CommonMeasurementObjectType-CM-Rprt		CRITICALITY	ignore			TYPE	CommonMeasurementObjectType-CM-Rprt		PRESENCE	mandatory	}|
--	{ ID	id-SFN										CRITICALITY	ignore			TYPE	SFN										PRESENCE	optional	},
	-- UTRAN only
--	...
--}

--CommonMeasurementReport-Extensions RNSAP-PROTOCOL-EXTENSION ::= {
--	{ ID	id-MeasurementRecoveryReportingIndicator		CRITICALITY ignore		EXTENSION	MeasurementRecoveryReportingIndicator		PRESENCE optional },
	-- UTRAN only
--	...
--}

CommonMeasurementObjectType-CM-Rprt ::= CHOICE {
	cell							Cell-CM-Rprt,
	...
 }

Cell-CM-Rprt ::= SEQUENCE {
	commonMeasurementValueInformation	CommonMeasurementValueInformation,
--	iE-Extensions					ProtocolExtensionContainer  {{ CellItem-CM-Rprt-ExtIEs }}		OPTIONAL,
	iE-Extensions					ProtocolExtensionContainer  OPTIONAL,
	...

 }

--CellItem-CM-Rprt-ExtIEs RNSAP-PROTOCOL-EXTENSION ::= {
--	...
--}

-- **************************************************************
--
-- COMMON MEASUREMENT TERMINATION REQUEST
--
-- **************************************************************

--CommonMeasurementTerminationRequest ::= SEQUENCE {
--	protocolIEs				ProtocolIE-Container	{{CommonMeasurementTerminationRequest-IEs}},
--	protocolExtensions		ProtocolExtensionContainer	{{CommonMeasurementTerminationRequest-Extensions}}		OPTIONAL,
--	...
--}
CommonMeasurementTerminationRequest ::= SEQUENCE {
	protocolIEs				ProtocolIE-Container,
	protocolExtensions		ProtocolExtensionContainer	OPTIONAL,
	...
}

--CommonMeasurementTerminationRequest-IEs RNSAP-PROTOCOL-IES ::= {
--	{ ID	id-MeasurementID			CRITICALITY		ignore				TYPE	MeasurementID			PRESENCE	mandatory},
--	...
--}

--CommonMeasurementTerminationRequest-Extensions RNSAP-PROTOCOL-EXTENSION ::= {
--	...
--}

-- **************************************************************
--
-- COMMON MEASUREMENT FAILURE INDICATION
--
-- **************************************************************

--CommonMeasurementFailureIndication ::= SEQUENCE {
--	protocolIEs				ProtocolIE-Container	{{CommonMeasurementFailureIndication-IEs}},
--	protocolExtensions			ProtocolExtensionContainer	{{CommonMeasurementFailureIndication-Extensions}}				OPTIONAL,
--	...
--}
CommonMeasurementFailureIndication ::= SEQUENCE {
	protocolIEs				ProtocolIE-Container,
	protocolExtensions			ProtocolExtensionContainer	OPTIONAL,
	...
}

--CommonMeasurementFailureIndication-IEs RNSAP-PROTOCOL-IES ::= {
--	{ ID	id-MeasurementID			CRITICALITY	ignore			TYPE	MeasurementID			PRESENCE	mandatory	}|
--	{ ID	id-Cause					CRITICALITY	ignore			TYPE	Cause					PRESENCE	mandatory	},
--	...
--}

--CommonMeasurementFailureIndication-Extensions RNSAP-PROTOCOL-EXTENSION ::= {
--	...
--}

-- **************************************************************
--
-- INFORMATION EXCHANGE INITIATION REQUEST
--
-- **************************************************************

--InformationExchangeInitiationRequest ::= SEQUENCE {
--	protocolIEs				ProtocolIE-Container	{{InformationExchangeInitiationRequest-IEs}},
--	protocolExtensions		ProtocolExtensionContainer	{{InformationExchangeInitiationRequest-Extensions}}		OPTIONAL,
--	...
--}
InformationExchangeInitiationRequest ::= SEQUENCE {
	protocolIEs				ProtocolIE-Container,
	protocolExtensions		ProtocolExtensionContainer	OPTIONAL,
	...
}

--InformationExchangeInitiationRequest-IEs RNSAP-PROTOCOL-IES ::= {
--	{ ID	id-InformationExchangeID						CRITICALITY	reject		TYPE	InformationExchangeID					PRESENCE	mandatory	}|
--	{ ID	id-InformationExchangeObjectType-InfEx-Rqst		CRITICALITY	reject		TYPE 	InformationExchangeObjectType-InfEx-Rqst		PRESENCE 	mandatory	}|
--
--	{ ID	id-InformationType								CRITICALITY	reject		TYPE	InformationType							PRESENCE	mandatory	}|
--	{ ID	id-InformationReportCharacteristics				CRITICALITY	reject		TYPE	InformationReportCharacteristics		PRESENCE	mandatory	},
--	...
--}

--InformationExchangeInitiationRequest-Extensions RNSAP-PROTOCOL-EXTENSION ::= {
--	...
--}

InformationExchangeObjectType-InfEx-Rqst ::= CHOICE {
	cell													Cell-InfEx-Rqst,
	...,
	extension-InformationExchangeObjectType-InfEx-Rqst		Extension-InformationExchangeObjectType-InfEx-Rqst

}

Cell-InfEx-Rqst ::= SEQUENCE {
	c-ID							C-ID, --May be a GERAN cell identifier
--	iE-Extensions					ProtocolExtensionContainer  { { CellItem-InfEx-Rqst-ExtIEs} }		OPTIONAL,
	iE-Extensions					ProtocolExtensionContainer  OPTIONAL,
	...
}

--CellItem-InfEx-Rqst-ExtIEs RNSAP-PROTOCOL-EXTENSION ::= {
--	...
--}

--Extension-InformationExchangeObjectType-InfEx-Rqst	::= ProtocolIE-Single-Container {{ Extension-InformationExchangeObjectType-InfEx-RqstIE }}
Extension-InformationExchangeObjectType-InfEx-Rqst	::= ProtocolIE-Single-Container

--Extension-InformationExchangeObjectType-InfEx-RqstIE RNSAP-PROTOCOL-IES ::= {
--	{ ID id-GSM-Cell-InfEx-Rqst	CRITICALITY reject	TYPE GSM-Cell-InfEx-Rqst	PRESENCE mandatory }|
--	{ ID id-MBMS-Bearer-Service-List		CRITICALITY		reject		TYPE	MBMS-Bearer-Service-List		PRESENCE	mandatory}

--}

GSM-Cell-InfEx-Rqst ::= SEQUENCE {
	cGI								CGI,
--	iE-Extensions					ProtocolExtensionContainer  { { GSMCellItem-InfEx-Rqst-ExtIEs} }		OPTIONAL,
	iE-Extensions					ProtocolExtensionContainer  OPTIONAL,
	...
}

--GSMCellItem-InfEx-Rqst-ExtIEs RNSAP-PROTOCOL-EXTENSION ::= {
--	...
--}


-- **************************************************************
--
-- INFORMATION EXCHANGE INITIATION RESPONSE
--
-- **************************************************************
--InformationExchangeInitiationResponse ::= SEQUENCE {
--	protocolIEs				ProtocolIE-Container	{{InformationExchangeInitiationResponse-IEs}},
--	protocolExtensions		ProtocolExtensionContainer	{{InformationExchangeInitiationResponse-Extensions}}		OPTIONAL,
--	...
--}
InformationExchangeInitiationResponse ::= SEQUENCE {
	protocolIEs				ProtocolIE-Container,
	protocolExtensions		ProtocolExtensionContainer	OPTIONAL,
	...
}

--InformationExchangeInitiationResponse-IEs RNSAP-PROTOCOL-IES ::= {
--	{ ID	id-InformationExchangeID						CRITICALITY	ignore			TYPE	InformationExchangeID					PRESENCE	mandatory	}|
--	{ ID	id-InformationExchangeObjectType-InfEx-Rsp		CRITICALITY	ignore			TYPE	InformationExchangeObjectType-InfEx-Rsp		PRESENCE	optional	}|
--	{ ID	id-CriticalityDiagnostics						CRITICALITY	ignore			TYPE	CriticalityDiagnostics					PRESENCE	optional	},
--	...
--}

--InformationExchangeInitiationResponse-Extensions RNSAP-PROTOCOL-EXTENSION ::= {
--	...
--}

InformationExchangeObjectType-InfEx-Rsp ::= CHOICE {
	cell						Cell-InfEx-Rsp,
	...,
	extension-InformationExchangeObjectType-InfEx-Rsp		Extension-InformationExchangeObjectType-InfEx-Rsp
}

Cell-InfEx-Rsp ::= SEQUENCE {
	requestedDataValue				RequestedDataValue,
--	iE-Extensions					ProtocolExtensionContainer  { { CellItem-InfEx-Rsp-ExtIEs} }		OPTIONAL,
	iE-Extensions					ProtocolExtensionContainer  OPTIONAL,
	...
}

--CellItem-InfEx-Rsp-ExtIEs RNSAP-PROTOCOL-EXTENSION ::= {
--	...
--}


--Extension-InformationExchangeObjectType-InfEx-Rsp	::= ProtocolIE-Single-Container {{ Extension-InformationExchangeObjectType-InfEx-RspIE }}
Extension-InformationExchangeObjectType-InfEx-Rsp	::= ProtocolIE-Single-Container

--Extension-InformationExchangeObjectType-InfEx-RspIE RNSAP-PROTOCOL-IES ::= {
--	{ ID id-MBMS-Bearer-Service-List-InfEx-Rsp	CRITICALITY		ignore		TYPE	MBMS-Bearer-Service-List-InfEx-Rsp		PRESENCE	mandatory}
--}

--MBMS-Bearer-Service-List-InfEx-Rsp	::= SEQUENCE (SIZE (1..maxNrOfMBMSServices)) OF MBMS-Bearer-ServiceItemIEs-InfEx-Rsp
MBMS-Bearer-Service-List-InfEx-Rsp	::= SEQUENCE (SIZE (1..128)) OF MBMS-Bearer-ServiceItemIEs-InfEx-Rsp



MBMS-Bearer-ServiceItemIEs-InfEx-Rsp	::=SEQUENCE{
	tmgi	TMGI,
	requestedDataValue		RequestedDataValue,
--	iE-Extensions					ProtocolExtensionContainer { { MBMS-Bearer-ServiceItem-InfEx-Rsp-ExtIEs} } OPTIONAL,
	iE-Extensions					ProtocolExtensionContainer OPTIONAL,
	...
}

--MBMS-Bearer-ServiceItem-InfEx-Rsp-ExtIEs	RNSAP-PROTOCOL-EXTENSION ::= {
--	...
--}
-- **************************************************************
--
-- INFORMATION EXCHANGE INITIATION FAILURE
--
-- **************************************************************

--InformationExchangeInitiationFailure ::= SEQUENCE {
--	protocolIEs				ProtocolIE-Container	{{InformationExchangeInitiationFailure-IEs}},
--	protocolExtensions		ProtocolExtensionContainer	{{InformationExchangeInitiationFailure-Extensions}}		OPTIONAL,
--	...
--}
InformationExchangeInitiationFailure ::= SEQUENCE {
	protocolIEs				ProtocolIE-Container,
	protocolExtensions		ProtocolExtensionContainer	OPTIONAL,
	...
}

--InformationExchangeInitiationFailure-IEs RNSAP-PROTOCOL-IES ::= {
--	{ ID	id-InformationExchangeID				CRITICALITY		ignore			TYPE	InformationExchangeID				PRESENCE	mandatory	}|
--	{ ID	id-Cause								CRITICALITY		ignore			TYPE	Cause										PRESENCE	mandatory	}|
--	{ ID	id-CriticalityDiagnostics				CRITICALITY		ignore			TYPE	CriticalityDiagnostics				PRESENCE	optional	},
--	...
--}

--InformationExchangeInitiationFailure-Extensions RNSAP-PROTOCOL-EXTENSION ::= {
--	...
--}

-- **************************************************************
--
-- INFORMATION REPORT
--
-- **************************************************************

--InformationReport ::= SEQUENCE {
--	protocolIEs				ProtocolIE-Container	{{InformationReport-IEs}},
--	protocolExtensions		ProtocolExtensionContainer	{{InformationReport-Extensions}}		OPTIONAL,
--	...
--}
InformationReport ::= SEQUENCE {
	protocolIEs				ProtocolIE-Container,
	protocolExtensions		ProtocolExtensionContainer	OPTIONAL,
	...
}

--InformationReport-IEs RNSAP-PROTOCOL-IES ::= {
--	{ ID	id-InformationExchangeID						CRITICALITY	ignore			TYPE	InformationExchangeID								PRESENCE	mandatory	}|
--	{ ID	id-InformationExchangeObjectType-InfEx-Rprt		CRITICALITY	ignore			TYPE	InformationExchangeObjectType-InfEx-Rprt		PRESENCE	mandatory	},
--	...
--}

--InformationReport-Extensions RNSAP-PROTOCOL-EXTENSION ::= {
--	...
--}

InformationExchangeObjectType-InfEx-Rprt ::= CHOICE {
	cell							Cell-InfEx-Rprt,
	...
 }

Cell-InfEx-Rprt ::= SEQUENCE {
	requestedDataValueInformation	RequestedDataValueInformation,
--	iE-Extensions					ProtocolExtensionContainer  {{ CellItem-InfEx-Rprt-ExtIEs }}		OPTIONAL,
	iE-Extensions					ProtocolExtensionContainer  OPTIONAL,
	...

 }

--CellItem-InfEx-Rprt-ExtIEs RNSAP-PROTOCOL-EXTENSION ::= {
--	...
--}


-- **************************************************************
--
-- INFORMATION EXCHANGE TERMINATION REQUEST
--
-- **************************************************************

--InformationExchangeTerminationRequest ::= SEQUENCE {
--	protocolIEs				ProtocolIE-Container	{{InformationExchangeTerminationRequest-IEs}},
--	protocolExtensions		ProtocolExtensionContainer	{{InformationExchangeTerminationRequest-Extensions}}		OPTIONAL,
--	...
--}
InformationExchangeTerminationRequest ::= SEQUENCE {
	protocolIEs				ProtocolIE-Container,
	protocolExtensions		ProtocolExtensionContainer	OPTIONAL,
	...
}

--InformationExchangeTerminationRequest-IEs RNSAP-PROTOCOL-IES ::= {
--	{ ID	id-InformationExchangeID			CRITICALITY		ignore				TYPE	InformationExchangeID			PRESENCE	mandatory},
--	...
--}

--InformationExchangeTerminationRequest-Extensions RNSAP-PROTOCOL-EXTENSION ::= {
--	...
--}


-- **************************************************************
--
-- INFORMATION EXCHANGE FAILURE INDICATION
--
-- **************************************************************

--InformationExchangeFailureIndication ::= SEQUENCE {
--	protocolIEs				ProtocolIE-Container	{{InformationExchangeFailureIndication-IEs}},
--	protocolExtensions			ProtocolExtensionContainer	{{InformationExchangeFailureIndication-Extensions}}				OPTIONAL,
--	...
--}
InformationExchangeFailureIndication ::= SEQUENCE {
	protocolIEs				ProtocolIE-Container,
	protocolExtensions			ProtocolExtensionContainer	OPTIONAL,
	...
}

--InformationExchangeFailureIndication-IEs RNSAP-PROTOCOL-IES ::= {
--	{ ID	id-InformationExchangeID			CRITICALITY	ignore			TYPE	InformationExchangeID			PRESENCE	mandatory	}|
--	{ ID	id-Cause							CRITICALITY	ignore			TYPE	Cause								PRESENCE	mandatory	},
--	...
--}

--InformationExchangeFailureIndication-Extensions RNSAP-PROTOCOL-EXTENSION ::= {
--	...
--}

-- **************************************************************
--
-- RESET REQUEST
--
-- **************************************************************

--ResetRequest ::= SEQUENCE {
--	protocolIEs				ProtocolIE-Container	{{ResetRequest-IEs}},
--	protocolExtensions		ProtocolExtensionContainer	{{ResetRequest-Extensions}}		OPTIONAL,
--	...
--}
ResetRequest ::= SEQUENCE {
	protocolIEs				ProtocolIE-Container,
	protocolExtensions		ProtocolExtensionContainer	OPTIONAL,
	...
}

--ResetRequest-IEs RNSAP-PROTOCOL-IES ::= {
--	{ ID id-RNC-ID				CRITICALITY reject	TYPE RNC-ID		PRESENCE mandatory} |
--	{ ID id-ResetIndicator		CRITICALITY	reject		TYPE 	ResetIndicator		PRESENCE 	mandatory},
--	...
--}

--ResetRequest-Extensions RNSAP-PROTOCOL-EXTENSION ::= {
--	...
--}

ResetIndicator ::= CHOICE {
	context			ContextList-Reset,
	all-contexts		NULL,
	...,
	contextGroup	ContextGroupList-Reset
}

ContextList-Reset ::= SEQUENCE {
	contextInfoList-Reset		ContextInfoList-Reset,
--	iE-Extensions							ProtocolExtensionContainer  { {ContextItem-Reset-ExtIEs} }		OPTIONAL,
	iE-Extensions							ProtocolExtensionContainer  OPTIONAL,
	...
}

--ContextItem-Reset-ExtIEs RNSAP-PROTOCOL-EXTENSION ::= {
--	...
--}

--ContextInfoList-Reset ::= SEQUENCE (SIZE (1.. maxResetContext))	OF ProtocolIE-Single-Container {{ ContextInfoItemIE-Reset }}
ContextInfoList-Reset ::= SEQUENCE (SIZE (1.. 250))	OF ProtocolIE-Single-Container

--ContextInfoItemIE-Reset RNSAP-PROTOCOL-IES ::= {
--	{ID id-ContextInfoItem-Reset		CRITICALITY reject		TYPE ContextInfoItem-Reset		PRESENCE mandatory}
--}

ContextInfoItem-Reset ::= SEQUENCE {
	contextType-Reset			ContextType-Reset,
--	iE-Extensions				ProtocolExtensionContainer  { { ContextInfoItem-Reset-ExtIEs} }		OPTIONAL,
	iE-Extensions				ProtocolExtensionContainer  OPTIONAL,
	...
}

--ContextInfoItem-Reset-ExtIEs RNSAP-PROTOCOL-EXTENSION ::= {
--	...
--}

ContextType-Reset ::= CHOICE {
	sRNTI			S-RNTI,
	dRNTI			D-RNTI,
	...
}

ContextGroupList-Reset ::= SEQUENCE {
	contextGroupInfoList-Reset		ContextGroupInfoList-Reset,
--	iE-Extensions					ProtocolExtensionContainer  { {ContextGroupItem-Reset-ExtIEs} }		OPTIONAL,
	iE-Extensions					ProtocolExtensionContainer  OPTIONAL,
	...
}

--ContextGroupItem-Reset-ExtIEs RNSAP-PROTOCOL-EXTENSION ::= {
--	...
--}

--ContextGroupInfoList-Reset ::= SEQUENCE (SIZE (1.. maxResetContextGroup))	OF ProtocolIE-Single-Container {{ ContextGroupInfoItemIE-Reset }}
ContextGroupInfoList-Reset ::= SEQUENCE (SIZE (1.. 32))	OF ProtocolIE-Single-Container

--ContextGroupInfoItemIE-Reset RNSAP-PROTOCOL-IES ::= {
--	{ID id-ContextGroupInfoItem-Reset		CRITICALITY reject		TYPE ContextGroupInfoItem-Reset		PRESENCE mandatory}
--}

ContextGroupInfoItem-Reset ::= SEQUENCE {
	s-RNTI-Group				S-RNTI-Group,
--	iE-Extensions				ProtocolExtensionContainer  { { ContextGroupInfoItem-Reset-ExtIEs} }		OPTIONAL,
	iE-Extensions				ProtocolExtensionContainer  OPTIONAL,
	...
}

--ContextGroupInfoItem-Reset-ExtIEs RNSAP-PROTOCOL-EXTENSION ::= {
--	...
--}

-- **************************************************************
--
-- RESET RESPONSE
--
-- **************************************************************
--ResetResponse ::= SEQUENCE {
--	protocolIEs				ProtocolIE-Container	{{ResetResponse-IEs}},
--	protocolExtensions		ProtocolExtensionContainer	{{ResetResponse-Extensions}}     		OPTIONAL,
--	...
--}
ResetResponse ::= SEQUENCE {
	protocolIEs				ProtocolIE-Container,
	protocolExtensions		ProtocolExtensionContainer	OPTIONAL,
	...
}

--ResetResponse-IEs RNSAP-PROTOCOL-IES ::= {
--	{ ID id-RNC-ID				CRITICALITY ignore	TYPE RNC-ID		PRESENCE mandatory} |
--	{ ID id-CriticalityDiagnostics		CRITICALITY		ignore		TYPE	CriticalityDiagnostics		PRESENCE	optional},
--	...
--}

--ResetResponse-Extensions RNSAP-PROTOCOL-EXTENSION ::= {
--	...
--}

-- **************************************************************
--
-- RADIO LINK ACTIVATION COMMAND FDD
--
-- **************************************************************

--RadioLinkActivationCommandFDD ::= SEQUENCE {
--	protocolIEs				ProtocolIE-Container	{{RadioLinkActivationCommandFDD-IEs}},
--	protocolExtensions		ProtocolExtensionContainer	{{RadioLinkActivationCommandFDD-Extensions}}			OPTIONAL,
--	...
--}
RadioLinkActivationCommandFDD ::= SEQUENCE {
	protocolIEs				ProtocolIE-Container,
	protocolExtensions		ProtocolExtensionContainer	OPTIONAL,
	...
}

--RadioLinkActivationCommandFDD-IEs RNSAP-PROTOCOL-IES ::= {
--	{ ID id-DelayedActivationList-RL-ActivationCmdFDD		CRITICALITY	ignore	TYPE	DelayedActivationInformationList-RL-ActivationCmdFDD			PRESENCE	mandatory	},
--	...
--}

--RadioLinkActivationCommandFDD-Extensions RNSAP-PROTOCOL-EXTENSION ::= {
--	...
--}

DelayedActivationInformationList-RL-ActivationCmdFDD ::= SEQUENCE (SIZE (1..16)) OF ProtocolIE-Single-Container 
--DelayedActivationInformationList-RL-ActivationCmdFDD ::= SEQUENCE (SIZE (1..maxNrOfRLs)) OF ProtocolIE-Single-Container { 
--	{ DelayedActivationInformation-RL-ActivationCmdFDD-IEs} }

--DelayedActivationInformation-RL-ActivationCmdFDD-IEs RNSAP-PROTOCOL-IES ::= {
--	{ ID id-DelayedActivationInformation-RL-ActivationCmdFDD	CRITICALITY ignore	TYPE DelayedActivationInformation-RL-ActivationCmdFDD	PRESENCE optional	}
--}

DelayedActivationInformation-RL-ActivationCmdFDD ::= SEQUENCE {
	rL-ID						RL-ID,
	delayed-activation-update	DelayedActivationUpdate,
--	iE-Extensions				ProtocolExtensionContainer { { DelayedActivationInformation-RL-ActivationCmdFDD-ExtIEs} } OPTIONAL,
	iE-Extensions				ProtocolExtensionContainer OPTIONAL,
	...
}

--DelayedActivationInformation-RL-ActivationCmdFDD-ExtIEs RNSAP-PROTOCOL-EXTENSION ::= {
--	...
--}

-- **************************************************************
--
-- RADIO LINK ACTIVATION COMMAND TDD
--
-- **************************************************************
--RadioLinkActivationCommandTDD ::= SEQUENCE {
--	protocolIEs				ProtocolIE-Container	{{RadioLinkActivationCommandTDD-IEs}},
--	protocolExtensions		ProtocolExtensionContainer	{{RadioLinkActivationCommandTDD-Extensions}}			OPTIONAL,
--	...
--}
RadioLinkActivationCommandTDD ::= SEQUENCE {
	protocolIEs				ProtocolIE-Container,
	protocolExtensions		ProtocolExtensionContainer	OPTIONAL,
	...
}

--RadioLinkActivationCommandTDD-IEs RNSAP-PROTOCOL-IES ::= {
--	{ ID id-DelayedActivationList-RL-ActivationCmdTDD		CRITICALITY	ignore	TYPE	DelayedActivationInformationList-RL-ActivationCmdTDD			PRESENCE	mandatory	},
--	...
--}

--RadioLinkActivationCommandTDD-Extensions RNSAP-PROTOCOL-EXTENSION ::= {
--	...
--}

DelayedActivationInformationList-RL-ActivationCmdTDD ::= SEQUENCE (SIZE (1..16)) OF ProtocolIE-Single-Container  
--DelayedActivationInformationList-RL-ActivationCmdTDD ::= SEQUENCE (SIZE (1..maxNrOfRLs)) OF ProtocolIE-Single-Container { 
--	{ DelayedActivationInformation-RL-ActivationCmdTDD-IEs} }

--DelayedActivationInformation-RL-ActivationCmdTDD-IEs RNSAP-PROTOCOL-IES ::= {
--	{ ID id-DelayedActivationInformation-RL-ActivationCmdTDD	CRITICALITY ignore	TYPE DelayedActivationInformation-RL-ActivationCmdTDD	PRESENCE optional	}
--}

DelayedActivationInformation-RL-ActivationCmdTDD ::= SEQUENCE {
	rL-ID						RL-ID,
	delayed-activation-update	DelayedActivationUpdate,
--	iE-Extensions				ProtocolExtensionContainer { { DelayedActivationInformation-RL-ActivationCmdTDD-ExtIEs} } OPTIONAL,
	iE-Extensions				ProtocolExtensionContainer OPTIONAL,
	...
}

--DelayedActivationInformation-RL-ActivationCmdTDD-ExtIEs RNSAP-PROTOCOL-EXTENSION ::= {
--	...
--}
-- **************************************************************
--
-- GERAN UPLINK SIGNALLING TRANSFER INDICATION
--
-- **************************************************************

--GERANUplinkSignallingTransferIndication ::= SEQUENCE {
--	protocolIEs                     ProtocolIE-Container       {{GERANUplinkSignallingTransferIndication-IEs}},
--	protocolExtensions              ProtocolExtensionContainer {{GERANUplinkSignallingTransferIndication-Extensions}}	OPTIONAL,
--	...
--}
GERANUplinkSignallingTransferIndication ::= SEQUENCE {
	protocolIEs                     ProtocolIE-Container,
	protocolExtensions              ProtocolExtensionContainer OPTIONAL,
	...
}

--GERANUplinkSignallingTransferIndication-IEs RNSAP-PROTOCOL-IES ::= {
--	{ ID id-UC-ID						CRITICALITY ignore	TYPE UC-ID							PRESENCE mandatory	}	| 
	-- UC-Id may be GERAN cell identifier.
--	{ ID id-SAI							CRITICALITY ignore	TYPE SAI							PRESENCE mandatory	}	|
--	{ ID id-S-RNTI						CRITICALITY ignore	TYPE S-RNTI							PRESENCE mandatory	}	|
--	{ ID id-D-RNTI						CRITICALITY ignore	TYPE D-RNTI							PRESENCE optional	}	|
--	{ ID id-L3-Information				CRITICALITY ignore	TYPE L3-Information					PRESENCE mandatory	}	|
--	{ ID id-CN-PS-DomainIdentifier		CRITICALITY ignore	TYPE CN-PS-DomainIdentifier			PRESENCE optional	} 	|
--	{ ID id-CN-CS-DomainIdentifier		CRITICALITY ignore	TYPE CN-CS-DomainIdentifier			PRESENCE optional	} 	|
--	{ ID id-URA-Information				CRITICALITY ignore	TYPE URA-Information				PRESENCE optional	}, 
	-- URA information may be GRA information
--	...
--}

--GERANUplinkSignallingTransferIndication-Extensions RNSAP-PROTOCOL-EXTENSION ::= {
--	...
--}

-- **************************************************************
--
-- RADIO LINK PARAMETER UPDATE INDICATION FDD
--
-- **************************************************************

--RadioLinkParameterUpdateIndicationFDD ::= SEQUENCE {
--	protocolIEs				ProtocolIE-Container	{{RadioLinkParameterUpdateIndicationFDD-IEs}},
--	protocolExtensions		ProtocolExtensionContainer	{{RadioLinkParameterUpdateIndicationFDD-Extensions}}		OPTIONAL,
--	...
--}
RadioLinkParameterUpdateIndicationFDD ::= SEQUENCE {
	protocolIEs				ProtocolIE-Container,
	protocolExtensions		ProtocolExtensionContainer	OPTIONAL,
	...
}

--RadioLinkParameterUpdateIndicationFDD-IEs RNSAP-PROTOCOL-IES ::= {
--	{ ID	id-HSDSCH-FDD-Update-Information						CRITICALITY ignore	TYPE	HSDSCH-FDD-Update-Information			PRESENCE	optional}|
--	{ ID	id-RL-ParameterUpdateIndicationFDD-RL-InformationList	CRITICALITY ignore	TYPE	RL-ParameterUpdateIndicationFDD-RL-InformationList		PRESENCE optional	},
--	...
--}

--RL-ParameterUpdateIndicationFDD-RL-InformationList ::= SEQUENCE (SIZE (1..maxNrOfRLs)) OF ProtocolIE-Single-Container { { RL-ParameterUpdateIndicationFDD-RL-InformationList-IEs} }
RL-ParameterUpdateIndicationFDD-RL-InformationList ::= SEQUENCE (SIZE (1..16)) OF ProtocolIE-Single-Container

--RL-ParameterUpdateIndicationFDD-RL-InformationList-IEs RNSAP-PROTOCOL-IES ::= {
--	{ ID id-RL-ParameterUpdateIndicationFDD-RL-Information-Item		CRITICALITY ignore	TYPE RL-ParameterUpdateIndicationFDD-RL-Information-Item		PRESENCE mandatory	}
--}

RL-ParameterUpdateIndicationFDD-RL-Information-Item::= SEQUENCE {
	rL-ID								RL-ID,
	phase-Reference-Update-Indicator	Phase-Reference-Update-Indicator	OPTIONAL,
--	iE-Extensions						ProtocolExtensionContainer { { RL-ParameterUpdateIndicationFDD-RL-Information-ExtIEs} } OPTIONAL,
	iE-Extensions						ProtocolExtensionContainer OPTIONAL,
	...
}

--RL-ParameterUpdateIndicationFDD-RL-Information-ExtIEs RNSAP-PROTOCOL-EXTENSION ::= {
--	...
--}

--RadioLinkParameterUpdateIndicationFDD-Extensions RNSAP-PROTOCOL-EXTENSION ::= {
--	...
--}

-- **************************************************************
--
-- RADIO LINK PARAMETER UPDATE INDICATION TDD
--
-- **************************************************************

--RadioLinkParameterUpdateIndicationTDD ::= SEQUENCE {
--	protocolIEs				ProtocolIE-Container	{{RadioLinkParameterUpdateIndicationTDD-IEs}},
--	protocolExtensions		ProtocolExtensionContainer	{{RadioLinkParameterUpdateIndicationTDD-Extensions}}		OPTIONAL,
--	...
--}

RadioLinkParameterUpdateIndicationTDD ::= SEQUENCE {
	protocolIEs				ProtocolIE-Container,
	protocolExtensions		ProtocolExtensionContainer OPTIONAL,
	...
}
--RadioLinkParameterUpdateIndicationTDD-IEs RNSAP-PROTOCOL-IES ::= {
--	{ ID	id-HSDSCH-TDD-Update-Information		CRITICALITY		ignore		TYPE	HSDSCH-TDD-Update-Information			PRESENCE	optional},
--	...
--}

--RadioLinkParameterUpdateIndicationTDD-Extensions RNSAP-PROTOCOL-EXTENSION ::= {
--	...
--}

-- **************************************************************
--
-- UE MEASUREMENT INITIATION REQUEST
--
-- **************************************************************

--UEMeasurementInitiationRequest ::= SEQUENCE {
--	protocolIEs                     ProtocolIE-Container       {{UEMeasurementInitiationRequest-IEs}},
--	protocolExtensions              ProtocolExtensionContainer {{UEMeasurementInitiationRequest-Extensions}}                   OPTIONAL,
--	...
--}
UEMeasurementInitiationRequest ::= SEQUENCE {
	protocolIEs                     ProtocolIE-Container,
	protocolExtensions              ProtocolExtensionContainer OPTIONAL,
	...
}


--UEMeasurementInitiationRequest-IEs RNSAP-PROTOCOL-IES ::= {
--	{ ID id-AllowedQueuingTime					CRITICALITY reject	TYPE AllowedQueuingTime 						PRESENCE optional		} |
--	{ ID id-MeasurementID						CRITICALITY reject	TYPE MeasurementID								PRESENCE mandatory	} |
--	{ ID id-UEMeasurementType					CRITICALITY reject	TYPE UEMeasurementType							PRESENCE mandatory	} |
--	{ ID id-UEMeasurementTimeslotInfoHCR		CRITICALITY reject	TYPE UEMeasurementTimeslotInfoHCR			PRESENCE optional		} |
--	{ ID id-UEMeasurementTimeslotInfoLCR		CRITICALITY reject	TYPE UEMeasurementTimeslotInfoLCR			PRESENCE optional		} |
--	{ ID id-MeasurementFilterCoefficient		CRITICALITY reject	TYPE MeasurementFilterCoefficient			PRESENCE optional		} |
--	{ ID id-UEMeasurementReportCharacteristics	CRITICALITY reject	TYPE UEMeasurementReportCharacteristics	PRESENCE mandatory	} |
--	{ ID id-UEMeasurementParameterModAllow		CRITICALITY reject  TYPE UEMeasurementParameterModAllow			PRESENCE mandatory	},
--	...
--}

--UEMeasurementInitiationRequest-Extensions RNSAP-PROTOCOL-EXTENSION ::= {
--	...
--}

-- **************************************************************
--
-- UE MEASUREMENT INITIATION RESPONSE
--
-- **************************************************************

--UEMeasurementInitiationResponse ::= SEQUENCE {
--	protocolIEs                     ProtocolIE-Container       {{UEMeasurementInitiationResponse-IEs}},
--	protocolExtensions              ProtocolExtensionContainer {{UEMeasurementInitiationResponse-Extensions}}                   OPTIONAL,
--	...
--}

UEMeasurementInitiationResponse ::= SEQUENCE {
	protocolIEs                     ProtocolIE-Container,
	protocolExtensions              ProtocolExtensionContainer OPTIONAL,
	...
}
--UEMeasurementInitiationResponse-IEs RNSAP-PROTOCOL-IES ::= {
--	{ ID id-MeasurementID						CRITICALITY ignore	TYPE MeasurementID								PRESENCE mandatory	} |
--	{ ID id-MeasurementFilterCoefficient		CRITICALITY reject	TYPE MeasurementFilterCoefficient			PRESENCE optional		} |
--	{ ID id-UEMeasurementReportCharacteristics	CRITICALITY reject	TYPE UEMeasurementReportCharacteristics	PRESENCE optional		} |
--	{ ID id-CriticalityDiagnostics				CRITICALITY ignore	TYPE CriticalityDiagnostics						PRESENCE optional	},
--	...
--}

--UEMeasurementInitiationResponse-Extensions RNSAP-PROTOCOL-EXTENSION ::= {
--	...
--}

-- **************************************************************
--
-- UE MEASUREMENT INITIATION FAILURE
--
-- **************************************************************

--UEMeasurementInitiationFailure ::= SEQUENCE {
--	protocolIEs                     ProtocolIE-Container       {{UEMeasurementInitiationFailure-IEs}},
--	protocolExtensions              ProtocolExtensionContainer {{UEMeasurementInitiationFailure-Extensions}}                   OPTIONAL,
--	...
--}
UEMeasurementInitiationFailure ::= SEQUENCE {
	protocolIEs                     ProtocolIE-Container,
	protocolExtensions              ProtocolExtensionContainer OPTIONAL,
	...
}

--UEMeasurementInitiationFailure-IEs RNSAP-PROTOCOL-IES ::= {
--	{ ID id-MeasurementID					CRITICALITY ignore	TYPE MeasurementID						PRESENCE mandatory	} |
--	{ ID id-Cause							CRITICALITY ignore	TYPE Cause								PRESENCE mandatory	} |
--	{ ID id-CriticalityDiagnostics			CRITICALITY ignore	TYPE CriticalityDiagnostics				PRESENCE optional	},
--	...
--}

--UEMeasurementInitiationFailure-Extensions RNSAP-PROTOCOL-EXTENSION ::= {
--	...
--}

-- **************************************************************
--
-- UE MEASUREMENT REPORT
--
-- **************************************************************

--UEMeasurementReport ::= SEQUENCE {
--	protocolIEs                     ProtocolIE-Container       {{UEMeasurementReport-IEs}},
--	protocolExtensions              ProtocolExtensionContainer {{UEMeasurementReport-Extensions}}                   OPTIONAL,
--	...
--}
UEMeasurementReport ::= SEQUENCE {
	protocolIEs                     ProtocolIE-Container,
	protocolExtensions              ProtocolExtensionContainer OPTIONAL,
	...
}

--UEMeasurementReport-IEs RNSAP-PROTOCOL-IES ::= {
--	{ ID id-MeasurementID					CRITICALITY ignore	TYPE MeasurementID							PRESENCE mandatory	} |
--	{ ID id-UEMeasurementValueInformation	CRITICALITY ignore	TYPE UEMeasurementValueInformation		PRESENCE mandatory	},
--	...
--}

--UEMeasurementReport-Extensions RNSAP-PROTOCOL-EXTENSION ::= {
--	...
--}

-- **************************************************************
--
-- UE MEASUREMENT TERMINATION REQUEST
--
-- **************************************************************

--UEMeasurementTerminationRequest ::= SEQUENCE {
--	protocolIEs                     ProtocolIE-Container       {{UEMeasurementTerminationRequest-IEs}},
--	protocolExtensions              ProtocolExtensionContainer {{UEMeasurementTerminationRequest-Extensions}}                   OPTIONAL,
--	...
--}
UEMeasurementTerminationRequest ::= SEQUENCE {
	protocolIEs                     ProtocolIE-Container,
	protocolExtensions              ProtocolExtensionContainer OPTIONAL,
	...
}

--UEMeasurementTerminationRequest-IEs RNSAP-PROTOCOL-IES ::= {
--	{ ID id-MeasurementID				CRITICALITY ignore	TYPE MeasurementID				PRESENCE mandatory	},
--	...
--}

--UEMeasurementTerminationRequest-Extensions RNSAP-PROTOCOL-EXTENSION ::= {
--	...
--}

-- **************************************************************
--
-- UE MEASUREMENT FAILURE INDICATION
--
-- **************************************************************

--UEMeasurementFailureIndication ::= SEQUENCE {
--	protocolIEs                     ProtocolIE-Container       {{UEMeasurementFailureIndication-IEs}},
--	protocolExtensions              ProtocolExtensionContainer {{UEMeasurementFailureIndication-Extensions}}                   OPTIONAL,
--	...
--}
UEMeasurementFailureIndication ::= SEQUENCE {
	protocolIEs                     ProtocolIE-Container,
	protocolExtensions              ProtocolExtensionContainer OPTIONAL,
	...
}

--UEMeasurementFailureIndication-IEs RNSAP-PROTOCOL-IES ::= {
--	{ ID id-MeasurementID				CRITICALITY ignore	TYPE MeasurementID				PRESENCE mandatory	} |
--	{ ID id-Cause						CRITICALITY ignore	TYPE Cause						PRESENCE mandatory	},
--	...
--}

--UEMeasurementFailureIndication-Extensions RNSAP-PROTOCOL-EXTENSION ::= {
--	...
--}
-- **************************************************************
--
-- IUR INVOKE TRACE
--
-- **************************************************************

--IurInvokeTrace ::= SEQUENCE {
--	protocolIEs									ProtocolIE-Container		{{IurInvokeTrace-IEs}},
--	protocolExtensions							ProtocolExtensionContainer	{{IurInvokeTrace-Extensions}}		OPTIONAL,
--	...
--}
IurInvokeTrace ::= SEQUENCE {
	protocolIEs									ProtocolIE-Container,
	protocolExtensions							ProtocolExtensionContainer	OPTIONAL,
	...
}
--IurInvokeTrace-IEs RNSAP-PROTOCOL-IES ::= {
--	{ ID id-D-RNTI								CRITICALITY ignore	TYPE D-RNTI										PRESENCE optional		}|
--	{ ID id-TraceReference						CRITICALITY ignore	TYPE TraceReference								PRESENCE mandatory	}|
--	{ ID id-UEIdentity							CRITICALITY ignore	TYPE UEIdentity									PRESENCE mandatory	}|
--	{ ID id-TraceRecordingSessionReference		CRITICALITY ignore	TYPE TraceRecordingSessionReference			PRESENCE mandatory	}|
--	{ ID id-ListOfInterfacesToTrace				CRITICALITY ignore	TYPE ListOfInterfacesToTrace					PRESENCE optional		}|
--	{ ID id-TraceDepth							CRITICALITY ignore	TYPE TraceDepth									PRESENCE mandatory	},
--	...
--}

--ListOfInterfacesToTrace ::= SEQUENCE (SIZE (1..maxNrOfInterfaces)) OF ProtocolIE-Single-Container {{ InterfacesToBeTracedItemIE }}
ListOfInterfacesToTrace ::= SEQUENCE (SIZE (1..16)) OF ProtocolIE-Single-Container

--InterfacesToBeTracedItemIE RNSAP-PROTOCOL-IES ::= {
--	{ ID id-InterfacesToTraceItem				CRITICALITY ignore	TYPE InterfacesToTraceItem						PRESENCE mandatory	}
--}

InterfacesToTraceItem ::= SEQUENCE {
	interface				ENUMERATED {iub,iur,...},
--	iE-Extensions			ProtocolExtensionContainer { {InterfacesToTraceItem-ExtIEs} }	OPTIONAL,
	iE-Extensions			ProtocolExtensionContainer OPTIONAL,
	...
}

--InterfacesToTraceItem-ExtIEs RNSAP-PROTOCOL-EXTENSION ::= {
--	...
--}


--IurInvokeTrace-Extensions RNSAP-PROTOCOL-EXTENSION ::= {
--	...
--}
-- **************************************************************
--
-- IUR DEACTIVATE TRACE
--
-- **************************************************************

--IurDeactivateTrace ::= SEQUENCE {
--	protocolIEs									ProtocolIE-Container		{{IurDeactivateTrace-IEs}},
--	protocolExtensions							ProtocolExtensionContainer	{{IurDeactivateTrace-Extensions}}	OPTIONAL,
--	...
--}
IurDeactivateTrace ::= SEQUENCE {
	protocolIEs									ProtocolIE-Container,
	protocolExtensions							ProtocolExtensionContainer	OPTIONAL,
	...
}

--IurDeactivateTrace-IEs RNSAP-PROTOCOL-IES ::= {
--	{ ID id-D-RNTI								CRITICALITY ignore	TYPE D-RNTI										PRESENCE optional		}|
--	{ ID id-TraceReference						CRITICALITY ignore	TYPE TraceReference								PRESENCE mandatory	},
--	...
--}

--IurDeactivateTrace-Extensions RNSAP-PROTOCOL-EXTENSION ::= {
--	...
--}
-- **************************************************************
--
-- MBMS ATTACH COMMAND
--
-- **************************************************************

--MBMSAttachCommand ::= SEQUENCE {
--	protocolIEs				ProtocolIE-Container	{{MBMSAttachCommand-IEs}},
--	protocolExtensions		ProtocolExtensionContainer	{{MBMSAttachCommand-Extensions}}		OPTIONAL,
--	...
--}
MBMSAttachCommand ::= SEQUENCE {
	protocolIEs				ProtocolIE-Container,
	protocolExtensions		ProtocolExtensionContainer	OPTIONAL,
	...
}

--MBMSAttachCommand-IEs RNSAP-PROTOCOL-IES ::= {
--	{ ID id-MBMS-Bearer-Service-List		CRITICALITY		ignore		TYPE MBMS-Bearer-Service-List PRESENCE	mandatory} |
--	{ ID id-UE-State						CRITICALITY		ignore		TYPE	UE-State				PRESENCE	optional},
--	...
--}

--MBMSAttachCommand-Extensions RNSAP-PROTOCOL-EXTENSION ::= {
--	...
--}

-- **************************************************************
--
-- MBMS DETACH COMMAND
--
-- **************************************************************

--MBMSDetachCommand ::= SEQUENCE {
--	protocolIEs				ProtocolIE-Container	{{MBMSDetachCommand-IEs}},
--	protocolExtensions		ProtocolExtensionContainer	{{MBMSDetachCommand-Extensions}}		OPTIONAL,
--	...
--}
MBMSDetachCommand ::= SEQUENCE {
	protocolIEs				ProtocolIE-Container,
	protocolExtensions		ProtocolExtensionContainer	OPTIONAL,
	...
}

--MBMSDetachCommand-IEs RNSAP-PROTOCOL-IES ::= {
--	{ ID id-MBMS-Bearer-Service-List 	CRITICALITY		ignore		TYPE MBMS-Bearer-Service-List PRESENCE	mandatory} |
--	{ ID id-UE-State					CRITICALITY		ignore		TYPE	UE-State				PRESENCE	optional},
--	...
--}

--MBMSDetachCommand-Extensions RNSAP-PROTOCOL-EXTENSION ::= {
--	...
--}

-- **************************************************************
--
-- DIRECT INFORMATION TRANSFER
--
-- **************************************************************

--DirectInformationTransfer ::= SEQUENCE {
--	protocolIEs				ProtocolIE-Container		{{DirectInformationTransfer-IEs}},
--	protocolExtensions		ProtocolExtensionContainer	{{DirectInformationTransfer-Extensions}}		OPTIONAL,
--	...
--}
DirectInformationTransfer ::= SEQUENCE {
	protocolIEs				ProtocolIE-Container,
	protocolExtensions		ProtocolExtensionContainer OPTIONAL,
	...
}
--DirectInformationTransfer-IEs RNSAP-PROTOCOL-IES ::= {
--	{ ID id-RNC-ID								CRITICALITY ignore 	TYPE RNC-ID									PRESENCE mandatory} |
--	{ ID id-ProvidedInformation					CRITICALITY ignore 	TYPE ProvidedInformation					PRESENCE mandatory} ,
--	...
--}

--DirectInformationTransfer-Extensions RNSAP-PROTOCOL-EXTENSION ::= {
--	...
--}


-- **************************************************************
--
-- PRIVATE MESSAGE
--
-- **************************************************************

PrivateMessage ::= SEQUENCE {
--	privateIEs		PrivateIE-Container  {{PrivateMessage-IEs}},
	privateIEs		PrivateIE-Container,
	...
}

--PrivateMessage-IEs RNSAP-PRIVATE-IES ::= {
--	...
--}

--END

--9.3.4	Information Element Definitions
-- **************************************************************
--
-- Information Element Definitions
--
-- **************************************************************

--RNSAP-IEs {
--itu-t (0) identified-organization (4) etsi (0) mobileDomain (0) 
--umts-Access (20) modules (3) rnsap (1) version1 (1) rnsap-IEs (2) }

--DEFINITIONS AUTOMATIC TAGS ::= 

--BEGIN

--IMPORTS
-- :
-- :
-- FROM RNSAP-Containers;

-- A

AccessPointName		::= OCTET STRING (SIZE (1..255))

AckNack-RepetitionFactor ::= INTEGER (1..4,...)
-- Step: 1

Ack-Power-Offset ::= INTEGER (0..8,...)
-- According to mapping in ref. [21] subclause 4.2.1

Active-MBMS-Bearer-Service-ListFDD	::= SEQUENCE (SIZE (1..256)) OF MBMS-Bearer-ServiceItemFDD

Active-MBMS-Bearer-Service-ListFDD-PFL	::= SEQUENCE (SIZE (1..256)) OF MBMS-Bearer-ServiceItemFDD-PFL

Active-MBMS-Bearer-Service-ListTDD	::= SEQUENCE (SIZE (1..256)) OF MBMS-Bearer-ServiceItemTDD

Active-MBMS-Bearer-Service-ListTDD-PFL	::= SEQUENCE (SIZE (1..256)) OF MBMS-Bearer-ServiceItemTDD-PFL

Active-Pattern-Sequence-Information ::= SEQUENCE {
	cMConfigurationChangeCFN		CFN,
	transmission-Gap-Pattern-Sequence-Status	Transmission-Gap-Pattern-Sequence-Status-List		OPTIONAL,
--	iE-Extensions		ProtocolExtensionContainer { {Active-Pattern-Sequence-Information-ExtIEs} } OPTIONAL,
	iE-Extensions		ProtocolExtensionContainer OPTIONAL,
	...
}

--Active-Pattern-Sequence-Information-ExtIEs RNSAP-PROTOCOL-EXTENSION ::= {
--	...
--}

AdditionalPreferredFrequency	::= SEQUENCE (SIZE (1..8)) OF AdditionalPreferredFrequencyItem

AdditionalPreferredFrequencyItem ::= SEQUENCE {
	dL-UARFCN						UARFCN,
	correspondingCells				CorrespondingCells	,
--	iE-Extensions					ProtocolExtensionContainer { { AdditionalPreferredFrequencyItem-ExtIEs} } OPTIONAL,
	iE-Extensions					ProtocolExtensionContainer OPTIONAL,
	...
}


--AdditionalPreferredFrequencyItem-ExtIEs RNSAP-PROTOCOL-EXTENSION ::= {
--	...
--}

AdjustmentPeriod			::= INTEGER(1..256)
-- Unit Frame

AffectedUEInformationForMBMS	::= SEQUENCE (SIZE (1..4096)) OF S-RNTI

AllocationRetentionPriority ::= SEQUENCE {
	priorityLevel				PriorityLevel,
	pre-emptionCapability		Pre-emptionCapability,
	pre-emptionVulnerability	Pre-emptionVulnerability,
--	iE-Extensions			ProtocolExtensionContainer { {AllocationRetentionPriority-ExtIEs} } OPTIONAL,
	iE-Extensions			ProtocolExtensionContainer OPTIONAL,
	...
}

--AllocationRetentionPriority-ExtIEs RNSAP-PROTOCOL-EXTENSION ::= {
--	...
--}

Allowed-Rate-Information	::= SEQUENCE {
	allowed-UL-Rate			Allowed-Rate OPTIONAL,
	allowed-DL-Rate			Allowed-Rate OPTIONAL,
--	iE-Extensions			ProtocolExtensionContainer { {Allowed-Rate-Information-ExtIEs} } OPTIONAL,
	iE-Extensions			ProtocolExtensionContainer OPTIONAL,
	...
}

--Allowed-Rate-Information-ExtIEs RNSAP-PROTOCOL-EXTENSION ::= {
--	...
--}

Allowed-Rate			::= INTEGER (1..32)
-- "1": TFI 0, "2": TFI 1, "3": TFI 2, ...

AllowedQueuingTime			::= INTEGER (1..60)
-- seconds

AlphaValue					::=	INTEGER (0..8)
-- Actual value = Alpha / 8

Angle-Of-Arrival-Value-LCR ::= SEQUENCE {
	aOA-LCR					AOA-LCR,
	aOA-LCR-Accuracy-Class	AOA-LCR-Accuracy-Class,
--	iE-Extensions			ProtocolExtensionContainer { {Angle-Of-Arrival-Value-LCR-ExtIEs} } OPTIONAL,
	iE-Extensions			ProtocolExtensionContainer OPTIONAL,
...
}

--Angle-Of-Arrival-Value-LCR-ExtIEs RNSAP-PROTOCOL-EXTENSION ::= {
--	...
--}

AOA-LCR ::= INTEGER (0..719)
-- Angle Of Arrival for 1.28Mcps TDD

AOA-LCR-Accuracy-Class	::= ENUMERATED {a,b,c,d,e,f,g,h,...}

AntennaColocationIndicator ::= ENUMERATED {
	co-located,
	...
}

-- B

BadSatellites ::= SEQUENCE {
	badSatelliteInformation		SEQUENCE (SIZE (1..16)) OF
		SEQUENCE {
			badSAT-ID					SAT-ID,
--			iE-Extensions				ProtocolExtensionContainer { { BadSatelliteInformation-ExtIEs} }		OPTIONAL,
			iE-Extensions				ProtocolExtensionContainer OPTIONAL,
			...
		},
--	iE-Extensions				ProtocolExtensionContainer { { BadSatellites-ExtIEs} }		OPTIONAL,
	iE-Extensions				ProtocolExtensionContainer OPTIONAL,
	...
}

--BadSatelliteInformation-ExtIEs RNSAP-PROTOCOL-EXTENSION ::= {
--	...
--}

--BadSatellites-ExtIEs RNSAP-PROTOCOL-EXTENSION ::= {
--	...
--}

Band-Indicator ::= ENUMERATED {
	dcs1800Band,
	pcs1900Band,
	...
}

BCC ::= BIT STRING (SIZE (3))

BCCH-ARFCN ::= INTEGER (0..1023)

BetaCD ::= INTEGER (0..15)

BindingID				::= OCTET STRING (SIZE (1..4,...))
-- If the Binding ID includes an UDP port, the UDP port is included in octet 1 and 2.

BLER					::= INTEGER (-63..0)
-- Step 0.1 (Range -6.3..0). It is the Log10 of the BLER

SCTD-Indicator	::= ENUMERATED {
	active,
	inactive
}

BSIC ::= SEQUENCE {
	nCC			NCC,
	bCC			BCC
}

BundlingModeIndicator ::= ENUMERATED {
	bundling,
	no-bundling
}

BurstModeParameters ::= SEQUENCE {
	burstStart		INTEGER (0..15),
	burstLength		INTEGER (10..25),
	burstFreq		INTEGER (1..16),
--	iE-Extensions				ProtocolExtensionContainer { { BurstModeParameters-ExtIEs} }		OPTIONAL,
	iE-Extensions				ProtocolExtensionContainer OPTIONAL,
	...
}

--BurstModeParameters-ExtIEs RNSAP-PROTOCOL-EXTENSION ::= {
--	...
--}

-- C

Cause ::= CHOICE {
	radioNetwork		CauseRadioNetwork,
	transport			CauseTransport,
	protocol			CauseProtocol,
	misc				CauseMisc,
	...
}

CauseMisc ::= ENUMERATED {
	control-processing-overload,
	hardware-failure,
	om-intervention,
	not-enough-user-plane-processing-resources,
	unspecified,
	...
}

CauseProtocol ::= ENUMERATED {
	transfer-syntax-error,
	abstract-syntax-error-reject,
	abstract-syntax-error-ignore-and-notify,
	message-not-compatible-with-receiver-state,
	semantic-error,
	unspecified,
	abstract-syntax-error-falsely-constructed-message,
	...
}

CauseRadioNetwork ::= ENUMERATED {
	unknown-C-ID,
	cell-not-available,
	power-level-not-supported,
	ul-scrambling-code-already-in-use,
	dl-radio-resources-not-available,
	ul-radio-resources-not-available,
	measurement-not-supported-for-the-object,
	combining-resources-not-available,
	combining-not-supported,
	reconfiguration-not-allowed,
	requested-configuration-not-supported,
	synchronisation-failure,
	requested-tx-diversity-mode-not-supported,
	measurement-temporaily-not-available,
	unspecified,
	invalid-CM-settings,
	reconfiguration-CFN-not-elapsed,
	number-of-DL-codes-not-supported,
	dedicated-transport-channel-type-not-supported,
	dl-shared-channel-type-not-supported,
	ul-shared-channel-type-not-supported,
	common-transport-channel-type-not-supported,
	ul-spreading-factor-not-supported,
	dl-spreading-factor-not-supported,
	cm-not-supported,
	transaction-not-supported-by-destination-node-b,
	rl-already-activated-or-alocated,
	...,
    number-of-UL-codes-not-supported,
	cell-reserved-for-operator-use,
	dpc-mode-change-not-supported,
	information-temporarily-not-available,
	information-provision-not-supported-for-the-object,
	power-balancing-status-not-compatible,
	delayed-activation-not-supported,
	rl-timing-adjustment-not-supported,
	unknown-RNTI,
	measurement-repetition-rate-not-compatible,
	ue-not-capable-of-support,
	f-dpch-not-supported
}

CauseTransport ::= ENUMERATED {
	transport-resource-unavailable,
	unspecified,
	...
}

CellCapabilityContainer-FDD ::= BIT STRING (SIZE (32))
-- First bit: Flexible Hard Split Support Indicator
-- Second bit: Delayed Activation Support Indicator
-- Third bit: HS-DSCH Support Indicator
-- Fourth bit: DSCH Support Indicator
-- Fifth bit: F-DPCH Support Indicator
-- sixth bit: E-DCH Support Indicator
-- Note that undefined bits are considered as a spare bit and spare bits shall be set to 0 by the transmitter and shall be ignored by the receiver.

CellCapabilityContainer-TDD ::= BIT STRING (SIZE (32))
-- First bit: Delayed Activation Support Indicator
-- Second bit: HS-DSCH Support Indicator
-- Third bit: DSCH Support Indicator
-- Note that undefined bits are considered as a spare bit and spare bits shall be set to 0 by the transmitter and shall be ignored by the receiver.

CellCapabilityContainer-TDD-LCR ::= BIT STRING (SIZE (32))
-- First bit: Delayed Activation Support Indicator
-- Second bit: HS-DSCH Support Indicator
-- Third bit: DSCH Support Indicator
-- Note that undefined bits are considered as a spare bit and spare bits shall be set to 0 by the transmitter and shall be ignored by the receiver.

C-ID					::= INTEGER (0..65535)

CCTrCH-ID				::= INTEGER (0..15)

Cell-Capacity-Class-Value ::= SEQUENCE {
		uplinkCellCapacityClassValue		INTEGER(1..100,...),
		downlinkCellCapacityClassValue		INTEGER(1..100,...)
}


CellIndividualOffset	::= INTEGER (-20..20)

CellParameterID				::= INTEGER (0..127,...)

CellPortionID	::= INTEGER (0..63,...)

CFN					::= INTEGER (0..255)

CGI ::= SEQUENCE {
	lAI			SEQUENCE {
		pLMN-Identity	PLMN-Identity,
		lAC				LAC,
--		iE-Extensions			ProtocolExtensionContainer { {LAI-ExtIEs} } OPTIONAL,
		iE-Extensions			ProtocolExtensionContainer OPTIONAL,
		...
	},
	cI				CI,
--	iE-Extensions			ProtocolExtensionContainer { {CGI-ExtIEs} } OPTIONAL
	iE-Extensions			ProtocolExtensionContainer OPTIONAL
}

--LAI-ExtIEs RNSAP-PROTOCOL-EXTENSION ::= {
--	...
--}

--CGI-ExtIEs RNSAP-PROTOCOL-EXTENSION ::= {
--	...
--}

ChannelCodingType ::= ENUMERATED {
	no-codingTDD,
	convolutional-coding,
	turbo-coding,
	...
}

ChipOffset				::= INTEGER (0..38399)

CI					::= OCTET STRING (SIZE (2))

ClosedLoopMode1-SupportIndicator	::= ENUMERATED {
	closedLoop-Mode1-Supported,
	closedLoop-Mode1-not-Supported
}


Closedlooptimingadjustmentmode	::= ENUMERATED {
	adj-1-slot,
	adj-2-slot,
	...
}

CodingRate ::= ENUMERATED {
	half,
	third,
	...
}

CommonMeasurementAccuracy ::= CHOICE {
	tUTRANGPSMeasurementAccuracyClass		TUTRANGPSAccuracyClass,
	...
}

CommonMeasurementType ::= ENUMERATED {
	uTRAN-GPS-timing-of-cell-frames-for-UE-Positioning,
	sFN-SFN-observerd-time-difference,
	load,
	transmitted-carrier-power, 
	received-total-wide-band-power,
	uplink-timeslot-iscp,
	...,
	rT-load,
	nRT-load-Information,
	upPTSInterference
}
-- For measurements on the Iur-g interface, only load, RT Load and NRT Load information are requested.

CommonMeasurementValue ::= CHOICE {
	tUTRANGPSMeasurementValueInformation	TUTRANGPSMeasurementValueInformation,
	sFNSFNMeasurementValueInformation		SFNSFNMeasurementValueInformation,
	loadValue							LoadValue,
	transmittedCarrierPowerValue		INTEGER(0..100),
	receivedTotalWideBandPowerValue		INTEGER(0..621),
	uplinkTimeslotISCPValue				UL-TimeslotISCP,
	...,
	extension-CommonMeasurementValue	Extension-CommonMeasurementValue
}

--Extension-CommonMeasurementValue	::= ProtocolIE-Single-Container {{ Extension-CommonMeasurementValueIE }}
Extension-CommonMeasurementValue	::= ProtocolIE-Single-Container

--Extension-CommonMeasurementValueIE RNSAP-PROTOCOL-IES ::= {
--	{ ID id-RTLoadValue	CRITICALITY ignore	TYPE RTLoadValue	PRESENCE mandatory }|
--	{ ID id-NRTLoadInformationValue	CRITICALITY ignore	TYPE NRTLoadInformationValue	PRESENCE mandatory }|
--	{ ID id-UpPTSInterferenceValue		CRITICALITY reject	TYPE 	UpPTSInterferenceValue		PRESENCE mandatory }
--}

-- For measurements on the Iur-g interface, only load, RT Load and NRT Load values are reported. 

CommonMeasurementValueInformation ::= CHOICE {
	measurementAvailable		CommonMeasurementAvailable,
	measurementnotAvailable		NULL
}

CommonMeasurementAvailable::= SEQUENCE {
	commonMeasurementValue		CommonMeasurementValue,
--	iE-Extensions					ProtocolExtensionContainer { { CommonMeasurementAvailableItem-ExtIEs} }		OPTIONAL,
	iE-Extensions					ProtocolExtensionContainer OPTIONAL,
	...
}

--CommonMeasurementAvailableItem-ExtIEs RNSAP-PROTOCOL-EXTENSION ::= {
--	...
--}

CongestionCause ::= ENUMERATED {
	uTRAN-dynamic-resources,
	uTRAN-semistatic-resources,
	...
}

CommonTransportChannelResourcesInitialisationNotRequired ::= ENUMERATED {
	not-Required
}

CorrespondingCells	::= SEQUENCE (SIZE (1..65536)) OF C-ID


CoverageIndicator ::= ENUMERATED {
	overlap, 
	covers, 
	containedIn,
	...
}

CRC-Size 				::= ENUMERATED {
	v0,
	v8,
	v12,
	v16,
	v24,
	...
}

CriticalityDiagnostics ::= SEQUENCE {
	procedureID					ProcedureID			OPTIONAL,
	triggeringMessage			TriggeringMessage		OPTIONAL,
	procedureCriticality		Criticality				OPTIONAL,
	transactionID				TransactionID			OPTIONAL,
	iEsCriticalityDiagnostics		CriticalityDiagnostics-IE-List	OPTIONAL,
--	iE-Extensions				ProtocolExtensionContainer { {CriticalityDiagnostics-ExtIEs} } OPTIONAL,
	iE-Extensions				ProtocolExtensionContainer OPTIONAL,
	...
}

--CriticalityDiagnostics-ExtIEs RNSAP-PROTOCOL-EXTENSION ::= {
--	...
--}

CriticalityDiagnostics-IE-List ::= SEQUENCE (SIZE (1..256)) OF
	SEQUENCE {
		iECriticality			Criticality,
		iE-ID					ProtocolIE-ID,
		repetitionNumber		RepetitionNumber0		OPTIONAL,
--		iE-Extensions			ProtocolExtensionContainer { {CriticalityDiagnostics-IE-List-ExtIEs} } OPTIONAL,
		iE-Extensions			ProtocolExtensionContainer OPTIONAL,
		...
	}

--CriticalityDiagnostics-IE-List-ExtIEs RNSAP-PROTOCOL-EXTENSION ::= {
--{	ID id-MessageStructure		CRITICALITY ignore		EXTENSION MessageStructure		PRESENCE optional	}|
--{	ID id-TypeOfError			CRITICALITY ignore		EXTENSION TypeOfError			PRESENCE mandatory	},
--	...
--}

MessageStructure ::= SEQUENCE (SIZE (1..256)) OF
	SEQUENCE { 
		iE-ID					ProtocolIE-ID,
		repetitionNumber		RepetitionNumber1		OPTIONAL,
--		iE-Extensions			ProtocolExtensionContainer { {MessageStructure-ExtIEs} } OPTIONAL,
		iE-Extensions			ProtocolExtensionContainer OPTIONAL,
		...
	}


--MessageStructure-ExtIEs RNSAP-PROTOCOL-EXTENSION ::= {
--	...
--}

CN-CS-DomainIdentifier ::= SEQUENCE {
	pLMN-Identity		PLMN-Identity,
	lAC					LAC,
--	iE-Extensions		ProtocolExtensionContainer { {CN-CS-DomainIdentifier-ExtIEs} } OPTIONAL
	iE-Extensions		ProtocolExtensionContainer OPTIONAL
}

--CN-CS-DomainIdentifier-ExtIEs RNSAP-PROTOCOL-EXTENSION ::= {
--	...
--}

CN-PS-DomainIdentifier ::= SEQUENCE {
	pLMN-Identity		PLMN-Identity,
	lAC					LAC,
	rAC					RAC,
--	iE-Extensions		ProtocolExtensionContainer { {CN-PS-DomainIdentifier-ExtIEs} } OPTIONAL
	iE-Extensions		ProtocolExtensionContainer OPTIONAL
}

--CN-PS-DomainIdentifier-ExtIEs RNSAP-PROTOCOL-EXTENSION ::= {
--	...
--}

CNDomainType	::= ENUMERATED {
	cs-domain,
	ps-domain,
	dont-care,
	...
}
-- See in [16]

CQI-Feedback-Cycle ::= ENUMERATED {v0, v2, v4, v8, v10, v20, v40, v80, v160,...}

CQI-Power-Offset ::= INTEGER (0..8,...)
-- According to mapping in ref. [21] subclause 4.2.1

CQI-RepetitionFactor ::= INTEGER (1..4,...)
-- Step: 1

C-RNTI					::= INTEGER (0..65535)

-- D

DATA-ID ::= INTEGER (0..3)


DCH-FDD-Information		::= SEQUENCE (SIZE (1..128)) OF DCH-FDD-InformationItem

DCH-FDD-InformationItem ::= SEQUENCE {
	payloadCRC-PresenceIndicator		PayloadCRC-PresenceIndicator,
	ul-FP-Mode							UL-FP-Mode,
	toAWS								ToAWS,
	toAWE								ToAWE,
	dCH-SpecificInformationList			DCH-Specific-FDD-InformationList,
--	iE-Extensions						ProtocolExtensionContainer { {DCH-FDD-InformationItem-ExtIEs} } OPTIONAL,
	iE-Extensions						ProtocolExtensionContainer OPTIONAL,
	...
}

--DCH-FDD-InformationItem-ExtIEs RNSAP-PROTOCOL-EXTENSION ::= {
--	{ ID id-TnlQos			CRITICALITY 	ignore		EXTENSION 	TnlQos		PRESENCE 	optional	},
--	...
--}

DCH-Specific-FDD-InformationList ::= SEQUENCE (SIZE (1..128)) OF DCH-Specific-FDD-Item

DCH-Specific-FDD-Item ::=	SEQUENCE {
	dCH-ID								DCH-ID,
	trCH-SrcStatisticsDescr				TrCH-SrcStatisticsDescr,
	ul-transportFormatSet				TransportFormatSet,
	dl-transportFormatSet				TransportFormatSet,
	ul-BLER								BLER,
	dl-BLER								BLER,
	allocationRetentionPriority			AllocationRetentionPriority,
	frameHandlingPriority				FrameHandlingPriority,
	qE-Selector							QE-Selector,
	dRACControl							DRACControl,
--	iE-Extensions						ProtocolExtensionContainer { {DCH-FDD-SpecificItem-ExtIEs} } OPTIONAL,
	iE-Extensions						ProtocolExtensionContainer OPTIONAL,
	...
}

--DCH-FDD-SpecificItem-ExtIEs RNSAP-PROTOCOL-EXTENSION ::= {
--	{ ID id-Guaranteed-Rate-Information		CRITICALITY ignore	EXTENSION Guaranteed-Rate-Information		PRESENCE optional	}|
--	{ ID id-TrafficClass					CRITICALITY ignore	EXTENSION TrafficClass	PRESENCE mandatory}|
--	{ ID id-Unidirectional-DCH-Indicator	CRITICALITY reject	EXTENSION Unidirectional-DCH-Indicator		PRESENCE optional	},
--	...
--}

DCH-ID					::= INTEGER (0..255)

DCH-InformationResponse ::= SEQUENCE (SIZE (1..128)) OF DCH-InformationResponseItem

DCH-InformationResponseItem ::= SEQUENCE {
	dCH-ID						DCH-ID,
	bindingID					BindingID				OPTIONAL,
	transportLayerAddress		TransportLayerAddress	OPTIONAL,
--	iE-Extensions				ProtocolExtensionContainer { {DCH-InformationResponseItem-ExtIEs} } OPTIONAL,
	iE-Extensions				ProtocolExtensionContainer OPTIONAL,
	...
}

--DCH-InformationResponseItem-ExtIEs RNSAP-PROTOCOL-EXTENSION ::= {
--	{ ID id-Allowed-Rate-Information		CRITICALITY ignore	EXTENSION Allowed-Rate-Information		PRESENCE optional	},
--	...
--}

DCH-TDD-Information		::= SEQUENCE (SIZE (1..128)) OF DCH-TDD-InformationItem

DCH-TDD-InformationItem ::= SEQUENCE {
	payloadCRC-PresenceIndicator		PayloadCRC-PresenceIndicator,
	ul-FP-Mode							UL-FP-Mode,
	toAWS								ToAWS,
	toAWE								ToAWE,
	dCH-SpecificInformationList			DCH-Specific-TDD-InformationList,
--	iE-Extensions						ProtocolExtensionContainer { {DCH-TDD-InformationItem-ExtIEs} } OPTIONAL,
	iE-Extensions						ProtocolExtensionContainer OPTIONAL,
	...
}

--DCH-TDD-InformationItem-ExtIEs RNSAP-PROTOCOL-EXTENSION ::= {
--	{ ID id-TnlQos						CRITICALITY 	ignore		EXTENSION 	TnlQos		PRESENCE 	optional	},
--	...
--}

DCH-Specific-TDD-InformationList ::= SEQUENCE (SIZE (1..128)) OF DCH-Specific-TDD-Item

DCH-Specific-TDD-Item ::=	SEQUENCE {
	dCH-ID								DCH-ID,	
	ul-cCTrCH-ID						CCTrCH-ID, -- UL CCTrCH in which the DCH is mapped
	dl-cCTrCH-ID						CCTrCH-ID, -- DL CCTrCH in which the DCH is mapped
	trCH-SrcStatisticsDescr				TrCH-SrcStatisticsDescr,
	ul-transportFormatSet				TransportFormatSet,
	dl-transportFormatSet				TransportFormatSet,
	ul-BLER								BLER,
	dl-BLER								BLER,
	allocationRetentionPriority			AllocationRetentionPriority,
	frameHandlingPriority				FrameHandlingPriority,
	qE-Selector							QE-Selector			OPTIONAL,
	-- This IE shall be present if DCH is part of set of Co-ordinated DCHs
--	iE-Extensions						ProtocolExtensionContainer { {DCH-Specific-TDD-Item-ExtIEs} } OPTIONAL,
	iE-Extensions						ProtocolExtensionContainer OPTIONAL,
	...
}

--DCH-Specific-TDD-Item-ExtIEs RNSAP-PROTOCOL-EXTENSION ::= {
--	{ ID id-Guaranteed-Rate-Information		CRITICALITY ignore	EXTENSION Guaranteed-Rate-Information		PRESENCE optional	}|
--	{ ID id-TrafficClass					CRITICALITY ignore	EXTENSION TrafficClass 	PRESENCE mandatory}|
--	{ ID id-Unidirectional-DCH-Indicator	CRITICALITY reject	EXTENSION Unidirectional-DCH-Indicator		PRESENCE optional	},
--	...
--}

DedicatedMeasurementType ::= ENUMERATED { 
	sir, 
	sir-error, 
	transmitted-code-power, 
	rSCP, 
	rx-timing-deviation,
	round-trip-time,
	..., 
	rx-timing-deviation-LCR,
	angle-Of-Arrival-LCR,
	hs-sich-quality
}

DedicatedMeasurementValue ::= CHOICE {
	sIR-Value			SIR-Value,
	sIR-ErrorValue			SIR-Error-Value,
	transmittedCodePowerValue	Transmitted-Code-Power-Value,
	rSCP				RSCP-Value,	-- TDD only
	rxTimingDeviationValue	Rx-Timing-Deviation-Value,	-- 3.84Mcps TDD only
	roundTripTime		Round-Trip-Time-Value,  -- FDD only
	...,
	extension-DedicatedMeasurementValue		Extension-DedicatedMeasurementValue
}

--Extension-DedicatedMeasurementValue	::= ProtocolIE-Single-Container {{ Extension-DedicatedMeasurementValueIE }}
Extension-DedicatedMeasurementValue	::= ProtocolIE-Single-Container 

--Extension-DedicatedMeasurementValueIE RNSAP-PROTOCOL-IES ::= {
--	{ ID id-Rx-Timing-Deviation-Value-LCR	CRITICALITY reject	TYPE Rx-Timing-Deviation-Value-LCR	PRESENCE mandatory }|
--	{ ID id-Angle-Of-Arrival-Value-LCR		CRITICALITY reject	TYPE Angle-Of-Arrival-Value-LCR	PRESENCE mandatory }|
--	{ ID id-HS-SICH-Reception-Quality		CRITICALITY reject	TYPE HS-SICH-Reception-Quality-Value	PRESENCE mandatory },
--	...
--}

DedicatedMeasurementValueInformation ::= CHOICE {
	measurementAvailable		DedicatedMeasurementAvailable,
	measurementnotAvailable		DedicatedMeasurementnotAvailable
}

DedicatedMeasurementAvailable::= SEQUENCE {
	dedicatedmeasurementValue		DedicatedMeasurementValue,
    cFN                             CFN                     OPTIONAL,
--	ie-Extensions					ProtocolExtensionContainer { { DedicatedMeasurementAvailableItem-ExtIEs} }		OPTIONAL,
	iE-Extensions					ProtocolExtensionContainer OPTIONAL,
	...
}

--DedicatedMeasurementAvailableItem-ExtIEs RNSAP-PROTOCOL-EXTENSION ::= {
--	...
--}

DedicatedMeasurementnotAvailable ::= NULL

DelayedActivation ::= CHOICE {
	cfn						CFN,
	separate-indication		NULL
}

DelayedActivationUpdate ::= CHOICE {
	activate		Activate-Info,
	deactivate		Deactivate-Info
}

Activate-Info ::= SEQUENCE {
	activation-type  		Execution-Type,
	initial-dl-tx-power 	DL-Power,
	firstRLS-Indicator		FirstRLS-Indicator											OPTIONAL, --FDD Only
	propagation-delay		PropagationDelay 											OPTIONAL, --FDD Only
--	iE-Extensions			ProtocolExtensionContainer { { Activate-Info-ExtIEs} }		OPTIONAL,
	iE-Extensions			ProtocolExtensionContainer OPTIONAL,
	...
}

--Activate-Info-ExtIEs RNSAP-PROTOCOL-EXTENSION ::= {
--	...
--}

Deactivate-Info ::= SEQUENCE {
	deactivation-type  		Execution-Type,
--	iE-Extensions			ProtocolExtensionContainer { { Deactivate-Info-ExtIEs} }		OPTIONAL,
	iE-Extensions			ProtocolExtensionContainer OPTIONAL,
	...
}

--Deactivate-Info-ExtIEs RNSAP-PROTOCOL-EXTENSION ::= {
--	...
--}

Execution-Type ::= CHOICE {
	synchronised 	CFN,
	unsynchronised	NULL
}

DeltaSIR				::= INTEGER (0..30)
-- Step 0.1 dB, Range 0..3 dB.

DGPSCorrections ::= SEQUENCE {
	gPSTOW									GPSTOW,
	gPS-Status-Health						GPS-Status-Health,
	satellite-DGPSCorrections-Information	SEQUENCE (SIZE (1..16)) OF
		SEQUENCE {
			sAT-ID								SAT-ID,
			iode-dgps							BIT STRING (SIZE (8)),
			uDRE								UDRE,
			pRC									PRC,
			range-Correction-Rate				Range-Correction-Rate,
--			iE-Extensions						ProtocolExtensionContainer { { Satellite-DGPSCorrections-Information-ExtIEs} }		OPTIONAL,
			iE-Extensions						ProtocolExtensionContainer OPTIONAL,
			...
		},
--	iE-Extensions					ProtocolExtensionContainer { { DGPSCorrections-ExtIEs} }		OPTIONAL,
	iE-Extensions					ProtocolExtensionContainer OPTIONAL,
	...
}

--Satellite-DGPSCorrections-Information-ExtIEs RNSAP-PROTOCOL-EXTENSION ::= {
--	...
--}

--DGPSCorrections-ExtIEs RNSAP-PROTOCOL-EXTENSION ::= {
--	...
--}

DGPSThreshold ::= SEQUENCE {
	pRCDeviation		PRCDeviation,
--	iE-Extensions		ProtocolExtensionContainer { { DGPSThreshold-ExtIEs} }		OPTIONAL,
	iE-Extensions		ProtocolExtensionContainer OPTIONAL,
	...
}

--DGPSThreshold-ExtIEs RNSAP-PROTOCOL-EXTENSION ::= {
--	...
--}

DiscardTimer ::= ENUMERATED {v20,v40,v60,v80,v100,v120,v140,v160,v180,v200,v250,v300,v400,v500,v750,v1000,v1250,v1500,v1750,v2000,v2500,v3000,v3500,v4000,v4500,v5000,v7500,
 ...
}

DiversityControlField			::= ENUMERATED {
	may,
	must,
	must-not
}

DiversityMode				::= ENUMERATED {
	none,
	sTTD,
	closedLoopMode1,
	not-used-closedLoopMode2,
	...
}

DL-DPCH-SlotFormat			::= INTEGER (0..16,...)

DL-DPCH-TimingAdjustment ::= ENUMERATED {
	timing-advance,
	timing-delay
}

DL-Power				::= INTEGER (-350..150)
-- Value = DL-Power / 10
-- Unit dB, Range -35dB .. +15dB, Step 0.1dB

DL-PowerBalancing-Information ::= SEQUENCE {
	powerAdjustmentType					PowerAdjustmentType,
    dLReferencePower					DL-Power		OPTIONAL,
	-- This IE shall be present if Power Adjustment Type IE equals to 'Common'
	dLReferencePowerList		DL-ReferencePowerInformationList		OPTIONAL,
	-- This IE shall be present if Power Adjustment Type IE equals to 'Individual'
	maxAdjustmentStep					MaxAdjustmentStep		OPTIONAL,
	-- This IE shall be present if Power Adjustment Type IE equals to 'Common' or 'Individual'
	adjustmentPeriod					AdjustmentPeriod		OPTIONAL,
	-- This IE shall be present if Power Adjustment Type IE equals to 'Common' or 'Individual'
	adjustmentRatio						ScaledAdjustmentRatio	OPTIONAL,
	-- This IE shall be present if Power Adjustment Type IE equals to 'Common' or 'Individual'
--	iE-Extensions						ProtocolExtensionContainer { { DL-PowerBalancing-Information-ExtIEs } } OPTIONAL,
	iE-Extensions						ProtocolExtensionContainer OPTIONAL,
	...
}

--DL-PowerBalancing-Information-ExtIEs RNSAP-PROTOCOL-EXTENSION ::= {
--	...
--}

DL-ReferencePowerInformationList 		::= SEQUENCE (SIZE (1..16)) OF DL-ReferencePowerInformationItem

DL-ReferencePowerInformationItem ::= SEQUENCE {
	rL-ID						RL-ID,
	dl-Reference-Power			DL-Power,
--	iE-Extensions				ProtocolExtensionContainer { {DL-ReferencePowerInformationItem-ExtIEs} } OPTIONAL,
	iE-Extensions				ProtocolExtensionContainer OPTIONAL,
	...
}

--DL-ReferencePowerInformationItem-ExtIEs RNSAP-PROTOCOL-EXTENSION ::= {
--	...
--}

DL-PowerBalancing-ActivationIndicator	::= ENUMERATED {
	dL-PowerBalancing-Activated
}

DL-PowerBalancing-UpdatedIndicator	::= ENUMERATED {
	dL-PowerBalancing-Updated
}

DL-ReferencePowerInformation	::=	SEQUENCE {
	common-DL-ReferencePowerInformation			DL-Power		OPTIONAL,
	individual-DL-ReferencePowerInformation		DL-ReferencePowerInformationList		OPTIONAL,
--	iE-Extensions								ProtocolExtensionContainer { { DL-ReferencePowerInformation-ExtIEs } } OPTIONAL,
	iE-Extensions								ProtocolExtensionContainer OPTIONAL,
	...
}

--DL-ReferencePowerInformation-ExtIEs RNSAP-PROTOCOL-EXTENSION ::= {
--	...
--}

D-RNTI					::= INTEGER (0..1048575)

D-RNTI-ReleaseIndication ::= ENUMERATED {
	release-D-RNTI,
	not-release-D-RNTI
}

DL-ScramblingCode			::= INTEGER (0..15)

DL-FrameType ::= ENUMERATED {
	typeA,
	typeB,
	...
}

DL-Timeslot-Information ::= SEQUENCE ( SIZE (1..15)) OF DL-Timeslot-InformationItem

DL-Timeslot-InformationItem ::= SEQUENCE {
	timeSlot						TimeSlot,
	midambleShiftAndBurstType		MidambleShiftAndBurstType,
	tFCI-Presence					TFCI-Presence,
	dL-Code-Information				TDD-DL-Code-Information,
--	iE-Extensions					ProtocolExtensionContainer { {DL-Timeslot-InformationItem-ExtIEs} } OPTIONAL,
	iE-Extensions					ProtocolExtensionContainer OPTIONAL,
	...
}

--DL-Timeslot-InformationItem-ExtIEs RNSAP-PROTOCOL-EXTENSION ::= {
--	...
--}

DL-TimeslotLCR-Information ::= SEQUENCE (SIZE (1.. 6)) OF DL-TimeslotLCR-InformationItem

DL-TimeslotLCR-InformationItem	 ::= SEQUENCE {
	timeSlotLCR								TimeSlotLCR,
	midambleShiftLCR						MidambleShiftLCR,
	tFCI-Presence							TFCI-Presence,
	dL-Code-LCR-Information				TDD-DL-Code-LCR-Information,
--	iE-Extensions							ProtocolExtensionContainer { { DL-TimeslotLCR-InformationItem-ExtIEs} }		OPTIONAL,
	iE-Extensions							ProtocolExtensionContainer OPTIONAL,
	...
}

--DL-TimeslotLCR-InformationItem-ExtIEs RNSAP-PROTOCOL-EXTENSION ::= {
--	{ ID id-Maximum-DL-Power-TimeslotLCR-InformationItem	CRITICALITY ignore   EXTENSION DL-Power		PRESENCE optional	}|
	-- Applicable to 1.28Mcps TDD only
--	{ ID id-Minimum-DL-Power-TimeslotLCR-InformationItem	CRITICALITY ignore	 EXTENSION DL-Power		PRESENCE optional	},
	-- Applicable to 1.28Mcps TDD only
--	...
--}

DL-TimeSlot-ISCP-Info ::= SEQUENCE (SIZE (1..15)) OF DL-TimeSlot-ISCP-InfoItem

DL-TimeSlot-ISCP-InfoItem ::= SEQUENCE {
	timeSlot					TimeSlot,
	dL-TimeslotISCP				DL-TimeslotISCP,
--	iE-Extensions				ProtocolExtensionContainer { { DL-TimeSlot-ISCP-InfoItem-ExtIEs} } OPTIONAL,
	iE-Extensions				ProtocolExtensionContainer OPTIONAL,
	...
}

--DL-TimeSlot-ISCP-InfoItem-ExtIEs RNSAP-PROTOCOL-EXTENSION ::= {
--	...
--}

DL-TimeSlot-ISCP-LCR-Information ::= SEQUENCE (SIZE (1..6)) OF	DL-TimeSlot-ISCP-LCR-InfoItem

DL-TimeSlot-ISCP-LCR-InfoItem ::= SEQUENCE {
 	timeSlotLCR						TimeSlotLCR,
	dL-TimeslotISCP					DL-TimeslotISCP,
--	iE-Extensions					ProtocolExtensionContainer { { DL-TimeSlot-ISCP-LCR-InfoItem-ExtIEs} }		OPTIONAL,
	iE-Extensions					ProtocolExtensionContainer OPTIONAL,
	...
 }

--DL-TimeSlot-ISCP-LCR-InfoItem-ExtIEs RNSAP-PROTOCOL-EXTENSION ::= {
--	...
--}

DL-TimeslotISCP			::= INTEGER (0..91)
-- According to mapping in [24]

Downlink-Compressed-Mode-Method 	::= ENUMERATED {
	not-Used-puncturing,
	sFdiv2,
	higher-layer-scheduling,
	...
}

DPC-Mode ::= ENUMERATED {
	mode0,
	mode1,
	...
}

DPC-Mode-Change-SupportIndicator ::= ENUMERATED {
dPC-ModeChangeSupported
}

DPCH-ID					::= INTEGER (0..239)

DPCHConstantValue ::= INTEGER (-10..10)
-- Unit dB, Step 1dB

DRACControl		::= ENUMERATED {
	not-Used-requested,
	not-requested
}

DRXCycleLengthCoefficient				::= INTEGER (3..9)
-- See in [16]

DSCH-RNTI ::= INTEGER (0..65535)

DSCH-FlowControlInformation ::=  SEQUENCE (SIZE(1..16)) OF DSCH-FlowControlItem

DSCH-FlowControlItem ::= SEQUENCE {
	dSCH-SchedulingPriority				SchedulingPriorityIndicator,
	mAC-c-sh-SDU-Lengths				MAC-c-sh-SDU-LengthList,
--	iE-Extensions						ProtocolExtensionContainer { {DSCH-FlowControlItem-ExtIEs} } OPTIONAL,
	iE-Extensions						ProtocolExtensionContainer OPTIONAL,
	...
}

--DSCH-FlowControlItem-ExtIEs RNSAP-PROTOCOL-EXTENSION ::= {
--	{ ID id-DSCH-InitialWindowSize	CRITICALITY ignore	EXTENSION	DSCH-InitialWindowSize	PRESENCE optional },
--	...
--}

DSCH-ID					::= INTEGER (0..255)

DSCH-InitialWindowSize			::= INTEGER (1..255)
-- Number of MAC-c/sh SDUs.
-- 255 = Unlimited number of MAC-c/sh SDUs

DSCH-TDD-Information ::=  SEQUENCE (SIZE (1..10)) OF DSCH-TDD-InformationItem

DSCH-TDD-InformationItem ::= SEQUENCE {
	dSCH-ID								DSCH-ID,
	dl-ccTrCHID							CCTrCH-ID, -- DL CCTrCH in which the DSCH is mapped
	trChSourceStatisticsDescriptor		TrCH-SrcStatisticsDescr,
	transportFormatSet					TransportFormatSet,
	allocationRetentionPriority 		AllocationRetentionPriority,
	schedulingPriorityIndicator			SchedulingPriorityIndicator,
	bLER								BLER,
--	iE-Extensions						ProtocolExtensionContainer { {DSCH-TDD-InformationItem-ExtIEs} } OPTIONAL,
	iE-Extensions						ProtocolExtensionContainer OPTIONAL,
	...
}

--DSCH-TDD-InformationItem-ExtIEs RNSAP-PROTOCOL-EXTENSION ::= {
--	{ ID id-TrafficClass					CRITICALITY ignore	EXTENSION TrafficClass		PRESENCE mandatory}|
--	{ ID id-BindingID						CRITICALITY	ignore	EXTENSION 	BindingID	PRESENCE 	optional	}|
	-- Shall be ignored if bearer establishment with ALCAP.	
--	{ ID id-TransportLayerAddress			CRITICALITY	ignore	EXTENSION 	TransportLayerAddress		PRESENCE 	optional	},
	-- Shall be ignored if bearer establishment with ALCAP.
--	...
--}

DsField ::= BIT STRING (SIZE (8))

-- E

EDCH-DDI-Value ::= INTEGER (0..63)

EDCH-FDD-DL-ControlChannelInformation ::= SEQUENCE {
	eAGCH-ERGCH-EHICH-FDD-ScramblingCode				DL-ScramblingCode					OPTIONAL,
	eAGCH-ChannelisationCode							FDD-DL-ChannelisationCodeNumber		OPTIONAL,
	primary-e-RNTI										E-RNTI								OPTIONAL,
	secondary-e-RNTI									E-RNTI								OPTIONAL,
	eRGCH-EHICH-ChannelisationCode						FDD-DL-ChannelisationCodeNumber,
	eRGCH-SignatureSequence								ERGCH-SignatureSequence				OPTIONAL,
	eHICH-SignatureSequence								EHICH-SignatureSequence				OPTIONAL,
	serving-Grant-Value									E-Serving-Grant-Value				OPTIONAL,
	primary-Secondary-Grant-Selector					E-Primary-Secondary-Grant-Selector	OPTIONAL,
	e-RGCH-Release-Indicator							E-RGCH-Release-Indicator			OPTIONAL,
--	iE-Extensions										ProtocolExtensionContainer { { EDCH-FDD-DL-ControlChannelInformation-ExtIEs } }			OPTIONAL,
	iE-Extensions										ProtocolExtensionContainer OPTIONAL,
	...
}

--EDCH-FDD-DL-ControlChannelInformation-ExtIEs RNSAP-PROTOCOL-EXTENSION ::= {
--	...
--}

EDCH-FDD-Information ::= SEQUENCE {
	eDCH-MACdFlows-Information						EDCH-MACdFlows-Information,
--	iE-Extensions									ProtocolExtensionContainer { { EDCH-FDD-Information-ExtIEs } }			OPTIONAL,
	iE-Extensions									ProtocolExtensionContainer OPTIONAL,
	...
}

--EDCH-FDD-Information-ExtIEs RNSAP-PROTOCOL-EXTENSION ::= {
--	...
--}

EDCH-FDD-InformationResponse ::= SEQUENCE (SIZE (1..8)) OF EDCH-FDD-InformationResponseItem

EDCH-FDD-InformationResponseItem ::= SEQUENCE {
	eDCH-MACdFlow-ID						EDCH-MACdFlow-ID,
	bindingID					BindingID				OPTIONAL,
	transportLayerAddress		TransportLayerAddress	OPTIONAL,
--	iE-Extensions		 		ProtocolExtensionContainer { {EDCH-FDD-InformationResponseItem-ExtIEs} } OPTIONAL,
	iE-Extensions		 		ProtocolExtensionContainer OPTIONAL,
	...
}

--EDCH-FDD-InformationResponseItem-ExtIEs RNSAP-PROTOCOL-EXTENSION ::= {
--	...
--}

EDCH-FDD-Information-To-Modify ::= SEQUENCE {
	eDCH-MACdFlow-Specific-Information				EDCH-MACdFlow-Specific-InfoToModifyList,
--	iE-Extensions									ProtocolExtensionContainer { { EDCH-FDD-Information-To-Modify-ExtIEs } }			OPTIONAL,
	iE-Extensions									ProtocolExtensionContainer OPTIONAL,
	...
}

--EDCH-FDD-Information-To-Modify-ExtIEs RNSAP-PROTOCOL-EXTENSION ::= {
--	...
--}

EDCH-FDD-Update-Information ::= SEQUENCE (SIZE (1..16)) OF EDCH-FDD-Update-InfoItem

EDCH-FDD-Update-InfoItem  ::= SEQUENCE {
	eDCH-FDD-DL-ControlChannelInformation			EDCH-FDD-DL-ControlChannelInformation			OPTIONAL,
--	iE-Extensions						ProtocolExtensionContainer { { EDCH-FDD-Update-InfoItem-ExtIEs } }			OPTIONAL,
	iE-Extensions						ProtocolExtensionContainer OPTIONAL,
	...
}

--EDCH-FDD-Update-InfoItem-ExtIEs RNSAP-PROTOCOL-EXTENSION ::= {
--	...
--}

E-DCH-Grant-Type-Information ::= CHOICE {
	e-DCH-Non-Scheduled-Transmission-Grant		E-DCH-Non-Scheduled-Transmission-Grant-Items,
	e-DCH-Scheduled-Transmission-Grant			NULL,
	...
}

E-DCH-HARQ-PO-FDD ::= INTEGER (0.. 6)


E-DCH-LogicalChannelInformation ::= SEQUENCE (SIZE (1..16)) OF E-DCH-LogicalChannelInformationItem

E-DCH-LogicalChannelInformationItem ::= SEQUENCE {
	logicalChannelId				LogicalChannelID,
	schedulingPriorityIndicator		SchedulingPriorityIndicator,
	mACes-GuaranteedBitRate			MACes-Guaranteed-Bitrate		OPTIONAL,
	eDCH-DDI-Value					EDCH-DDI-Value,
	mACd-PDU-Size-List				E-DCH-MACdPDU-SizeList, 
--	iE-Extensions					ProtocolExtensionContainer { { E-DCH-LogicalChannelInformationItem-ExtIEs } }			OPTIONAL,
	iE-Extensions					ProtocolExtensionContainer OPTIONAL,
	...
}

--E-DCH-LogicalChannelInformationItem-ExtIEs RNSAP-PROTOCOL-EXTENSION ::= {
--	...
--}

E-DCH-MACdPDU-SizeList ::= SEQUENCE (SIZE (1..64)) OF E-DCH-MACdPDU-SizeListItem

E-DCH-MACdPDU-SizeListItem ::= SEQUENCE {
	mACdPDU-Size					MACdPDU-Size,
--	iE-Extensions					ProtocolExtensionContainer { { E-DCH-MACdPDU-SizeListItem-ExtIEs } }			OPTIONAL,
	iE-Extensions					ProtocolExtensionContainer OPTIONAL,
	...
}

--E-DCH-MACdPDU-SizeListItem-ExtIEs RNSAP-PROTOCOL-EXTENSION ::= {
--	...
--}




E-DCH-LogicalChannelToModify ::= SEQUENCE (SIZE (1..16)) OF E-DCH-LogicalChannelToModifyItem

E-DCH-LogicalChannelToModifyItem ::= SEQUENCE {
	logicalChannelId				LogicalChannelID,
	schedulingPriorityIndicator		SchedulingPriorityIndicator		OPTIONAL,
	mACes-GuaranteedBitRate			MACes-Guaranteed-Bitrate		OPTIONAL,
	eDCH-DDI-Value					EDCH-DDI-Value					OPTIONAL,
	mACd-PDU-Size-List				E-DCH-MACdPDU-SizeToModifyList, 
--	iE-Extensions					ProtocolExtensionContainer { { E-DCH-LogicalChannelToModifyItem-ExtIEs } }			OPTIONAL,
	iE-Extensions					ProtocolExtensionContainer OPTIONAL,
	...
}

--E-DCH-LogicalChannelToModifyItem-ExtIEs RNSAP-PROTOCOL-EXTENSION ::= {
--	...
--}

E-DCH-MACdPDU-SizeToModifyList ::= SEQUENCE (SIZE (0..64)) OF E-DCH-MACdPDU-SizeListItem



E-DCH-LogicalChannelToDelete ::= SEQUENCE (SIZE (1..16)) OF E-DCH-LogicalChannelToDeleteItem

E-DCH-LogicalChannelToDeleteItem ::= SEQUENCE {
	logicalChannelId				LogicalChannelID,
--	iE-Extensions					ProtocolExtensionContainer { { E-DCH-LogicalChannelToDeleteItem-ExtIEs } }			OPTIONAL,
	iE-Extensions					ProtocolExtensionContainer OPTIONAL,
	...
}

--E-DCH-LogicalChannelToDeleteItem-ExtIEs RNSAP-PROTOCOL-EXTENSION ::= {
--	...
--}

LogicalChannelID ::= INTEGER (1..15)



EDCH-MACdFlow-ID ::= INTEGER (0..7)

EDCH-MACdFlows-Information ::= SEQUENCE {
	eDCH-MACdFlow-Specific-Information				EDCH-MACdFlow-Specific-InfoList,
--	iE-Extensions									ProtocolExtensionContainer { { EDCH-MACdFlow-Specific-Information-ExtIEs } }			OPTIONAL,
	iE-Extensions									ProtocolExtensionContainer OPTIONAL,
	...
}

E-DCH-MACdFlow-Multiplexing-List ::= BIT STRING ( SIZE(8) )

--EDCH-MACdFlow-Specific-Information-ExtIEs RNSAP-PROTOCOL-EXTENSION ::= {
--	...
--}

EDCH-MACdFlow-Specific-InfoList ::= SEQUENCE (SIZE (1..8)) OF EDCH-MACdFlow-Specific-InfoItem

EDCH-MACdFlow-Specific-InfoItem ::= SEQUENCE {
	eDSCH-MACdFlow-ID					EDCH-MACdFlow-ID,
	allocationRetentionPriority			AllocationRetentionPriority			OPTIONAL,
	tnlQoS								TnlQos 								OPTIONAL,
	payloadCRC-PresenceIndicator		PayloadCRC-PresenceIndicator,
	maxNr-Retransmissions-EDCH			MaxNr-Retransmissions-EDCH,
	trafficClass						TrafficClass,
	eDCH-HARQ-PO-FDD					E-DCH-HARQ-PO-FDD,
	eDCH-MACdFlow-Multiplexing-List		E-DCH-MACdFlow-Multiplexing-List	OPTIONAL,
	eDCH-Grant-Type-Information			E-DCH-Grant-Type-Information		OPTIONAL,
	bundlingModeIndicator				BundlingModeIndicator				OPTIONAL,
	eDCHLogicalChannelInformation		E-DCH-LogicalChannelInformation,
--	iE-Extensions						ProtocolExtensionContainer { { EDCH-MACdFlow-Specific-InfoItem-ExtIEs } }			OPTIONAL,
	iE-Extensions						ProtocolExtensionContainer OPTIONAL,
	...
}

--EDCH-MACdFlow-Specific-InfoItem-ExtIEs RNSAP-PROTOCOL-EXTENSION ::= {
--	...
--}

EDCH-MACdFlow-Specific-InfoToModifyList ::= SEQUENCE (SIZE (1..8)) OF EDCH-MACdFlow-Specific-InfoToModifyItem

EDCH-MACdFlow-Specific-InfoToModifyItem ::= SEQUENCE {
	eDSCH-MACdFlow-ID					EDCH-MACdFlow-ID,
	allocationRetentionPriority			AllocationRetentionPriority			OPTIONAL,
	transportBearerRequestIndicator		TransportBearerRequestIndicator,
	tnlQoS								TnlQos 								OPTIONAL,
	maxNr-Retransmissions-EDCH			MaxNr-Retransmissions-EDCH			OPTIONAL,
	trafficClass						TrafficClass						OPTIONAL,
	eDCH-HARQ-PO-FDD					E-DCH-HARQ-PO-FDD					OPTIONAL,
	eDCH-MACdFlow-Multiplexing-List		E-DCH-MACdFlow-Multiplexing-List	OPTIONAL,
	eDCH-Grant-Type-Information			E-DCH-Grant-Type-Information		OPTIONAL,
	bundlingModeIndicator				BundlingModeIndicator				OPTIONAL,
	eDCH-LogicalChannelToAdd			E-DCH-LogicalChannelInformation		OPTIONAL,
	eDCH-LogicalChannelToModify			E-DCH-LogicalChannelToModify		OPTIONAL,
	eDCH-LogicalChannelToDelete			E-DCH-LogicalChannelToDelete		OPTIONAL,
--	iE-Extensions						ProtocolExtensionContainer { { EDCH-MACdFlow-Specific-InfoToModifyItem-ExtIEs } }			OPTIONAL,
	iE-Extensions						ProtocolExtensionContainer OPTIONAL,
	...
}

--EDCH-MACdFlow-Specific-InfoToModifyItem-ExtIEs RNSAP-PROTOCOL-EXTENSION ::= {
--	...
--}

EDCH-MACdFlows-To-Delete ::= SEQUENCE (SIZE (1..8)) OF EDCH-MACdFlows-To-Delete-Item

EDCH-MACdFlows-To-Delete-Item ::= SEQUENCE {
	eDSCH-MACdFlow-ID					EDCH-MACdFlow-ID,
--	iE-Extensions						ProtocolExtensionContainer { { EDCH-MACdFlows-To-Delete-Item-ExtIEs } }			OPTIONAL,
	iE-Extensions						ProtocolExtensionContainer OPTIONAL,
	...
}

--EDCH-MACdFlows-To-Delete-Item-ExtIEs RNSAP-PROTOCOL-EXTENSION ::= {
--	...
--}

EDCH-Physical-Layer-Category ::= INTEGER -- FFS

EDCH-RL-Indication ::= ENUMERATED {
	eDCH,
	non-EDCH
}

E-DCH-Non-Scheduled-Transmission-Grant-Items ::= SEQUENCE {
	maxBits-MACe-PDU-non-scheduled				Max-Bits-MACe-PDU-non-scheduled,
	hARQ-Process-Allocation-2ms		HARQ-Process-Allocation-2ms-EDCH													OPTIONAL,
--	iE-Extensions					ProtocolExtensionContainer { { E-DCH-Non-Scheduled-Transmission-Grant-Items-ExtIEs} }	OPTIONAL,
	iE-Extensions					ProtocolExtensionContainer OPTIONAL,
	...
}

--E-DCH-Non-Scheduled-Transmission-Grant-Items-ExtIEs RNSAP-PROTOCOL-EXTENSION ::= {
--	...
--}

E-DCH-TFCI-Table-Index ::= INTEGER (0..1,...)

EDPCH-Information-FDD ::= SEQUENCE {
	maxSet-E-DPDCHs											Max-Set-E-DPDCHs,
	punctureLimit											PunctureLimit,
	e-TFCS-Information											E-TFCS-Information,
	e-TTI													E-TTI,
	e-DPCCH-PO												E-DPCCH-PO,
--	iE-Extensions						ProtocolExtensionContainer { { EDPCH-Information-FDD-ExtIEs } }			OPTIONAL,
	iE-Extensions						ProtocolExtensionContainer OPTIONAL,
	...
}

--EDPCH-Information-FDD-ExtIEs RNSAP-PROTOCOL-EXTENSION ::= {
--	...
--}

EDPCH-Information-RLReconfPrepare-FDD ::= SEQUENCE {
	maxSet-E-DPDCHs											Max-Set-E-DPDCHs			OPTIONAL,
	punctureLimit											PunctureLimit,
	e-TFCS-Information											E-TFCS-Information,
	e-TTI													E-TTI,
	e-DPCCH-PO												E-DPCCH-PO,
--	iE-Extensions						ProtocolExtensionContainer { { EDPCH-Information-RLReconfPrepare-FDD-ExtIEs } }			OPTIONAL,
	iE-Extensions						ProtocolExtensionContainer OPTIONAL,
	...
}

--EDPCH-Information-RLReconfPrepare-FDD-ExtIEs RNSAP-PROTOCOL-EXTENSION ::= {
--	...
--}

EDPCH-Information-RLReconfRequest-FDD ::= SEQUENCE {
	e-TFCS-Information										E-TFCS-Information																OPTIONAL,
	e-DPCCH-PO												E-DPCCH-PO																		OPTIONAL,
--	iE-Extensions						ProtocolExtensionContainer { { EDPCH-Information-RLReconfRequest-FDD-ExtIEs } }			OPTIONAL,
	iE-Extensions						ProtocolExtensionContainer OPTIONAL,
	...
}

--EDPCH-Information-RLReconfRequest-FDD-ExtIEs RNSAP-PROTOCOL-EXTENSION ::= {
--	...
--}

E-DPCCH-PO ::= INTEGER (0..8)

E-Primary-Secondary-Grant-Selector ::= ENUMERATED {
	primary,
	secondary
}

EHICH-SignatureSequence ::= INTEGER  (0..39)


E-RGCH-Release-Indicator ::= ENUMERATED {e-RGCHreleased}

ERGCH-SignatureSequence ::= INTEGER  (0..39)

E-Serving-Grant-Value ::= INTEGER (0..31,...)

EDCH-Serving-RL ::= CHOICE {
	e-DCH-Serving-RL-in-this-DRNS			EDCH-Serving-RL-in-this-DRNS,
	e-DCH-Serving-RL-not-in-this-DRNS		NULL,
	...
}

EDCH-Serving-RL-in-this-DRNS ::= SEQUENCE {
	e-DCH-Serving-RL-Id				RL-ID,
--	iE-Extensions					ProtocolExtensionContainer { { EDCH-Serving-RL-in-this-DRNS-ExtIEs} }	OPTIONAL,
	iE-Extensions					ProtocolExtensionContainer OPTIONAL,
	...
}

--EDCH-Serving-RL-in-this-DRNS-ExtIEs RNSAP-PROTOCOL-EXTENSION ::= {
--	...
--}

E-RNTI ::= INTEGER (0..65535)

E-TFCI ::= INTEGER (0..127)

E-TFCS-Information ::= SEQUENCE {
	e-DCH-TFCI-Table-Index									E-DCH-TFCI-Table-Index,
	e-DCH-Min-Set-E-TFCI							E-TFCI,
	reference-E-TFCI-Information					Reference-E-TFCI-Information,
--	iE-Extensions									ProtocolExtensionContainer { {E-TFCS-Information-ExtIEs} }		OPTIONAL,
	iE-Extensions									ProtocolExtensionContainer OPTIONAL,
	...

}

--E-TFCS-Information-ExtIEs RNSAP-PROTOCOL-EXTENSION ::= {
--	...
--}

E-TTI  ::= ENUMERATED {
	tti10,
	tti2
-- 10ms TTI, 2ms TTI
}

Enhanced-PrimaryCPICH-EcNo			::= INTEGER (0..49)

EventA ::= SEQUENCE {
	measurementTreshold		MeasurementThreshold,
	measurementHysteresisTime	MeasurementHysteresisTime		OPTIONAL,
--	iE-Extensions			ProtocolExtensionContainer { {EventA-ExtIEs} } OPTIONAL,
	iE-Extensions			ProtocolExtensionContainer OPTIONAL,
	...
}

--EventA-ExtIEs RNSAP-PROTOCOL-EXTENSION ::= {
--	...
--}

EventB ::= SEQUENCE {
	measurementTreshold		MeasurementThreshold,
	measurementHysteresisTime	MeasurementHysteresisTime		OPTIONAL,
--	iE-Extensions			ProtocolExtensionContainer { {EventB-ExtIEs} } OPTIONAL,
	iE-Extensions			ProtocolExtensionContainer OPTIONAL,
	...
}

--EventB-ExtIEs RNSAP-PROTOCOL-EXTENSION ::= {
--	...
--}


EventC ::= SEQUENCE {
	measurementIncreaseDecreaseThreshold	MeasurementIncreaseDecreaseThreshold,
	measurementChangeTime		MeasurementChangeTime,
--	iE-Extensions			ProtocolExtensionContainer { {EventC-ExtIEs} } OPTIONAL,
	iE-Extensions			ProtocolExtensionContainer OPTIONAL,
	...
}

--EventC-ExtIEs RNSAP-PROTOCOL-EXTENSION ::= {
--	...
--}

EventD ::= SEQUENCE {
	measurementIncreaseDecreaseThreshold	MeasurementIncreaseDecreaseThreshold,
	measurementChangeTime		MeasurementChangeTime,
--	iE-Extensions			ProtocolExtensionContainer { {EventD-ExtIEs} } OPTIONAL,
	iE-Extensions			ProtocolExtensionContainer OPTIONAL,
	...
}

--EventD-ExtIEs RNSAP-PROTOCOL-EXTENSION ::= {
--	...
--}

EventE ::= SEQUENCE {
	measurementThreshold1		MeasurementThreshold,
	measurementThreshold2		MeasurementThreshold			OPTIONAL,
	measurementHysteresisTime	MeasurementHysteresisTime		OPTIONAL,
	reportPeriodicity		ReportPeriodicity			OPTIONAL,
--	iE-Extensions			ProtocolExtensionContainer { {EventE-ExtIEs} } OPTIONAL,
	iE-Extensions			ProtocolExtensionContainer OPTIONAL,
	...
}

--EventE-ExtIEs RNSAP-PROTOCOL-EXTENSION ::= {
--	...
--}

EventF ::= SEQUENCE {
	measurementThreshold1		MeasurementThreshold,
	measurementThreshold2		MeasurementThreshold			OPTIONAL,
	measurementHysteresisTime	MeasurementHysteresisTime		OPTIONAL,
	reportPeriodicity		ReportPeriodicity			OPTIONAL,
--	iE-Extensions			ProtocolExtensionContainer { {EventF-ExtIEs} } OPTIONAL,
	iE-Extensions			ProtocolExtensionContainer OPTIONAL,
	...
}

--EventF-ExtIEs RNSAP-PROTOCOL-EXTENSION ::= {
--	...
--}

--ExtendedGSMCellIndividualOffset	::= INTEGER (-50..-11|11..50)
ExtendedGSMCellIndividualOffset	::= INTEGER (-50..50)

-- F

FACH-FlowControlInformation ::= SEQUENCE (SIZE (1..16)) OF FACH-FlowControlInformationItem

FACH-FlowControlInformationItem ::= SEQUENCE {
	fACH-SchedulingPriority			SchedulingPriorityIndicator,
	mAC-c-sh-SDU-Lengths			MAC-c-sh-SDU-LengthList,
	fACH-InitialWindowSize			FACH-InitialWindowSize,
--	iE-Extensions					ProtocolExtensionContainer { {FACH-FlowControlInformationItem-ExtIEs} } OPTIONAL,
	iE-Extensions					ProtocolExtensionContainer OPTIONAL,
	...
}

--FACH-FlowControlInformationItem-ExtIEs RNSAP-PROTOCOL-EXTENSION ::= {
--	...
--}

FACH-InitialWindowSize			::= INTEGER { unlimited(255) } (0..255)
-- Number of frames MAC-c-sh SDUs.
-- 255 = Unlimited number of FACH data frames

FACH-InformationList ::= SEQUENCE (SIZE(0.. 8)) OF FACH-InformationItem

FACH-InformationItem ::= SEQUENCE {
	transportFormatSet				TransportFormatSet,
--	iE-Extensions					ProtocolExtensionContainer { { FACH-InformationItem-ExtIEs} } OPTIONAL,
	iE-Extensions					ProtocolExtensionContainer OPTIONAL,
	...
}

--FACH-InformationItem-ExtIEs RNSAP-PROTOCOL-EXTENSION ::= {
--	...
--}

FACH-PCH-InformationList ::= SEQUENCE (SIZE(1..10)) OF FACH-PCH-InformationItem

FACH-PCH-InformationItem ::= SEQUENCE {
	transportFormatSet				TransportFormatSet,
--	iE-Extensions					ProtocolExtensionContainer { { FACH-PCH-InformationItem-ExtIEs} } OPTIONAL,
	iE-Extensions					ProtocolExtensionContainer OPTIONAL,
	...
}

--FACH-PCH-InformationItem-ExtIEs RNSAP-PROTOCOL-EXTENSION ::= {
--	...
--}

FDD-DCHs-to-Modify				::= SEQUENCE (SIZE (1..128)) OF FDD-DCHs-to-ModifyItem

FDD-DCHs-to-ModifyItem ::= SEQUENCE {
	ul-FP-Mode							UL-FP-Mode		OPTIONAL,
	toAWS								ToAWS		OPTIONAL,
	toAWE								ToAWE		OPTIONAL,
	transportBearerRequestIndicator		TransportBearerRequestIndicator,
	dCH-SpecificInformationList			FDD-DCHs-to-ModifySpecificInformationList,
--	iE-Extensions						ProtocolExtensionContainer { {FDD-DCHs-to-ModifyItem-ExtIEs} } OPTIONAL,
	iE-Extensions						ProtocolExtensionContainer OPTIONAL,
	...
}

--FDD-DCHs-to-ModifyItem-ExtIEs RNSAP-PROTOCOL-EXTENSION ::= {
--	{ ID id-TnlQos						CRITICALITY 	ignore		EXTENSION 	TnlQos	PRESENCE 	optional	},
--	...
--}

FDD-DCHs-to-ModifySpecificInformationList ::= SEQUENCE (SIZE (1..128)) OF FDD-DCHs-to-ModifySpecificItem

FDD-DCHs-to-ModifySpecificItem ::=	SEQUENCE {
	dCH-ID							DCH-ID,
	ul-TransportformatSet			TransportFormatSet		OPTIONAL,
	dl-TransportformatSet			TransportFormatSet		OPTIONAL,
	allocationRetentionPriority		AllocationRetentionPriority 	OPTIONAL,
	frameHandlingPriority			FrameHandlingPriority		OPTIONAL,
	not-Used-dRACControl						NULL		OPTIONAL,
--	iE-Extensions					ProtocolExtensionContainer { {FDD-DCHs-to-ModifySpecificItem-ExtIEs} } OPTIONAL,
	iE-Extensions					ProtocolExtensionContainer OPTIONAL,
	...
}

--FDD-DCHs-to-ModifySpecificItem-ExtIEs RNSAP-PROTOCOL-EXTENSION ::= {
--	{ ID id-Guaranteed-Rate-Information		CRITICALITY ignore	EXTENSION Guaranteed-Rate-Information		PRESENCE optional	}|
--	{ ID id-TrafficClass		CRITICALITY ignore	EXTENSION TrafficClass		PRESENCE optional	},
--	...
--}

FDD-DL-ChannelisationCodeNumber		::= INTEGER (0..511)
-- According to the mapping in [27]. The maximum value is equal to the DL spreading factor -1--

FDD-DL-CodeInformation ::= SEQUENCE (SIZE (1..8)) OF FDD-DL-CodeInformationItem

FDD-DL-CodeInformationItem ::= SEQUENCE {
	dl-ScramblingCode											DL-ScramblingCode,
	fDD-DL-ChannelisationCodeNumber								FDD-DL-ChannelisationCodeNumber,
	transmission-Gap-Pattern-Sequence-ScramblingCode-Information		Transmission-Gap-Pattern-Sequence-ScramblingCode-Information	OPTIONAL,
--	iE-Extensions							ProtocolExtensionContainer { {FDD-DL-CodeInformationItem-ExtIEs} } OPTIONAL,
	iE-Extensions							ProtocolExtensionContainer OPTIONAL,
	...
}

--FDD-DL-CodeInformationItem-ExtIEs RNSAP-PROTOCOL-EXTENSION ::= {
--	...
--}

FDD-TPC-DownlinkStepSize ::= ENUMERATED {
	step-size0-5,
	step-size1,
	step-size1-5,
	step-size2,
	...
}

SchedulingPriorityIndicator 			::= INTEGER { lowest(0), highest(15) } (0..15)

FirstRLS-Indicator ::= ENUMERATED {
	first-RLS,
	not-first-RLS
}

FNReportingIndicator ::= ENUMERATED {
	fN-reporting-required,
	fN-reporting-not-required
}

FPACH-Information ::= SEQUENCE {
	timeSlotLCR					TimeSlotLCR,
	tDD-ChannelisationCodeLCR	TDD-ChannelisationCodeLCR,
	midambleShiftLCR			MidambleShiftLCR,
	wT							INTEGER (1..4),
	...
	}

FrameHandlingPriority			::= INTEGER { lowest(0), highest(15) } (0..15)

FrameOffset				::= INTEGER (0..255)
-- Frames

FrequencyBandIndicator		::= ENUMERATED {
	bandI,
	bandII,
	bandIII,
	bandIV,
	bandV,
	bandVI,
	bandVII,
	bandVIII,
	bandIX,
	bandX,
	bandXI,
	bandXII,
	bandXIII,
	bandXIV,
	bandXV,
	bandXVI,
	bandXVII,
	bandXVIII,
	bandXIX,
	bandXX,
	bandXXI,
	bandXXII,
	...
}


-- G

GapLength				::= INTEGER (1..14)
-- Unit Slot

GapDuration				::= INTEGER (1..144,...)
-- Unit Frame

GA-Cell ::= SEQUENCE (SIZE (1..16)) OF
	SEQUENCE {
		cell-GAIgeographicalCoordinate		GeographicalCoordinate,
--		iE-Extensions			ProtocolExtensionContainer { {GA-Cell-ExtIEs} } OPTIONAL,
		iE-Extensions			ProtocolExtensionContainer OPTIONAL,
		...
	}

--GA-Cell-ExtIEs RNSAP-PROTOCOL-EXTENSION ::= {
--	...
--}

GA-CellAdditionalShapes ::= CHOICE {
	pointWithUncertainty							GA-PointWithUnCertainty,
	pointWithUncertaintyEllipse						GA-PointWithUnCertaintyEllipse,
	pointWithAltitude								GA-PointWithAltitude,
	pointWithAltitudeAndUncertaintyEllipsoid		GA-PointWithAltitudeAndUncertaintyEllipsoid,
	ellipsoidArc									GA-EllipsoidArc,
	...
	}

GA-AltitudeAndDirection ::= SEQUENCE {
	directionOfAltitude		ENUMERATED {height, depth},
	altitude				INTEGER (0..32767),
	...
}

GA-EllipsoidArc ::= SEQUENCE {
	geographicalCoordinates		GeographicalCoordinate,
	innerRadius					INTEGER (0..65535),
	uncertaintyRadius			INTEGER (0..127),
	offsetAngle					INTEGER (0..179),
	includedAngle				INTEGER (0..179),
	confidence					INTEGER (0..127),
--	iE-Extensions				ProtocolExtensionContainer { { GA-EllipsoidArc-ExtIEs} } OPTIONAL,
	iE-Extensions				ProtocolExtensionContainer OPTIONAL,
	...
}

--GA-EllipsoidArc-ExtIEs RNSAP-PROTOCOL-EXTENSION ::= {
--	...
--}

GA-PointWithAltitude ::= SEQUENCE {
	geographicalCoordinates		GeographicalCoordinate,
	altitudeAndDirection		GA-AltitudeAndDirection,
--	iE-Extensions				ProtocolExtensionContainer { { GA-PointWithAltitude-ExtIEs} } OPTIONAL,
	iE-Extensions				ProtocolExtensionContainer OPTIONAL,
	...
}

--GA-PointWithAltitude-ExtIEs RNSAP-PROTOCOL-EXTENSION ::= {
--	...
--}

GA-PointWithAltitudeAndUncertaintyEllipsoid ::= SEQUENCE {
	geographicalCoordinates		GeographicalCoordinate,
	altitudeAndDirection		GA-AltitudeAndDirection,
	uncertaintyEllipse			GA-UncertaintyEllipse,
	uncertaintyAltitude			INTEGER (0..127),
	confidence					INTEGER (0..127),
--	iE-Extensions				ProtocolExtensionContainer { { GA-PointWithAltitudeAndUncertaintyEllipsoid-ExtIEs} } OPTIONAL,
	iE-Extensions				ProtocolExtensionContainer OPTIONAL,
	...
}

--GA-PointWithAltitudeAndUncertaintyEllipsoid-ExtIEs RNSAP-PROTOCOL-EXTENSION ::= {
--	...
--}

GA-PointWithUnCertaintyEllipse ::= SEQUENCE {
	geographicalCoordinates		GeographicalCoordinate,
	uncertaintyEllipse			GA-UncertaintyEllipse,
	confidence					INTEGER (0..127),
--	iE-Extensions				ProtocolExtensionContainer { { GA-PointWithUnCertaintyEllipse-ExtIEs} } OPTIONAL,
	iE-Extensions				ProtocolExtensionContainer OPTIONAL,
	...
}

--GA-PointWithUnCertaintyEllipse-ExtIEs RNSAP-PROTOCOL-EXTENSION ::= {
--	...
--}

GA-UncertaintyEllipse ::= SEQUENCE {
	uncertaintySemi-major		INTEGER (0..127),
	uncertaintySemi-minor		INTEGER (0..127),
	orientationOfMajorAxis		INTEGER (0..179),	-- The values 90..179 shall not be used.
	...
}

GA-PointWithUnCertainty ::=SEQUENCE {
	geographicalCoordinates		GeographicalCoordinate,
	uncertaintyCode			INTEGER (0..127),
--	iE-Extensions			ProtocolExtensionContainer { {GA-PointWithUnCertainty-ExtIEs} } OPTIONAL,
	iE-Extensions			ProtocolExtensionContainer OPTIONAL,
	...
}

--GA-PointWithUnCertainty-ExtIEs RNSAP-PROTOCOL-EXTENSION ::= {
--	...
--}

GA-AccessPointPosition ::= SEQUENCE {
	geographicalCoordinate		GeographicalCoordinate,
--	iE-Extensions			ProtocolExtensionContainer { {GA-AccessPoint-ExtIEs} } OPTIONAL,
	iE-Extensions			ProtocolExtensionContainer OPTIONAL,
	...
}

--GA-AccessPoint-ExtIEs RNSAP-PROTOCOL-EXTENSION ::= {
--	...
--}

GeographicalCoordinate ::= SEQUENCE {
	latitudeSign			ENUMERATED { north, south },
	latitude			INTEGER (0..8388607),
	longitude			INTEGER (-8388608..8388607),
--	iE-Extensions			ProtocolExtensionContainer { {GeographicalCoordinate-ExtIEs} } OPTIONAL,
	iE-Extensions			ProtocolExtensionContainer OPTIONAL,
	...
}

--GeographicalCoordinate-ExtIEs RNSAP-PROTOCOL-EXTENSION ::= {
--	...
--}

GERAN-Cell-Capability ::=	BIT STRING (SIZE (16))
-- First bit:  A/Gb mode --
-- Second bit: Iu mode   --
-- Note: undefined bits are considered as a spare bit and spare bits shall be set to 0 by the transmitter and shall be ignored by the receiver. --

GERAN-Classmark ::= 		OCTET STRING
	-- GERAN Classmark as defined in (38) --

GERAN-SI-Type ::= CHOICE {
	sI							GERAN-SystemInfo,
	pSI							GERAN-SystemInfo,
	...
}

GERAN-SystemInfo ::= SEQUENCE (SIZE (1..8)) OF
		SEQUENCE {
			gERAN-SI-block		OCTET STRING (SIZE (1..23)),
--			iE-Extensions		ProtocolExtensionContainer { { GERAN-SystemInfo-ExtIEs } }		OPTIONAL,
			iE-Extensions		ProtocolExtensionContainer OPTIONAL,
			...
}

--GERAN-SystemInfo-ExtIEs RNSAP-PROTOCOL-EXTENSION ::= {
--	...
--}

GenericTrafficCategory	::= BIT STRING (SIZE (8))

GPS-Almanac ::= SEQUENCE {
	wna-alm					BIT STRING (SIZE (8)),
	satellite-Almanac-Information		SEQUENCE (SIZE (1..16)) OF
		SEQUENCE {
			dATA-ID				DATA-ID,
			sAT-ID				SAT-ID,
			gps-e-alm			BIT STRING (SIZE (16)),
			gps-toa-alm			BIT STRING (SIZE (8)), 
			gps-delta-I-alm		BIT STRING (SIZE (16)),
			omegadot-alm		BIT STRING (SIZE (16)),
			svhealth-alm		BIT STRING (SIZE (8)),
			gps-a-sqrt-alm		BIT STRING (SIZE (24)),
			omegazero-alm		BIT STRING (SIZE (24)),
			m-zero-alm			BIT STRING (SIZE (24)),
			gps-omega-alm		BIT STRING (SIZE (24)),
			gps-af-zero-alm		BIT STRING (SIZE (11)),
			gps-af-one-alm		BIT STRING (SIZE (11)),
--			iE-Extensions		ProtocolExtensionContainer { { Satellite-Almanac-Information-ExtIEs} }		OPTIONAL,
			iE-Extensions		ProtocolExtensionContainer OPTIONAL,
			...
		},
	-- This GPS-Almanac-Information is for the 1st 16 satellites
	sVGlobalHealth-alm		BIT STRING (SIZE (364))		OPTIONAL,
--	iE-Extensions			ProtocolExtensionContainer { { GPS-Almanac-ExtIEs} }		OPTIONAL,
	iE-Extensions			ProtocolExtensionContainer OPTIONAL,
	...
}

--Satellite-Almanac-Information-ExtIEs RNSAP-PROTOCOL-EXTENSION ::= {
--	...
--} 

--GPS-Almanac-ExtIEs RNSAP-PROTOCOL-EXTENSION ::= {
--	{	ID id-Satellite-Almanac-Information-ExtItem	CRITICALITY	ignore		EXTENSION 	Satellite-Almanac-Information-ExtItem			PRESENCE	optional},
--	...
--}

Satellite-Almanac-Information-ExtItem ::= SEQUENCE (SIZE (1..16)) OF
		SEQUENCE {
			dATA-ID				DATA-ID,
			sAT-ID				SAT-ID,
			gps-e-alm			BIT STRING (SIZE (16)),
			gps-toa-alm			BIT STRING (SIZE (8)), 
			gps-delta-I-alm		BIT STRING (SIZE (16)),
			omegadot-alm		BIT STRING (SIZE (16)),
			svhealth-alm		BIT STRING (SIZE (8)),
			gps-a-sqrt-alm		BIT STRING (SIZE (24)),
			omegazero-alm		BIT STRING (SIZE (24)),
			m-zero-alm			BIT STRING (SIZE (24)),
			gps-omega-alm		BIT STRING (SIZE (24)),
			gps-af-zero-alm		BIT STRING (SIZE (11)),
			gps-af-one-alm		BIT STRING (SIZE (11)),
--			iE-Extensions		ProtocolExtensionContainer { { Satellite-Almanac-Information-ExtItemIEs} }		OPTIONAL,
			iE-Extensions		ProtocolExtensionContainer OPTIONAL,
			...
		}
--	Includes the GPS-Almanac-Information for the 17th through 32nd satellites.

--Satellite-Almanac-Information-ExtItemIEs RNSAP-PROTOCOL-EXTENSION ::= {
--	...
--}

GPSInformation ::= SEQUENCE (SIZE (1..8)) OF
	SEQUENCE {
		gPSInformationItem		ENUMERATED {
			gPS-NavigationModel-and-TimeRecovery,
			gPS-Ionospheric-Model,
			gPS-UTC-Model,
			gPS-Almanac,
			gPS-RealTime-Integrity,
			...
		},
--		iE-Extensions			ProtocolExtensionContainer { { GPSInformation-ExtIEs} }		OPTIONAL,
		iE-Extensions			ProtocolExtensionContainer OPTIONAL,
		...
	}
-- This IE shall be present if the Information Type IE indicates ‘GPS Information’

--GPSInformation-ExtIEs RNSAP-PROTOCOL-EXTENSION ::= {
--	...
--}

GPS-Ionospheric-Model ::= SEQUENCE {
	alpha-zero-ionos		BIT STRING (SIZE (8)),
	alpha-one-ionos			BIT STRING (SIZE (8)),
	alpha-two-ionos			BIT STRING (SIZE (8)),
	alpha-three-ionos		BIT STRING (SIZE (8)),
	beta-zero-ionos			BIT STRING (SIZE (8)),
	beta-one-ionos			BIT STRING (SIZE (8)),
	beta-two-ionos			BIT STRING (SIZE (8)),
	beta-three-ionos		BIT STRING (SIZE (8)),
--	iE-Extensions			ProtocolExtensionContainer { { GPS-Ionospheric-Model-ExtIEs} }		OPTIONAL,
	iE-Extensions			ProtocolExtensionContainer OPTIONAL,
	...
}

--GPS-Ionospheric-Model-ExtIEs RNSAP-PROTOCOL-EXTENSION ::= {
--	...
--}

GPS-NavigationModel-and-TimeRecovery ::= SEQUENCE (SIZE (1..16)) OF
	SEQUENCE {
		tx-tow-nav						INTEGER (0..1048575),
		sAT-ID							SAT-ID,
		tlm-message-nav					BIT STRING (SIZE (14)),
		tlm-revd-c-nav					BIT STRING (SIZE (2)),
		ho-word-nav						BIT STRING (SIZE (22)),
		w-n-nav							BIT STRING (SIZE (10)),
		ca-or-p-on-l2-nav				BIT STRING (SIZE (2)),
		user-range-accuracy-index-nav	BIT STRING (SIZE (4)),
		sv-health-nav					BIT STRING (SIZE (6)),
		iodc-nav						BIT STRING (SIZE (10)),
		l2-p-dataflag-nav				BIT STRING (SIZE (1)),
		sf1-reserved-nav				BIT STRING (SIZE (87)),
		t-gd-nav						BIT STRING (SIZE (8)),
		t-oc-nav						BIT STRING (SIZE (16)),
		a-f-2-nav						BIT STRING (SIZE (8)),
		a-f-1-nav						BIT STRING (SIZE (16)),
		a-f-zero-nav					BIT STRING (SIZE (22)),
		c-rs-nav						BIT STRING (SIZE (16)),
		delta-n-nav						BIT STRING (SIZE (16)),
		m-zero-nav						BIT STRING (SIZE (32)),
		c-uc-nav						BIT STRING (SIZE (16)),
		gps-e-nav						BIT STRING (SIZE (32)),
		c-us-nav						BIT STRING (SIZE (16)),
		a-sqrt-nav						BIT STRING (SIZE (32)),
		t-oe-nav						BIT STRING (SIZE (16)),
		fit-interval-flag-nav			BIT STRING (SIZE (1)),
		aodo-nav						BIT STRING (SIZE (5)),
		c-ic-nav						BIT STRING (SIZE (16)),
		omega-zero-nav					BIT STRING (SIZE (32)),
		c-is-nav						BIT STRING (SIZE (16)),
		i-zero-nav						BIT STRING (SIZE (32)),
		c-rc-nav						BIT STRING (SIZE (16)),
		gps-omega-nav					BIT STRING (SIZE (32)),
		omegadot-nav					BIT STRING (SIZE (24)),
		idot-nav						BIT STRING (SIZE (14)),
		spare-zero-fill					BIT STRING (SIZE (20)),
--		iE-Extensions					ProtocolExtensionContainer { { GPS-NavigationModel-and-TimeRecoveryItem-ExtIEs} }		OPTIONAL,
		iE-Extensions					ProtocolExtensionContainer OPTIONAL,
		...
	}

--GPS-NavigationModel-and-TimeRecoveryItem-ExtIEs RNSAP-PROTOCOL-EXTENSION ::= {
--	...
--}

GPS-RealTime-Integrity ::= CHOICE {
	badSatellites				BadSatellites,
	noBadSatellite				NULL
}

GPS-RX-POS ::= SEQUENCE {
	geographicalCoordinate		GeographicalCoordinate,
	altitudeAndDirection		GA-AltitudeAndDirection,
--	iE-Extensions				ProtocolExtensionContainer { { GPS-RX-POS-ExtIEs} } OPTIONAL,
	iE-Extensions				ProtocolExtensionContainer OPTIONAL,
	...
}

--GPS-RX-POS-ExtIEs RNSAP-PROTOCOL-EXTENSION ::= {
--	...
--}

GPS-Status-Health ::= ENUMERATED {
	udre-1-0,
	udre-0-75,
	udre-0-5,
	udre-0-3,
	udre-0-1,
	no-data,
	invalid-data
}

GPSTOW ::= INTEGER (0..604799)

GPS-UTC-Model ::= SEQUENCE {
	a-one-utc				BIT STRING (SIZE (24)),
	a-zero-utc				BIT STRING (SIZE (32)),
	t-ot-utc				BIT STRING (SIZE (8)),
	delta-t-ls-utc			BIT STRING (SIZE (8)),
	w-n-t-utc				BIT STRING (SIZE (8)),
	w-n-lsf-utc				BIT STRING (SIZE (8)),
	dn-utc					BIT STRING (SIZE (8)),
	delta-t-lsf-utc			BIT STRING (SIZE (8)),
--	iE-Extensions			ProtocolExtensionContainer { { GPS-UTC-Model-ExtIEs} }		OPTIONAL,
	iE-Extensions			ProtocolExtensionContainer OPTIONAL,
	...
}

--GPS-UTC-Model-ExtIEs RNSAP-PROTOCOL-EXTENSION ::= {
--	...
--}

Guaranteed-Rate-Information	::= SEQUENCE {
	guaranteed-UL-Rate			Guaranteed-Rate OPTIONAL,
	guaranteed-DL-Rate			Guaranteed-Rate OPTIONAL,
--	iE-Extensions				ProtocolExtensionContainer { {Guaranteed-Rate-Information-ExtIEs} } OPTIONAL,
	iE-Extensions				ProtocolExtensionContainer OPTIONAL,
	...
}

--Guaranteed-Rate-Information-ExtIEs RNSAP-PROTOCOL-EXTENSION ::= {
--	...
--}

Guaranteed-Rate			::= INTEGER (1..32)
-- "1": TFI 0, "2": TFI 1, "3": TFI 2, ...

-- H

HARQ-MemoryPartitioning	::= CHOICE {
	implicit		HARQ-MemoryPartitioning-Implicit,
	explicit		HARQ-MemoryPartitioning-Explicit,
	...
	}

HARQ-MemoryPartitioning-Implicit	::= SEQUENCE {
	number-of-Processes			INTEGER (1..8,...),
--	iE-Extensions				ProtocolExtensionContainer { { HARQ-MemoryPartitioning-Implicit-ExtIEs } }			OPTIONAL,
	iE-Extensions				ProtocolExtensionContainer OPTIONAL,
	...
}

--HARQ-MemoryPartitioning-Implicit-ExtIEs RNSAP-PROTOCOL-EXTENSION ::= {
--	...
--}

HARQ-MemoryPartitioning-Explicit	::= SEQUENCE {
	hARQ-MemoryPartitioningList			HARQ-MemoryPartitioningList,
--	iE-Extensions						ProtocolExtensionContainer { { HARQ-MemoryPartitioning-Explicit-ExtIEs } }			OPTIONAL,
	iE-Extensions						ProtocolExtensionContainer OPTIONAL,
	...
}

--HARQ-MemoryPartitioning-Explicit-ExtIEs RNSAP-PROTOCOL-EXTENSION ::= {
--	...
--}

HARQ-MemoryPartitioningList	::= SEQUENCE (SIZE (1..8)) OF HARQ-MemoryPartitioningItem

HARQ-MemoryPartitioningItem ::= SEQUENCE {
	process-Memory-Size					ENUMERATED {
										hms800, hms1600, hms2400, hms3200, hms4000,
										hms4800, hms5600, hms6400, hms7200, hms8000,
										hms8800, hms9600, hms10400, hms11200, hms12000,
										hms12800, hms13600, hms14400, hms15200, hms16000,
										hms17600, hms19200, hms20800, hms22400, hms24000,
										hms25600, hms27200, hms28800, hms30400, hms32000,
										hms36000, hms40000, hms44000, hms48000, hms52000,
										hms56000, hms60000, hms64000, hms68000, hms72000,
										hms76000, hms80000, hms88000, hms96000, hms104000,
										hms112000, hms120000, hms128000, hms136000, hms144000,
										hms152000, hms160000, hms176000, hms192000, hms208000,
										hms224000, hms240000, hms256000, hms272000, hms288000,
										hms304000,...},
--	iE-Extensions						ProtocolExtensionContainer { { HARQ-MemoryPartitioningItem-ExtIEs } }			OPTIONAL,
	iE-Extensions						ProtocolExtensionContainer OPTIONAL,
	...
}

--HARQ-MemoryPartitioningItem-ExtIEs RNSAP-PROTOCOL-EXTENSION ::= {
--	...
--}

HARQ-Preamble-Mode ::= ENUMERATED {
mode0,
mode1
}

HARQ-Process-Allocation-2ms-EDCH ::= BIT STRING ( SIZE(8) )

HARQ-Preamble-Mode-Activation-Indicator	::=ENUMERATED	{
	harqPreambleModeSupported
}

HCS-Prio	::= INTEGER (0..7)
-- 0 = lowest priority, ...7 = highest priority

HSDSCH-FDD-Information ::= SEQUENCE {
	hSDSCH-MACdFlows-Information				HSDSCH-MACdFlows-Information,
	uE-Capabilities-Info						UE-Capabilities-Info,
	mAChs-Reordering-Buffer-Size-for-RLC-UM		MAChsReorderingBufferSize-for-RLC-UM,
	cqiFeedback-CycleK							CQI-Feedback-Cycle,
	cqiRepetitionFactor							CQI-RepetitionFactor						OPTIONAL,
	-- This IE shall be present if the CQI Feedback Cycle k IE is set to a value greater than 0.
	ackNackRepetitionFactor						AckNack-RepetitionFactor,
	cqiPowerOffset								CQI-Power-Offset,
	ackPowerOffset								Ack-Power-Offset,
	nackPowerOffset								Nack-Power-Offset,
	hsscch-PowerOffset							HSSCCH-PowerOffset							OPTIONAL,
--	iE-Extensions								ProtocolExtensionContainer { { HSDSCH-FDD-Information-ExtIEs } }			OPTIONAL,
	iE-Extensions								ProtocolExtensionContainer OPTIONAL,
	...
}

--HSDSCH-FDD-Information-ExtIEs RNSAP-PROTOCOL-EXTENSION ::= {
--{ ID id-HARQ-Preamble-Mode 	CRITICALITY reject		EXTENSION	HARQ-Preamble-Mode	PRESENCE optional},
--	...
--}

HSDSCH-FDD-Information-Response ::= SEQUENCE {
	hSDSCH-MACdFlow-Specific-InfoList-Response		HSDSCH-MACdFlow-Specific-InfoList-Response													OPTIONAL,
	hSSCCH-Specific-InfoList-Response				HSSCCH-FDD-Specific-InfoList-Response														OPTIONAL,
	hSPDSCH-and-HSSCCH-ScramblingCode				DL-ScramblingCode														OPTIONAL,
	measurement-Power-Offset						Measurement-Power-Offset																	OPTIONAL,
	hARQ-MemoryPartitioning							HARQ-MemoryPartitioning																		OPTIONAL,
--	iE-Extensions									ProtocolExtensionContainer { { HSDSCH-FDD-Information-Response-ExtIEs } }		OPTIONAL,
	iE-Extensions									ProtocolExtensionContainer OPTIONAL,
	...
}

--HSDSCH-FDD-Information-Response-ExtIEs RNSAP-PROTOCOL-EXTENSION ::= {
--{ ID id-User-Plane-Congestion-Fields-Inclusion		CRITICALITY ignore	EXTENSION User-Plane-Congestion-Fields-Inclusion		PRESENCE optional}|
--{ ID id-HARQ-Preamble-Mode-Activation-Indicator		CRITICALITY ignore	EXTENSION HARQ-Preamble-Mode-Activation-Indicator		PRESENCE optional},
--	...
--}

HSDSCH-Information-to-Modify ::= SEQUENCE {
	hSDSCH-MACdFlow-Specific-InfoList-to-Modify		HSDSCH-MACdFlow-Specific-InfoList-to-Modify			OPTIONAL,
	priorityQueue-Info-to-Modify					PriorityQueue-InfoList-to-Modify					OPTIONAL,
	mAChs-Reordering-Buffer-Size-for-RLC-UM			MAChsReorderingBufferSize-for-RLC-UM				OPTIONAL,
	cqiFeedback-CycleK								CQI-Feedback-Cycle									OPTIONAL, 	-- For FDD only
	cqiRepetitionFactor								CQI-RepetitionFactor								OPTIONAL, 	-- For FDD only
	ackNackRepetitionFactor							AckNack-RepetitionFactor							OPTIONAL, 	-- For FDD only
	cqiPowerOffset									CQI-Power-Offset									OPTIONAL,	-- For FDD only
	ackPowerOffset									Ack-Power-Offset									OPTIONAL,	-- For FDD only
	nackPowerOffset									Nack-Power-Offset									OPTIONAL,	-- For FDD only
	hsscch-PowerOffset								HSSCCH-PowerOffset									OPTIONAL,	-- For FDD only
	hSSCCH-CodeChangeGrant							HSSCCH-Code-Change-Grant							OPTIONAL,
	tDDAckNackPowerOffset							TDD-AckNack-Power-Offset							OPTIONAL,	-- For TDD only
--	iE-Extensions									ProtocolExtensionContainer { { HSDSCH-Information-to-Modify-ExtIEs } }			OPTIONAL,
	iE-Extensions									ProtocolExtensionContainer OPTIONAL,
	...
}

--HSDSCH-Information-to-Modify-ExtIEs RNSAP-PROTOCOL-EXTENSION ::= {
--{ ID id-HARQ-Preamble-Mode 	CRITICALITY reject		EXTENSION	HARQ-Preamble-Mode	PRESENCE optional},
--	...
--}

HSDSCH-Information-to-Modify-Unsynchronised ::= SEQUENCE {
	hSDSCH-MACdFlow-Specific-InfoList-to-Modify		HSDSCH-MACdFlow-Specific-InfoList-to-Modify					OPTIONAL,
	priorityQueueInfotoModifyUnsynchronised			PriorityQueue-InfoList-to-Modify-Unsynchronised		OPTIONAL,
	cqiPowerOffset									CQI-Power-Offset				OPTIONAL,	-- For FDD only
	ackPowerOffset									Ack-Power-Offset				OPTIONAL,	-- For FDD only
	nackPowerOffset									Nack-Power-Offset				OPTIONAL,	-- For FDD only
	hsscch-PowerOffset								HSSCCH-PowerOffset				OPTIONAL,	-- Only for FDD
	tDDAckNackPowerOffset							TDD-AckNack-Power-Offset		OPTIONAL,	-- For TDD only
--	iE-Extensions									ProtocolExtensionContainer { { HSDSCH-Information-to-Modify-Unsynchronised-ExtIEs } }			OPTIONAL,
	iE-Extensions									ProtocolExtensionContainer OPTIONAL,
	...
}

--HSDSCH-Information-to-Modify-Unsynchronised-ExtIEs RNSAP-PROTOCOL-EXTENSION ::= {
--{ ID id-HARQ-Preamble-Mode 	CRITICALITY reject		EXTENSION	HARQ-Preamble-Mode	PRESENCE optional},
--	...
--}

HSDSCH-MACdFlow-ID ::= INTEGER (0..7)

HSDSCH-MACdFlow-Specific-InfoList ::= SEQUENCE (SIZE (1..8)) OF HSDSCH-MACdFlow-Specific-InfoItem

HSDSCH-MACdFlow-Specific-InfoItem ::= SEQUENCE {
	hSDSCH-MACdFlow-ID					HSDSCH-MACdFlow-ID,
	allocationRetentionPriority			AllocationRetentionPriority,
	trafficClass						TrafficClass,
	bindingID							BindingID								OPTIONAL,
	transportLayerAddress				TransportLayerAddress					OPTIONAL,
--	iE-Extensions						ProtocolExtensionContainer { { HSDSCH-MACdFlow-Specific-InfoItem-ExtIEs } }			OPTIONAL,
	iE-Extensions						ProtocolExtensionContainer OPTIONAL,
	...
}

--HSDSCH-MACdFlow-Specific-InfoItem-ExtIEs RNSAP-PROTOCOL-EXTENSION ::= {
--	...
--}

HSDSCH-MACdFlow-Specific-InfoList-Response ::= SEQUENCE (SIZE (0..8)) OF HSDSCH-MACdFlow-Specific-InfoItem-Response

HSDSCH-MACdFlow-Specific-InfoItem-Response ::= SEQUENCE {
	hSDSCH-MACdFlow-ID					HSDSCH-MACdFlow-ID,
	bindingID							BindingID								OPTIONAL,
	transportLayerAddress				TransportLayerAddress					OPTIONAL,
	hSDSCH-Initial-Capacity-Allocation	HSDSCH-Initial-Capacity-Allocation		OPTIONAL,
--	iE-Extensions						ProtocolExtensionContainer { { HSDSCH-MACdFlow-Specific-InfoItem-Response-ExtIEs } }			OPTIONAL,
	iE-Extensions						ProtocolExtensionContainer OPTIONAL,
	...
}

--HSDSCH-MACdFlow-Specific-InfoItem-Response-ExtIEs RNSAP-PROTOCOL-EXTENSION ::= {
--	...
--}

HSDSCH-MACdFlow-Specific-InfoList-to-Modify ::= SEQUENCE (SIZE (1..8)) OF HSDSCH-MACdFlow-Specific-InfoItem-to-Modify

HSDSCH-MACdFlow-Specific-InfoItem-to-Modify ::= SEQUENCE {
	hSDSCH-MACdFlow-ID					HSDSCH-MACdFlow-ID,
	allocationRetentionPriority			AllocationRetentionPriority				OPTIONAL,
	transportBearerRequestIndicator		TransportBearerRequestIndicator,
	trafficClass						TrafficClass							OPTIONAL,
	bindingID							BindingID								OPTIONAL,
	transportLayerAddress				TransportLayerAddress					OPTIONAL,
--	iE-Extensions						ProtocolExtensionContainer { { HSDSCH-MACdFlow-Specific-InfoItem-to-Modify-ExtIEs } }			OPTIONAL,
	iE-Extensions						ProtocolExtensionContainer OPTIONAL,
	...
}

--HSDSCH-MACdFlow-Specific-InfoItem-to-Modify-ExtIEs RNSAP-PROTOCOL-EXTENSION ::= {
--	...
--}

HSDSCH-MACdFlows-Information ::= SEQUENCE {
	hSDSCH-MACdFlow-Specific-Info					HSDSCH-MACdFlow-Specific-InfoList,
	priorityQueue-Info								PriorityQueue-InfoList,
--	iE-Extensions									ProtocolExtensionContainer { { HSDSCH-MACdFlows-Information-ExtIEs } }			OPTIONAL,
	iE-Extensions									ProtocolExtensionContainer OPTIONAL,
	...
}


--HSDSCH-MACdFlows-Information-ExtIEs RNSAP-PROTOCOL-EXTENSION ::= {
--	...
--}

HSDSCH-MACdFlows-to-Delete ::= SEQUENCE (SIZE (1..8)) OF HSDSCH-MACdFlows-to-Delete-Item

HSDSCH-MACdFlows-to-Delete-Item ::= SEQUENCE {
	hsDSCH-MACdFlow-ID					HSDSCH-MACdFlow-ID,
--	iE-Extensions						ProtocolExtensionContainer { { HSDSCH-MACdFlows-to-Delete-Item-ExtIEs} }		OPTIONAL,
	iE-Extensions						ProtocolExtensionContainer OPTIONAL,
	...
}

--HSDSCH-MACdFlows-to-Delete-Item-ExtIEs RNSAP-PROTOCOL-EXTENSION ::= {
--	...
--}

HSDSCH-Initial-Capacity-Allocation::= SEQUENCE (SIZE (1..8)) OF HSDSCH-Initial-Capacity-AllocationItem

HSDSCH-Initial-Capacity-AllocationItem ::= SEQUENCE {
	schedulingPriorityIndicator		SchedulingPriorityIndicator,
	maximum-MACdPDU-Size			MACdPDU-Size,
	hSDSCH-InitialWindowSize		HSDSCH-InitialWindowSize,
--	iE-Extensions					ProtocolExtensionContainer { {HSDSCH-Initial-Capacity-AllocationItem-ExtIEs} } OPTIONAL,
	iE-Extensions					ProtocolExtensionContainer OPTIONAL,
	...
}

--HSDSCH-Initial-Capacity-AllocationItem-ExtIEs RNSAP-PROTOCOL-EXTENSION ::= {
--	...
--}

HSDSCH-InitialWindowSize			::= INTEGER (1..255)
-- Number of MAC-d PDUs.

HSDSCH-RNTI ::= INTEGER (0..65535)

HSDSCH-TDD-Information ::= SEQUENCE {
	hSDSCH-MACdFlows-Information				HSDSCH-MACdFlows-Information,
	uE-Capabilities-Info						UE-Capabilities-Info,
	mAChs-Reordering-Buffer-Size-for-RLC-UM		MAChsReorderingBufferSize-for-RLC-UM,
	tDD-AckNack-Power-Offset					TDD-AckNack-Power-Offset,
--	iE-Extensions								ProtocolExtensionContainer { { HSDSCH-TDD-Information-ExtIEs } }			OPTIONAL,
	iE-Extensions								ProtocolExtensionContainer OPTIONAL,
	...
}

--HSDSCH-TDD-Information-ExtIEs RNSAP-PROTOCOL-EXTENSION ::= {
--	...
--}

HSDSCH-TDD-Information-Response ::= SEQUENCE {
	hSDSCH-MACdFlow-Specific-InfoList-Response		HSDSCH-MACdFlow-Specific-InfoList-Response			OPTIONAL,
	hSSCCH-TDD-Specific-InfoList-Response			HSSCCH-TDD-Specific-InfoList-Response				OPTIONAL,
-- Not Applicable to 1.28Mcps TDD
	hSSCCH-TDD-Specific-InfoList-Response-LCR		HSSCCH-TDD-Specific-InfoList-Response-LCR			OPTIONAL,
-- Not Applicable to 3.84Mcps TDD
	hSPDSCH-TDD-Specific-InfoList-Response			HSPDSCH-TDD-Specific-InfoList-Response				OPTIONAL,
	hSPDSCH-TDD-Specific-InfoList-Response-LCR		HSPDSCH-TDD-Specific-InfoList-Response-LCR			OPTIONAL,
	hARQ-MemoryPartitioning							HARQ-MemoryPartitioning								OPTIONAL,
--	iE-Extensions									ProtocolExtensionContainer { { HSDSCH-TDD-Information-Response-ExtIEs } }			OPTIONAL,
	iE-Extensions									ProtocolExtensionContainer OPTIONAL,
	...
}

--HSDSCH-TDD-Information-Response-ExtIEs RNSAP-PROTOCOL-EXTENSION ::= {
--{ ID id-User-Plane-Congestion-Fields-Inclusion	CRITICALITY ignore	EXTENSION User-Plane-Congestion-Fields-Inclusion		PRESENCE optional},
--	...
--}

HSPDSCH-TDD-Specific-InfoList-Response ::= SEQUENCE (SIZE (0..15)) OF HSPDSCH-TDD-Specific-InfoItem-Response

HSPDSCH-TDD-Specific-InfoItem-Response ::= SEQUENCE {
	timeslot										TimeSlot,
	midambleShiftAndBurstType						MidambleShiftAndBurstType,
--	iE-Extensions									ProtocolExtensionContainer { { HSPDSCH-TDD-Specific-InfoItem-Response-ExtIEs } }			OPTIONAL,
	iE-Extensions									ProtocolExtensionContainer OPTIONAL,
	...
}

--HSPDSCH-TDD-Specific-InfoItem-Response-ExtIEs RNSAP-PROTOCOL-EXTENSION ::= {
--	...
--}

HSPDSCH-TDD-Specific-InfoList-Response-LCR ::= SEQUENCE (SIZE (1.. 6)) OF HSPDSCH-TDD-Specific-InfoItem-Response-LCR

HSPDSCH-TDD-Specific-InfoItem-Response-LCR ::= SEQUENCE {
	timeslotLCR									TimeSlotLCR,
	midambleShiftLCR							MidambleShiftLCR,
--	iE-Extensions								ProtocolExtensionContainer { { HSPDSCH-TDD-Specific-InfoItem-Response-LCR-ExtIEs } }			OPTIONAL,
	iE-Extensions								ProtocolExtensionContainer OPTIONAL,
	...
}

--HSPDSCH-TDD-Specific-InfoItem-Response-LCR-ExtIEs RNSAP-PROTOCOL-EXTENSION ::= {
--	...
--}

HSSCCH-FDD-Specific-InfoList-Response ::= SEQUENCE (SIZE (0..4)) OF HSSCCH-FDD-Specific-InfoItem-Response

HSSCCH-FDD-Specific-InfoItem-Response ::= SEQUENCE {
	code-Number										INTEGER (0..127),
--	iE-Extensions									ProtocolExtensionContainer { { HSSCCH-FDD-Specific-InfoItem-Response-ExtIEs } }			OPTIONAL,
	iE-Extensions									ProtocolExtensionContainer OPTIONAL,
	...
}

--HSSCCH-FDD-Specific-InfoItem-Response-ExtIEs RNSAP-PROTOCOL-EXTENSION ::= {
--	...
--}

HSSCCH-PowerOffset ::= INTEGER (0..255)
-- PowerOffset = -32 + offset * 0.25
-- Unit dB, Range -32dB .. +31.75dB, Step +0.25dB

HSSCCH-TDD-Specific-InfoList-Response ::= SEQUENCE (SIZE (0..4)) OF HSSCCH-TDD-Specific-InfoItem-Response

HSSCCH-TDD-Specific-InfoItem-Response ::= SEQUENCE {
	timeslot										TimeSlot,
	midambleShiftAndBurstType						MidambleShiftAndBurstType,
	tDD-ChannelisationCode							TDD-ChannelisationCode,
	hSSICH-Info										HSSICH-Info,
--	iE-Extensions									ProtocolExtensionContainer { { HSSCCH-TDD-Specific-InfoItem-Response-ExtIEs } }			OPTIONAL,
	iE-Extensions									ProtocolExtensionContainer OPTIONAL,
	...
}

--HSSCCH-TDD-Specific-InfoItem-Response-ExtIEs RNSAP-PROTOCOL-EXTENSION ::= {
--	...
--}

HSSCCH-TDD-Specific-InfoList-Response-LCR ::= SEQUENCE (SIZE (0..4)) OF HSSCCH-TDD-Specific-InfoItem-Response-LCR

HSSCCH-TDD-Specific-InfoItem-Response-LCR ::= SEQUENCE {
	timeslotLCR									TimeSlotLCR,
	midambleShiftLCR							MidambleShiftLCR,
	first-TDD-ChannelisationCode				TDD-ChannelisationCode,
	second-TDD-ChannelisationCode			TDD-ChannelisationCode,
	hSSICH-InfoLCR								HSSICH-InfoLCR,
--	iE-Extensions								ProtocolExtensionContainer { { HSSCCH-TDD-Specific-InfoItem-Response-LCR-ExtIEs } }			OPTIONAL,
	iE-Extensions								ProtocolExtensionContainer OPTIONAL,
	...
}

--HSSCCH-TDD-Specific-InfoItem-Response-LCR-ExtIEs RNSAP-PROTOCOL-EXTENSION ::= {
--	...
--}

HSSICH-Info ::= SEQUENCE {
	hsSICH-ID										HS-SICH-ID,
	timeslot										TimeSlot,
	midambleShiftAndBurstType						MidambleShiftAndBurstType,
	tDD-ChannelisationCode							TDD-ChannelisationCode,
--	iE-Extensions									ProtocolExtensionContainer { { HSSICH-Info-ExtIEs } }			OPTIONAL,
	iE-Extensions									ProtocolExtensionContainer OPTIONAL,
	...
}

--HSSICH-Info-ExtIEs RNSAP-PROTOCOL-EXTENSION ::= {
--	...
--}

HSSICH-InfoLCR ::= SEQUENCE {
	hsSICH-ID										HS-SICH-ID,
	timeslotLCR										TimeSlotLCR,
	midambleShiftLCR								MidambleShiftLCR,
	tDD-ChannelisationCode						TDD-ChannelisationCode,
--	iE-Extensions									ProtocolExtensionContainer { { HSSICH-Info-LCR-ExtIEs } }			OPTIONAL,
	iE-Extensions									ProtocolExtensionContainer OPTIONAL,
	...
}

--HSSICH-Info-LCR-ExtIEs RNSAP-PROTOCOL-EXTENSION ::= {
--	...
--}

HS-SICH-Reception-Quality-Value ::= SEQUENCE {
	failed-HS-SICH				HS-SICH-failed,
	missed-HS-SICH				HS-SICH-missed,
	total-HS-SICH				HS-SICH-total,
--	iE-Extensions				ProtocolExtensionContainer { { HS-SICH-Reception-Quality-Value-ExtIEs} } OPTIONAL,
	iE-Extensions				ProtocolExtensionContainer OPTIONAL,
	...
}

--HS-SICH-Reception-Quality-Value-ExtIEs RNSAP-PROTOCOL-EXTENSION ::= {
--	...
--}

HS-SICH-failed ::= INTEGER (0..20)

HS-SICH-missed ::= INTEGER (0..20)

HS-SICH-total ::= INTEGER (0..20)

HS-SICH-Reception-Quality-Measurement-Value ::= INTEGER (0..20)
-- According to mapping in [23]

HS-SICH-ID ::= INTEGER (0..31)

HSSCCH-CodeChangeIndicator	::= ENUMERATED {
	hsSCCHCodeChangeNeeded
}

HSSCCH-Code-Change-Grant	::= ENUMERATED {
	changeGranted
}

HSDSCH-FDD-Update-Information ::= SEQUENCE {
	hsSCCHCodeChangeIndicator						HSSCCH-CodeChangeIndicator					OPTIONAL,
	cqiFeedback-CycleK								CQI-Feedback-Cycle							OPTIONAL, 
	cqiRepetitionFactor								CQI-RepetitionFactor						OPTIONAL,
	ackNackRepetitionFactor							AckNack-RepetitionFactor					OPTIONAL,
	cqiPowerOffset									CQI-Power-Offset 							OPTIONAL,
	ackPowerOffset									Ack-Power-Offset							OPTIONAL,
	nackPowerOffset									Nack-Power-Offset							OPTIONAL,
--	iE-Extensions									ProtocolExtensionContainer { { HSDSCH-FDD-Update-Information-ExtIEs } }		OPTIONAL,
	iE-Extensions									ProtocolExtensionContainer OPTIONAL,
	...
}

--HSDSCH-FDD-Update-Information-ExtIEs RNSAP-PROTOCOL-EXTENSION ::= {
--	...
--}

HSDSCH-TDD-Update-Information ::= SEQUENCE {
	hsSCCHCodeChangeIndicator						HSSCCH-CodeChangeIndicator					OPTIONAL,
	tDDAckNackPowerOffset							TDD-AckNack-Power-Offset					OPTIONAL,
--	iE-Extensions									ProtocolExtensionContainer { { HSDSCH-TDD-Update-Information-ExtIEs } }		OPTIONAL,
	iE-Extensions									ProtocolExtensionContainer OPTIONAL,
	...
}

--HSDSCH-TDD-Update-Information-ExtIEs RNSAP-PROTOCOL-EXTENSION ::= {
--	...
--}

-- I

IMEI		::= OCTET STRING (SIZE(8))

IMEISV		::= OCTET STRING (SIZE(8))

IMSI		::= OCTET STRING (SIZE(3..8))

InformationAvailable::= SEQUENCE {
	requestedDataValue		RequestedDataValue,
--	iE-Extensions			ProtocolExtensionContainer { { InformationAvailable-ExtIEs} }		OPTIONAL,
	iE-Extensions			ProtocolExtensionContainer OPTIONAL,
	...
}

--InformationAvailable-ExtIEs RNSAP-PROTOCOL-EXTENSION ::= {
--	...
--}

InformationExchangeID ::= INTEGER (0..1048575)

InformationNotAvailable ::= NULL

InformationReportCharacteristics ::= CHOICE {
	onDemand				NULL,
	periodic				PeriodicInformation,
	onModification			OnModificationInformation,
	...
}

InformationReportPeriodicity ::= CHOICE {
	min				INTEGER (1..60,...),
-- Unit min, Step 1min
	hour			INTEGER (1..24,...),
-- Unit hour, Step 1hour
	...
}

InformationThreshold ::= CHOICE {
	dGPSThreshold		DGPSThreshold,
	...
} 


InformationType ::= SEQUENCE {
	informationTypeItem		ENUMERATED {
		gA-AccessPointPositionwithAltitude,
		gA-AccessPointPosition,
		iPDLParameters,
		gPSInformation,
		dGPSCorrections,
		gPS-RX-POS,
		sFNSFN-GA-AccessPointPosition,
		...,
		cell-Capacity-Class,
		nACC-Related-Data,
		mBMSBearerServiceFullAddress
	},
	gPSInformation				GPSInformation			OPTIONAL,
--	iE-Extensions				ProtocolExtensionContainer { { InformationType-ExtIEs} }		OPTIONAL,
	iE-Extensions				ProtocolExtensionContainer OPTIONAL,
	...
}

-- The GPS Information IE shall be present if the Information Exchange Type IE indicates ‘GPS Information’
-- For information exchange on the Iur-g interface, only the Cell Capacity Class is used.

--InformationType-ExtIEs RNSAP-PROTOCOL-EXTENSION ::= {
--	...
--}

Initial-DL-DPCH-TimingAdjustment-Allowed ::= ENUMERATED {
	initial-DL-DPCH-TimingAdjustment-Allowed
}

InnerLoopDLPCStatus		::= ENUMERATED {active, inactive}

IPDLParameters ::= CHOICE {
	iPDL-FDD-Parameters			IPDL-FDD-Parameters,
	iPDL-TDD-Parameters			IPDL-TDD-Parameters, 	--3.84Mcps TDD only
	...,
	extension-IPDLParameters	Extension-IPDLParameters
}

--Extension-IPDLParameters	::=	ProtocolIE-Single-Container {{ Extension-IPDLParametersIE }}
Extension-IPDLParameters	::=	ProtocolIE-Single-Container

--Extension-IPDLParametersIE RNSAP-PROTOCOL-IES ::= {
--	{ ID id-IPDL-TDD-ParametersLCR	CRITICALITY reject	TYPE IPDL-TDD-ParametersLCR	PRESENCE mandatory },
--	...
--}

IPDL-FDD-Parameters ::= SEQUENCE {
	iPSpacingFDD				IPSpacingFDD,
	iPLength					IPLength,
	iPOffset					IPOffset,
	seed						Seed,
	burstModeParameters			BurstModeParameters		OPTIONAL,
--	iE-Extensions				ProtocolExtensionContainer { { IPDL-FDD-Parameters-ExtIEs} }		OPTIONAL,
	iE-Extensions				ProtocolExtensionContainer OPTIONAL,
	...
}

--IPDL-FDD-Parameters-ExtIEs RNSAP-PROTOCOL-EXTENSION ::= {
--	...
--}

IPDL-TDD-Parameters ::= SEQUENCE {
	iPSpacingTDD				IPSpacingTDD,
	iPStart						IPStart,
	iPSlot						IPSlot,
	iP-P-CCPCH					IP-P-CCPCH,
	burstModeParameters			BurstModeParameters		OPTIONAL,
--	iE-Extensions				ProtocolExtensionContainer { { IPDL-TDD-Parameters-ExtIEs} }		OPTIONAL,
	iE-Extensions				ProtocolExtensionContainer OPTIONAL,
	...
}

-- The BurstModeParameters IE shall be included if the Idle Periods are arranged in Burst Mode.

--IPDL-TDD-Parameters-ExtIEs RNSAP-PROTOCOL-EXTENSION ::= {
--	...
--}

IPDL-TDD-ParametersLCR ::= SEQUENCE {
	iPSpacingTDD				IPSpacingTDD,
	iPStart						IPStart,
	iPSub						IPSub,
	burstModeParameters			BurstModeParameters		OPTIONAL,
--	iE-Extensions				ProtocolExtensionContainer { { IPDL-TDD-ParametersLCR-ExtIEs} }		OPTIONAL,
	iE-Extensions				ProtocolExtensionContainer OPTIONAL,
	...
}

-- The BurstModeParameters IE shall be included if the Idle Periods are arranged in Burst Mode.

--IPDL-TDD-ParametersLCR-ExtIEs RNSAP-PROTOCOL-EXTENSION ::= {
--	...
--}

IPLength ::= ENUMERATED {
	ipl5,
	ipl10,
	...
}

IPMulticastAddress	::=	OCTET STRING (SIZE (4..16))

IPOffset ::= INTEGER (0..9)

IP-P-CCPCH ::= ENUMERATED {
	switchOff-1-Frame,
	switchOff-2-Frames
}

IPSlot ::= INTEGER (0..14)

IPSpacingFDD ::= ENUMERATED {
	ipsF5,
	ipsF7,
	ipsF10,
	ipsF15,
	ipsF20,
	ipsF30,
	ipsF40,
	ipsF50,
	...
}

IPSpacingTDD ::= ENUMERATED {
	ipsT30,
	ipsT40,
	ipsT50,
	ipsT70,
	ipsT100,
	...
}

IPStart ::= INTEGER (0..4095)

IPSub ::= ENUMERATED {
	first,
	second,
	both
}

-- J
-- K
-- L

LAC					::= OCTET STRING (SIZE (2)) --(EXCEPT ('0000'H|'FFFE'H))

LimitedPowerIncrease ::= ENUMERATED {
	used,
	not-used
}

L3-Information				::= BIT STRING

Load-Value-IncrDecrThres ::= INTEGER(0..100)

Load-Value ::= INTEGER(0..100)

LoadValue ::= SEQUENCE {
		uplinkLoadValue		INTEGER(0..100),
		downlinkLoadValue	INTEGER(0..100)
}

-- M
MaxNrOfUL-DPCHs				::= INTEGER (1..6)

MAC-c-sh-SDU-Length			::= INTEGER (1..5000)

MAC-c-sh-SDU-LengthList ::= SEQUENCE(SIZE(1..16)) OF MAC-c-sh-SDU-Length

MACdPDU-Size ::= INTEGER (1..5000,...)

MACdPDU-Size-IndexList ::= SEQUENCE (SIZE (1..8)) OF MACdPDU-Size-IndexItem

MACdPDU-Size-IndexItem ::= SEQUENCE {
	sID									SID,
	mACdPDU-Size						MACdPDU-Size,
--	iE-Extensions						ProtocolExtensionContainer { { MACdPDU-Size-IndexItem-ExtIEs } }			OPTIONAL,
	iE-Extensions						ProtocolExtensionContainer OPTIONAL,
	...
}

--MACdPDU-Size-IndexItem-ExtIEs RNSAP-PROTOCOL-EXTENSION ::= {
--	...
--}

MACdPDU-Size-IndexList-to-Modify ::= SEQUENCE (SIZE (1..8)) OF MACdPDU-Size-IndexItem-to-Modify

MACdPDU-Size-IndexItem-to-Modify ::= SEQUENCE {
	sID									SID,
	mACdPDU-Size						MACdPDU-Size,
--	iE-Extensions						ProtocolExtensionContainer { { MACdPDU-Size-IndexItem-to-Modify-ExtIEs } }			OPTIONAL,
	iE-Extensions						ProtocolExtensionContainer OPTIONAL,
	...
}

--MACdPDU-Size-IndexItem-to-Modify-ExtIEs RNSAP-PROTOCOL-EXTENSION ::= {
--	...
--}

MACes-Guaranteed-Bitrate ::= INTEGER (0..16777215,...)

MAChsGuaranteedBitRate ::= INTEGER (0..16777215,...)

MAChsReorderingBufferSize-for-RLC-UM ::= INTEGER (0..300,...)
-- Unit kBytes

MAC-hsWindowSize		::= ENUMERATED {v4, v6, v8, v12, v16, v24, v32,...}

MaximumAllowedULTxPower		::= INTEGER (-50..33)

Max-Bits-MACe-PDU-non-scheduled ::= INTEGER(1..19982)

MaxNrDLPhysicalchannels 	::= INTEGER (1..224)
-- 1.28Mcps TDD 97 - 224 are unused

MaxNrDLPhysicalchannelsTS 	::= INTEGER (1..16)

MaxNr-Retransmissions-EDCH  ::= INTEGER (0..15)

MaxNrTimeslots 				::= INTEGER (1..14)
-- 1.28Mcps values 7-14 are unused


MaxNrULPhysicalchannels 	::= INTEGER (1..2)

Max-Set-E-DPDCHs ::= ENUMERATED {
	vN64, vN32, vN16, vN8, vN4, v2xN4, v2xN2, v2xN2plus2xN4,
	...
	}
-- Values releated to [9]


MBMS-Bearer-Service-Full-Address ::= SEQUENCE {
	accessPointName							AccessPointName,
	iPMulticastAddress						IPMulticastAddress,
--	iE-Extensions						ProtocolExtensionContainer { { MBMS-Bearer-Service-Full-Address-ExtIEs } }			OPTIONAL,
	iE-Extensions						ProtocolExtensionContainer OPTIONAL,
	...
}

--MBMS-Bearer-Service-Full-Address-ExtIEs RNSAP-PROTOCOL-EXTENSION ::= {
--	...
--}

MBMS-Bearer-Service-List	::=	SEQUENCE (SIZE (1..128)) OF TMGI

MBMS-Bearer-ServiceItemFDD	::=SEQUENCE{
	tmgi	TMGI,
	transmissionMode 	TransmissionMode,
--	iE-Extensions					ProtocolExtensionContainer { { MBMS-Bearer-ServiceItemFDD-ExtIEs} } OPTIONAL,
	iE-Extensions					ProtocolExtensionContainer OPTIONAL,
	...
}


--MBMS-Bearer-ServiceItemFDD-ExtIEs RNSAP-PROTOCOL-EXTENSION ::= {
--	...
--}

MBMS-Bearer-ServiceItemFDD-PFL	::=SEQUENCE{
	tmgi	TMGI,
	transmissionMode 		TransmissionMode	OPTIONAL,
	preferredFrequencyLayer		UARFCN			OPTIONAL,
--	iE-Extensions					ProtocolExtensionContainer { { MBMS-Bearer-ServiceItemFDD-PFL-ExtIEs} } OPTIONAL,
	iE-Extensions					ProtocolExtensionContainer OPTIONAL,
	...
}

--MBMS-Bearer-ServiceItemFDD-PFL-ExtIEs RNSAP-PROTOCOL-EXTENSION ::= {
--	...
--}

MBMS-Bearer-ServiceItemTDD	::=SEQUENCE{
	tmgi	TMGI,
	transmissionMode 	TransmissionMode,
--	iE-Extensions					ProtocolExtensionContainer { { MBMS-Bearer-ServiceItemTDD-ExtIEs} } OPTIONAL,
	iE-Extensions					ProtocolExtensionContainer OPTIONAL,
	...
}

--MBMS-Bearer-ServiceItemTDD-ExtIEs RNSAP-PROTOCOL-EXTENSION ::= {
--	...
--}

MBMS-Bearer-ServiceItemTDD-PFL	::=SEQUENCE{
	tmgi	TMGI,
	transmissionMode 	TransmissionMode	OPTIONAL,
	preferredFrequencyLayer		UARFCN			OPTIONAL,
--	iE-Extensions					ProtocolExtensionContainer { { MBMS-Bearer-ServiceItemTDD-PFL-ExtIEs} } OPTIONAL,
	iE-Extensions					ProtocolExtensionContainer OPTIONAL,
	...
}
--MBMS-Bearer-ServiceItemTDD-PFL-ExtIEs RNSAP-PROTOCOL-EXTENSION ::= {
--	...
--}

MBMSChannelTypeInfo ::= SEQUENCE {
	tMGI				TMGI,
	pTM-Cell-List		PTMCellList		OPTIONAL,
	pTP-Cell-List		PTPCellList		OPTIONAL,
	not-Provided-Cell-List	NotProvidedCellList	OPTIONAL,
--	iE-Extensions		ProtocolExtensionContainer { { MBMSChannelTypeInfo-ExtIEs} } OPTIONAL,
	iE-Extensions		ProtocolExtensionContainer OPTIONAL,
	...
}

--MBMSChannelTypeInfo-ExtIEs RNSAP-PROTOCOL-EXTENSION ::= {
--	...
--}

MBMSChannelTypeCellList ::= SEQUENCE {
	c-ID									C-ID,
	affectedUEInformationForMBMS		AffectedUEInformationForMBMS	OPTIONAL,
--	iE-Extensions						ProtocolExtensionContainer { { MBMSChannelTypeCellList-ExtIEs} } OPTIONAL,
	iE-Extensions						ProtocolExtensionContainer OPTIONAL,
	...
}

--MBMSChannelTypeCellList-ExtIEs RNSAP-PROTOCOL-EXTENSION ::= {
--	...
--}

MBMSPreferredFreqLayerInfo	::= SEQUENCE {
	tMGI							TMGI,
	preferredFrequencyLayerInfo		PreferredFrequencyLayerInfo,
--	iE-Extensions					ProtocolExtensionContainer { { MBMSPreferredFreqLayerInfo-ExtIEs} } OPTIONAL,
	iE-Extensions					ProtocolExtensionContainer OPTIONAL,
	...
}
--MBMSPreferredFreqLayerInfo-ExtIEs RNSAP-PROTOCOL-EXTENSION ::= {
--	...
--}


MeasurementFilterCoefficient ::=  ENUMERATED{k0, k1, k2, k3, k4, k5, k6, k7, k8, k9, k11, k13, k15, k17, k19,...}
-- Measurement Filter Coefficient to be used for measurement

MeasurementID				::= INTEGER (0..1048575)

Measurement-Power-Offset ::= INTEGER(-12 .. 26)
-- Actual value = IE value * 0.5

MinimumSpreadingFactor		::= INTEGER (1..16)

MultipleURAsIndicator ::= ENUMERATED {
	multiple-URAs-exist,
	single-URA-exists
}

MaxAdjustmentStep			::= INTEGER(1..10)
-- Unit Slot

MeasurementChangeTime		::= INTEGER (1..6000,...)
-- The MeasurementChangeTime  gives the MeasurementChangeTime
-- in number of 10 ms periods.
-- E.g. Value 6000 means 60000ms(1min)
-- Unit is ms, Step is 10 ms


MeasurementHysteresisTime		::= INTEGER (1..6000,...)
-- The MeasurementHysteresisTime  gives the
-- MeasurementHysteresisTime in number of 10 ms periods.
-- E.g. Value 6000 means 60000ms(1min)
-- Unit is ms, Step is 10ms

MeasurementIncreaseDecreaseThreshold		::= CHOICE {
	sir								SIR-Value-IncrDecrThres,
	sir-error						SIR-Error-Value-IncrDecrThres,
	transmitted-code-power			Transmitted-Code-Power-Value-IncrDecrThres,
	rscp							RSCP-Value-IncrDecrThres,
	round-trip-time					Round-Trip-Time-IncrDecrThres,
	...,
	extension-MeasurementIncreaseDecreaseThreshold		Extension-MeasurementIncreaseDecreaseThreshold
}

--Extension-MeasurementIncreaseDecreaseThreshold	::= ProtocolIE-Single-Container {{ Extension-MeasurementIncreaseDecreaseThresholdIE }}
Extension-MeasurementIncreaseDecreaseThreshold	::= ProtocolIE-Single-Container

--Extension-MeasurementIncreaseDecreaseThresholdIE RNSAP-PROTOCOL-IES ::= {
--	{ ID id-Load-Value-IncrDecrThres	CRITICALITY reject	TYPE Load-Value-IncrDecrThres	PRESENCE mandatory }|
--	{ ID id-Transmitted-Carrier-Power-Value-IncrDecrThres	CRITICALITY reject	TYPE Transmitted-Carrier-Power-Value-IncrDecrThres		PRESENCE mandatory }|
--	{ ID id-Received-Total-Wideband-Power-Value-IncrDecrThres	CRITICALITY reject	TYPE Received-Total-Wideband-Power-Value-IncrDecrThres		PRESENCE mandatory }|
--	{ ID id-UL-Timeslot-ISCP-Value-IncrDecrThres	CRITICALITY reject	TYPE UL-Timeslot-ISCP-Value-IncrDecrThres	PRESENCE mandatory }|
--	{ ID id-RT-Load-Value-IncrDecrThres	CRITICALITY reject	TYPE RT-Load-Value-IncrDecrThres	PRESENCE mandatory }|
--	{ ID id-NRT-Load-Information-Value-IncrDecrThres	CRITICALITY reject	TYPE NRT-Load-Information-Value-IncrDecrThres	PRESENCE mandatory }|
--	{ ID id-UpPTSInterferenceValue		CRITICALITY reject	TYPE 	UpPTSInterferenceValue		PRESENCE mandatory }
--}

MeasurementRecoveryBehavior ::= NULL

MeasurementRecoveryReportingIndicator ::= NULL

MeasurementRecoverySupportIndicator ::= NULL

MeasurementThreshold 			::= CHOICE {
	sir								SIR-Value,
	sir-error						SIR-Error-Value,
	transmitted-code-power			Transmitted-Code-Power-Value,
	rscp							RSCP-Value,
	rx-timing-deviation				Rx-Timing-Deviation-Value,
	round-trip-time					Round-Trip-Time-Value,
	...,
	extension-MeasurementThreshold	Extension-MeasurementThreshold
}

--Extension-MeasurementThreshold	::= ProtocolIE-Single-Container {{ Extension-MeasurementThresholdIE }}
Extension-MeasurementThreshold	::= ProtocolIE-Single-Container

--Extension-MeasurementThresholdIE RNSAP-PROTOCOL-IES ::= {
--	{ ID id-TUTRANGPSMeasurementThresholdInformation	CRITICALITY reject	TYPE TUTRANGPSMeasurementThresholdInformation		PRESENCE mandatory }|
--	{ ID id-SFNSFNMeasurementThresholdInformation		CRITICALITY reject	TYPE SFNSFNMeasurementThresholdInformation			PRESENCE mandatory }|
--	{ ID id-Load-Value									CRITICALITY reject	TYPE Load-Value												PRESENCE mandatory }|
--	{ ID id-Transmitted-Carrier-Power-Value				CRITICALITY reject	TYPE Transmitted-Carrier-Power-Value					PRESENCE mandatory }|
--	{ ID id-Received-Total-Wideband-Power-Value			CRITICALITY reject	TYPE Received-Total-Wideband-Power-Value			PRESENCE mandatory }|
--	{ ID id-UL-Timeslot-ISCP-Value						CRITICALITY reject	TYPE UL-Timeslot-ISCP-Value								PRESENCE mandatory }|
--	{ ID id-RT-Load-Value								CRITICALITY reject	TYPE RT-Load-Value											PRESENCE mandatory }|
--	{ ID id-NRT-Load-Information-Value					CRITICALITY reject	TYPE NRT-Load-Information-Value						PRESENCE mandatory }|
--	{ ID id-Rx-Timing-Deviation-Value-LCR				CRITICALITY reject	TYPE Rx-Timing-Deviation-Value-LCR					PRESENCE mandatory}|
--	{ ID id-HS-SICH-Reception-Quality-Measurement-Value	CRITICALITY reject	TYPE HS-SICH-Reception-Quality-Measurement-Value	PRESENCE mandatory}|
--	{ ID id-UpPTSInterferenceValue						CRITICALITY reject	TYPE UpPTSInterferenceValue								PRESENCE mandatory }
--}

MidambleConfigurationBurstType1And3 ::=		ENUMERATED {v4, v8, v16}

MidambleConfigurationBurstType2 ::=		ENUMERATED {v3, v6}

MidambleConfigurationLCR ::=	ENUMERATED {v2, v4, v6, v8, v10, v12, v14, v16, ...}

MidambleShiftAndBurstType ::=		CHOICE {	
	type1								SEQUENCE {
		midambleConfigurationBurstType1And3		MidambleConfigurationBurstType1And3,
		midambleAllocationMode 				CHOICE {
			defaultMidamble						NULL,
			commonMidamble						NULL,
			ueSpecificMidamble					MidambleShiftLong,
			...
		},
		...
	},
	type2								SEQUENCE {
		midambleConfigurationBurstType2		MidambleConfigurationBurstType2,
		midambleAllocationMode 				CHOICE {
			defaultMidamble						NULL,
			commonMidamble						NULL,
			ueSpecificMidamble					MidambleShiftShort,
			...
		},
		...
	},
	type3								SEQUENCE {
		midambleConfigurationBurstType1And3	MidambleConfigurationBurstType1And3,
		midambleAllocationMode 			CHOICE {
			defaultMidamble						NULL,
			ueSpecificMidamble					MidambleShiftLong,
			...
		},
		...
	},
	...
}

MidambleShiftLong ::=				INTEGER (0..15)

MidambleShiftShort ::=				INTEGER (0..5)

MidambleShiftLCR ::= SEQUENCE {
	midambleAllocationMode		MidambleAllocationMode,
	midambleShift				MidambleShiftLong		OPTIONAL,
	-- The IE shall be present if the Midamble Allocation Mode IE is set to "UE specific midamble".
midambleConfigurationLCR	MidambleConfigurationLCR,
--	iE-Extensions				ProtocolExtensionContainer { {MidambleShiftLCR-ExtIEs} }		OPTIONAL,
	iE-Extensions				ProtocolExtensionContainer OPTIONAL,
	...
	}

MidambleAllocationMode ::= ENUMERATED {
	defaultMidamble,
	commonMidamble,
	uESpecificMidamble, 
	...
	}

--MidambleShiftLCR-ExtIEs  RNSAP-PROTOCOL-EXTENSION ::= {
--	...
--}

MinUL-ChannelisationCodeLength		::= ENUMERATED {
	v4,
	v8,
	v16,
	v32,
	v64,
	v128,
	v256
}

ModifyPriorityQueue ::= CHOICE {
	addPriorityQueue			PriorityQueue-InfoItem-to-Add,
	modifyPriorityQueue			PriorityQueue-InfoItem-to-Modify,
	deletePriorityQueue			PriorityQueue-Id,
	...
}

Modulation ::= ENUMERATED {
	qPSK,
	eightPSK,
	...
}

MultiplexingPosition ::= ENUMERATED {
	fixed,
	flexible
}

MAChs-ResetIndicator ::= ENUMERATED{
	mAChs-NotReset
}

-- N

NACC-Related-Data ::= SEQUENCE {
	gERAN-SI-Type				GERAN-SI-Type,
--	iE-Extensions				ProtocolExtensionContainer { {NACC-Related-Data-ExtIEs} }		OPTIONAL,
	iE-Extensions				ProtocolExtensionContainer OPTIONAL,
	...
	}

--NACC-Related-Data-ExtIEs RNSAP-PROTOCOL-EXTENSION ::= {
--	...
--}


Nack-Power-Offset ::= INTEGER (0..8,...)
-- According to mapping in ref. [21] subclause 4.2.1

NCC ::= BIT STRING (SIZE (3))

--Neighbouring-UMTS-CellInformation ::= SEQUENCE (SIZE (1..10)) OF ProtocolIE-Single-Container {{ Neighbouring-UMTS-CellInformationItemIE }}
Neighbouring-UMTS-CellInformation ::= SEQUENCE (SIZE (1..10)) OF ProtocolIE-Single-Container

--Neighbouring-UMTS-CellInformationItemIE RNSAP-PROTOCOL-IES ::= {
--	{ ID id-Neighbouring-UMTS-CellInformationItem	CRITICALITY ignore	TYPE	Neighbouring-UMTS-CellInformationItem	PRESENCE	mandatory }
--}

Neighbouring-UMTS-CellInformationItem ::= SEQUENCE {
	rNC-ID									RNC-ID,
	cN-PS-DomainIdentifier					CN-PS-DomainIdentifier		OPTIONAL,
	cN-CS-DomainIdentifier					CN-CS-DomainIdentifier		OPTIONAL,
	neighbouring-FDD-CellInformation		Neighbouring-FDD-CellInformation	OPTIONAL,
	neighbouring-TDD-CellInformation		Neighbouring-TDD-CellInformation	OPTIONAL,
--	iE-Extensions							ProtocolExtensionContainer { {Neighbouring-UMTS-CellInformationItem-ExtIEs} } OPTIONAL,
	iE-Extensions							ProtocolExtensionContainer OPTIONAL,
	...
}

--Neighbouring-UMTS-CellInformationItem-ExtIEs RNSAP-PROTOCOL-EXTENSION ::= {
--	{ ID id-neighbouring-LCR-TDD-CellInformation			CRITICALITY  ignore		EXTENSION	Neighbouring-LCR-TDD-CellInformation			PRESENCE optional },
--	...
--}

Neighbouring-FDD-CellInformation ::= SEQUENCE ( SIZE (1..256,...)) OF Neighbouring-FDD-CellInformationItem

Neighbouring-FDD-CellInformationItem ::= SEQUENCE {
	c-ID								C-ID,
	uARFCNforNu							UARFCN,
	uARFCNforNd							UARFCN,
	frameOffset							FrameOffset			OPTIONAL,
	primaryScramblingCode				PrimaryScramblingCode,
	primaryCPICH-Power					PrimaryCPICH-Power		OPTIONAL,
	cellIndividualOffset				CellIndividualOffset	OPTIONAL,
	txDiversityIndicator 				TxDiversityIndicator,
	sTTD-SupportIndicator				STTD-SupportIndicator	OPTIONAL,
	closedLoopMode1-SupportIndicator	ClosedLoopMode1-SupportIndicator	OPTIONAL,
	not-used-closedLoopMode2-SupportIndicator	NULL	OPTIONAL,
--	iE-Extensions						ProtocolExtensionContainer { { Neighbouring-FDD-CellInformationItem-ExtIEs} } OPTIONAL,
	iE-Extensions						ProtocolExtensionContainer OPTIONAL,
	...
}

--Neighbouring-FDD-CellInformationItem-ExtIEs RNSAP-PROTOCOL-EXTENSION ::= {
--	{ ID id-RestrictionStateIndicator				CRITICALITY ignore			EXTENSION RestrictionStateIndicator		PRESENCE optional	}|
--	{ ID id-DPC-Mode-Change-SupportIndicator	CRITICALITY	ignore		EXTENSION	DPC-Mode-Change-SupportIndicator		PRESENCE optional }|
--	{ ID id-CoverageIndicator				CRITICALITY ignore			EXTENSION CoverageIndicator					PRESENCE optional	}|
--	{ ID id-AntennaColocationIndicator		CRITICALITY ignore			EXTENSION AntennaColocationIndicator		PRESENCE optional	}|
--	{ ID id-HCS-Prio						CRITICALITY ignore			EXTENSION HCS-Prio								PRESENCE optional	}|
--	{ ID id-CellCapabilityContainer-FDD			CRITICALITY	ignore		EXTENSION	CellCapabilityContainer-FDD				PRESENCE optional }|
--	{ ID id-SNA-Information					CRITICALITY ignore			EXTENSION SNA-Information			PRESENCE optional }|
--	{ ID id-FrequencyBandIndicator					CRITICALITY ignore			EXTENSION FrequencyBandIndicator			PRESENCE optional },
--	...
--}

NeighbouringFDDCellMeasurementInformation ::= SEQUENCE {
	uC-ID								UC-ID,
	uARFCN								UARFCN,
	primaryScramblingCode				PrimaryScramblingCode,
--	iE-Extensions						ProtocolExtensionContainer { { NeighbouringFDDCellMeasurementInformationItem-ExtIEs} } OPTIONAL,
	iE-Extensions						ProtocolExtensionContainer OPTIONAL,
	...
}

--NeighbouringFDDCellMeasurementInformationItem-ExtIEs RNSAP-PROTOCOL-EXTENSION ::= {
--	...
--}

--Neighbouring-GSM-CellInformation ::= ProtocolIE-Single-Container {{ Neighbouring-GSM-CellInformationIE }}
Neighbouring-GSM-CellInformation ::= ProtocolIE-Single-Container

--Neighbouring-GSM-CellInformationIE RNSAP-PROTOCOL-IES ::= {
--	{ ID id-Neighbouring-GSM-CellInformation	CRITICALITY ignore	TYPE	Neighbouring-GSM-CellInformationIEs	PRESENCE	mandatory }
--}

Neighbouring-GSM-CellInformationIEs ::= SEQUENCE ( SIZE (1..256,...)) OF Neighbouring-GSM-CellInformationItem

Neighbouring-GSM-CellInformationItem ::= SEQUENCE {
	cGI									CGI,
	cellIndividualOffset				CellIndividualOffset	OPTIONAL,
	bSIC								BSIC,
	band-Indicator 						Band-Indicator,
	bCCH-ARFCN							BCCH-ARFCN,
--	iE-Extensions						ProtocolExtensionContainer { { Neighbouring-GSM-CellInformationItem-ExtIEs} } OPTIONAL,
	iE-Extensions						ProtocolExtensionContainer OPTIONAL,
	...
}

--Neighbouring-GSM-CellInformationItem-ExtIEs RNSAP-PROTOCOL-EXTENSION ::= {
--	{ ID id-CoverageIndicator				CRITICALITY ignore			EXTENSION CoverageIndicator						PRESENCE optional	} |
--	{ ID id-AntennaColocationIndicator		CRITICALITY ignore			EXTENSION AntennaColocationIndicator			PRESENCE optional	} |
--	{ ID id-HCS-Prio						CRITICALITY ignore			EXTENSION HCS-Prio									PRESENCE optional	} |
--	{ ID id-SNA-Information					CRITICALITY ignore			EXTENSION SNA-Information							PRESENCE optional	} |
--	{ ID id-GERAN-Cell-Capability			CRITICALITY ignore			EXTENSION GERAN-Cell-Capability					PRESENCE optional	} |
--	{ ID id-GERAN-Classmark					CRITICALITY ignore			EXTENSION GERAN-Classmark							PRESENCE optional	} |
--	{ ID id-ExtendedGSMCellIndividualOffset	CRITICALITY ignore			EXTENSION ExtendedGSMCellIndividualOffset	PRESENCE optional	},
--	...
--}

Neighbouring-TDD-CellInformation ::= SEQUENCE ( SIZE (1..256,...)) OF Neighbouring-TDD-CellInformationItem

Neighbouring-TDD-CellInformationItem ::= SEQUENCE {
	c-ID							C-ID,
	uARFCNforNt						UARFCN,
	frameOffset						FrameOffset			OPTIONAL,
	cellParameterID					CellParameterID,
	syncCase						SyncCase,
	timeSlot						TimeSlot			OPTIONAL
	-- This IE shall be present if Sync Case = Case1 -- ,
	sCH-TimeSlot					SCH-TimeSlot			OPTIONAL
	-- This IE shall be present if Sync Case = Case2 -- ,
	sCTD-Indicator			SCTD-Indicator,
	cellIndividualOffset			CellIndividualOffset	OPTIONAL,
	dPCHConstantValue				DPCHConstantValue	OPTIONAL,
	pCCPCH-Power					PCCPCH-Power			OPTIONAL,
--	iE-Extensions					ProtocolExtensionContainer { { Neighbouring-TDD-CellInformationItem-ExtIEs} } OPTIONAL,
	iE-Extensions					ProtocolExtensionContainer OPTIONAL,
	...
}

--Neighbouring-TDD-CellInformationItem-ExtIEs RNSAP-PROTOCOL-EXTENSION ::= {
--	{ ID id-RestrictionStateIndicator				CRITICALITY ignore			EXTENSION RestrictionStateIndicator		PRESENCE optional	}|
--	{ ID id-CoverageIndicator				CRITICALITY ignore			EXTENSION CoverageIndicator					PRESENCE optional	}|
--	{ ID id-AntennaColocationIndicator		CRITICALITY ignore			EXTENSION AntennaColocationIndicator		PRESENCE optional	}|
--	{ ID id-HCS-Prio						CRITICALITY ignore			EXTENSION HCS-Prio								PRESENCE optional	}|
--	{ ID id-CellCapabilityContainer-TDD				CRITICALITY	ignore	EXTENSION	CellCapabilityContainer-TDD			PRESENCE optional }|
--	{ ID id-SNA-Information							CRITICALITY ignore	EXTENSION SNA-Information						PRESENCE optional	},
--	...
--}

NeighbouringTDDCellMeasurementInformation ::= SEQUENCE {
	uC-ID								UC-ID,
	uARFCN								UARFCN,
	cellParameterID						CellParameterID,
	timeSlot							TimeSlot					OPTIONAL,
	midambleShiftAndBurstType			MidambleShiftAndBurstType	OPTIONAL,
--	iE-Extensions						ProtocolExtensionContainer { { NeighbouringTDDCellMeasurementInformationItem-ExtIEs} } OPTIONAL,
	iE-Extensions						ProtocolExtensionContainer OPTIONAL,
	...
}

--NeighbouringTDDCellMeasurementInformationItem-ExtIEs RNSAP-PROTOCOL-EXTENSION ::= {
--	...
--}

NeighbouringTDDCellMeasurementInformationLCR ::= SEQUENCE {
	uC-ID								UC-ID,
	uARFCN								UARFCN,
	cellParameterID						CellParameterID,
	timeSlotLCR							TimeSlotLCR					OPTIONAL,
	midambleShiftLCR					MidambleShiftLCR			OPTIONAL,
--	iE-Extensions						ProtocolExtensionContainer { { NeighbouringTDDCellMeasurementInformationLCRItem-ExtIEs} } OPTIONAL,
	iE-Extensions						ProtocolExtensionContainer OPTIONAL,
	...
}

--NeighbouringTDDCellMeasurementInformationLCRItem-ExtIEs RNSAP-PROTOCOL-EXTENSION ::= {
--	...
--}

Neighbouring-LCR-TDD-CellInformation ::= SEQUENCE (SIZE (1.. 256,...)) OF Neighbouring-LCR-TDD-CellInformationItem

Neighbouring-LCR-TDD-CellInformationItem ::= SEQUENCE {
	c-ID							C-ID,
	uARFCNforNt						UARFCN,
	frameOffset						FrameOffset			OPTIONAL,
	cellParameterID					CellParameterID,
	sCTD-Indicator			SCTD-Indicator,
	cellIndividualOffset			CellIndividualOffset	OPTIONAL,
	dPCHConstantValue				DPCHConstantValue	OPTIONAL,
	pCCPCH-Power					PCCPCH-Power			OPTIONAL,
	restrictionStateIndicator		RestrictionStateIndicator		OPTIONAL,
--	iE-Extensions					ProtocolExtensionContainer { { Neighbouring-LCR-TDD-CellInformationItem-ExtIEs} } OPTIONAL,
	iE-Extensions					ProtocolExtensionContainer OPTIONAL,
	...
}

--Neighbouring-LCR-TDD-CellInformationItem-ExtIEs RNSAP-PROTOCOL-EXTENSION ::= {
--	{ ID id-CoverageIndicator				CRITICALITY ignore		EXTENSION	CoverageIndicator							PRESENCE optional	}|
--	{ ID id-AntennaColocationIndicator		CRITICALITY ignore		EXTENSION	AntennaColocationIndicator				PRESENCE optional	}|
--	{ ID id-HCS-Prio						CRITICALITY ignore		EXTENSION	HCS-Prio									PRESENCE optional	}|
--	{ ID id-CellCapabilityContainer-TDD-LCR	CRITICALITY	ignore		EXTENSION	CellCapabilityContainer-TDD-LCR		PRESENCE optional }|
--	{ ID id-SNA-Information					CRITICALITY ignore		EXTENSION	SNA-Information								PRESENCE optional },
--	...
--}

NotProvidedCellList	::= SEQUENCE (SIZE (1..65536)) OF MBMSChannelTypeCellList

NrOfDLchannelisationcodes	::= INTEGER (1..8)

NrOfTransportBlocks			::= INTEGER (0..512)

NRT-Load-Information-Value-IncrDecrThres ::= INTEGER(0..3) 

NRT-Load-Information-Value ::= INTEGER(0..3)

NRTLoadInformationValue ::= SEQUENCE {
		uplinkNRTLoadInformationValue		INTEGER(0..3),
		downlinkNRTLoadInformationValue		INTEGER(0..3)
}

-- O
OnModification ::= SEQUENCE {
	measurementThreshold	MeasurementThreshold,
--	iE-Extensions			ProtocolExtensionContainer { {OnModification-ExtIEs} } OPTIONAL,
	iE-Extensions			ProtocolExtensionContainer OPTIONAL,
	...
}

--OnModification-ExtIEs RNSAP-PROTOCOL-EXTENSION ::= {
--	...
--}

OnModificationInformation ::= SEQUENCE {
	informationThreshold	InformationThreshold 	OPTIONAL,
--	iE-Extensions			ProtocolExtensionContainer { {OnModificationInformation-ExtIEs} } OPTIONAL,
	iE-Extensions			ProtocolExtensionContainer OPTIONAL,
	...
}

--OnModificationInformation-ExtIEs RNSAP-PROTOCOL-EXTENSION ::= {
--	...
--}

-- P

PagingCause ::= ENUMERATED {
	terminating-conversational-call,
	terminating-streaming-call,
	terminating-interactive-call,
	terminating-background-call,
	terminating-low-priority-signalling,
	...,
	terminating-high-priority-signalling, 
	terminating-cause-unknown
}
-- See in [16]

PagingRecordType ::= ENUMERATED {
	imsi-gsm-map,
	tmsi-gsm-map,
	p-tmsi-gsm-map,
	imsi-ds-41,
	tmsi-ds-41,
	...
}
-- See in [16]

PartialReportingIndicator ::= ENUMERATED {
	partial-reporting-allowed
}

PayloadCRC-PresenceIndicator ::= ENUMERATED {
	crc-included,
	crc-not-included
}

PCCPCH-Power ::= INTEGER (-150..400,...)
-- PCCPCH-power = power * 10
-- If power <= -15 PCCPCH shall be set to -150
-- If power >= 40 PCCPCH shall be set to 400
-- Unit dBm, Range -15dBm .. +40 dBm, Step 0.1dBm

PCH-InformationList ::= SEQUENCE (SIZE(0..1)) OF PCH-InformationItem

PCH-InformationItem ::= SEQUENCE {
	transportFormatSet				TransportFormatSet,
--	iE-Extensions					ProtocolExtensionContainer { { PCH-InformationItem-ExtIEs} } OPTIONAL,
	iE-Extensions					ProtocolExtensionContainer OPTIONAL,
	...
}

--PCH-InformationItem-ExtIEs RNSAP-PROTOCOL-EXTENSION ::= {
--	...
--}

PC-Preamble ::= INTEGER(0..7,...)

Periodic ::= SEQUENCE {
	reportPeriodicity		ReportPeriodicity,
--	iE-Extensions			ProtocolExtensionContainer { {Periodic-ExtIEs} } OPTIONAL,
	iE-Extensions			ProtocolExtensionContainer OPTIONAL,
	...
}

--Periodic-ExtIEs RNSAP-PROTOCOL-EXTENSION ::= {
--	...
--}

PeriodicInformation ::= SEQUENCE {
	informationReportPeriodicity		InformationReportPeriodicity,
--	iE-Extensions						ProtocolExtensionContainer { {PeriodicInformation-ExtIEs} } OPTIONAL,
	iE-Extensions						ProtocolExtensionContainer OPTIONAL,
	...
}

--PeriodicInformation-ExtIEs RNSAP-PROTOCOL-EXTENSION ::= {
--	...
--}

Permanent-NAS-UE-Identity ::= CHOICE {
	imsi		IMSI,
	...
}

Phase-Reference-Update-Indicator ::= ENUMERATED {
	phase-reference-needs-to-be-changed
}

PLMN-Identity ::= OCTET STRING (SIZE(3))

PowerAdjustmentType ::= ENUMERATED {
	none,
	common,
	individual
}

PowerOffset				::= INTEGER (0..24)

PRC ::= INTEGER (-2047..2047)
--pseudo range correction; scaling factor 0.32 meters

PRCDeviation ::= ENUMERATED {
	prcd1,
	prcd2,
	prcd5,
	prcd10,
	...
}

Pre-emptionCapability ::= ENUMERATED {
	shall-not-trigger-pre-emption,
	may-trigger-pre-emption
}

Pre-emptionVulnerability ::= ENUMERATED {
	not-pre-emptable,
	pre-emptable
}

PredictedSFNSFNDeviationLimit ::= INTEGER (1..256)
-- Unit chip, Step 1/16 chip, Range 1/16..16 chip

PredictedTUTRANGPSDeviationLimit ::= INTEGER (1..256)
-- Unit chip, Step 1/16 chip, Range 1/16..16 chip

PreferredFrequencyLayerInfo	::= SEQUENCE {
	defaultPreferredFrequency	UARFCN,
	additionalPreferredFrequency	AdditionalPreferredFrequency	OPTIONAL,
--	iE-Extensions					ProtocolExtensionContainer { { PreferredFrequencyLayerInfo-ExtIEs} } OPTIONAL,
	iE-Extensions					ProtocolExtensionContainer OPTIONAL,
	...
}
--PreferredFrequencyLayerInfo-ExtIEs RNSAP-PROTOCOL-EXTENSION ::= {
--	...
--}


PrimaryCPICH-Power			::= INTEGER (-100..500)
-- step 0.1 (Range -10.0..50.0) Unit is dBm

PrimaryCPICH-EcNo			::= INTEGER (-30..30)

Primary-CPICH-Usage-For-Channel-Estimation ::= ENUMERATED {
primary-CPICH-may-be-used,
primary-CPICH-shall-not-be-used
}

PrimaryCCPCH-RSCP			::= INTEGER (0..91)
-- Mapping of Non Negative values according to maping in [24]

PrimaryCCPCH-RSCP-Delta		::= INTEGER (-5..-1,...)
-- Mapping of Negative values according to maping in [24]

PrimaryScramblingCode			::= INTEGER (0..511)

PriorityLevel				::= INTEGER (0..15)
-- 0 = spare, 1 = highest priority, ...14 = lowest priority and 15 = no priority

PriorityQueue-Id ::= INTEGER (0..7)

PriorityQueue-InfoList ::= SEQUENCE (SIZE (1..8)) OF PriorityQueue-InfoItem

PriorityQueue-InfoItem ::= SEQUENCE {
	priorityQueue-Id					PriorityQueue-Id,
	associatedHSDSCH-MACdFlow			HSDSCH-MACdFlow-ID,
	schedulingPriorityIndicator			SchedulingPriorityIndicator,
	t1									T1,
	discardTimer						DiscardTimer				OPTIONAL,
	mAC-hsWindowSize					MAC-hsWindowSize,
	mAChsGuaranteedBitRate				MAChsGuaranteedBitRate		OPTIONAL,
	mACdPDU-Size-Index					MACdPDU-Size-IndexList,
	rLC-Mode							RLC-Mode,
--	iE-Extensions						ProtocolExtensionContainer { { PriorityQueue-InfoItem-ExtIEs } }			OPTIONAL,
	iE-Extensions						ProtocolExtensionContainer OPTIONAL,
	...
}

--PriorityQueue-InfoItem-ExtIEs RNSAP-PROTOCOL-EXTENSION ::= {
--	...
--}

PriorityQueue-InfoList-to-Modify ::= SEQUENCE (SIZE (1..8)) OF ModifyPriorityQueue

PriorityQueue-InfoItem-to-Add ::= SEQUENCE {
	priorityQueue-Id					PriorityQueue-Id,
	associatedHSDSCH-MACdFlow			HSDSCH-MACdFlow-ID,
	schedulingPriorityIndicator			SchedulingPriorityIndicator,
	t1									T1,
	discardTimer						DiscardTimer							OPTIONAL,
	mAC-hsWindowSize					MAC-hsWindowSize,
	mAChsGuaranteedBitRate				MAChsGuaranteedBitRate					OPTIONAL,
	mACdPDU-Size-Index					MACdPDU-Size-IndexList,
	rLC-Mode							RLC-Mode,
--	iE-Extensions						ProtocolExtensionContainer { { PriorityQueue-InfoItem-to-Add-ExtIEs } }			OPTIONAL,
	iE-Extensions						ProtocolExtensionContainer OPTIONAL,
	...
}

--PriorityQueue-InfoItem-to-Add-ExtIEs RNSAP-PROTOCOL-EXTENSION ::= {
--	...
--}

PriorityQueue-InfoItem-to-Modify ::= SEQUENCE {
	priorityQueue-Id					PriorityQueue-Id,
	schedulingPriorityIndicator			SchedulingPriorityIndicator				OPTIONAL,
	t1									T1										OPTIONAL,
	discardTimer						DiscardTimer							OPTIONAL,
	mAC-hsWindowSize					MAC-hsWindowSize						OPTIONAL,
	mAChsGuaranteedBitRate				MAChsGuaranteedBitRate					OPTIONAL,
	mACdPDU-Size-Index-to-Modify		MACdPDU-Size-IndexList-to-Modify					OPTIONAL,
--	iE-Extensions						ProtocolExtensionContainer { { PriorityQueue-InfoItem-to-Modify-ExtIEs } }			OPTIONAL,
	iE-Extensions						ProtocolExtensionContainer OPTIONAL,
	...
}

--PriorityQueue-InfoItem-to-Modify-ExtIEs RNSAP-PROTOCOL-EXTENSION ::= {
--	...
--}

PriorityQueue-InfoList-to-Modify-Unsynchronised ::= SEQUENCE (SIZE (0..8)) OF PriorityQueue-InfoItem-to-Modify-Unsynchronised

PriorityQueue-InfoItem-to-Modify-Unsynchronised ::= SEQUENCE {
	priorityQueueId						PriorityQueue-Id,
	schedulingPriorityIndicator			SchedulingPriorityIndicator									OPTIONAL,
	discardTimer						DiscardTimer												OPTIONAL,
	mAChsGuaranteedBitRate				MAChsGuaranteedBitRate										OPTIONAL,
--	iE-Extensions						ProtocolExtensionContainer { { PriorityQueue-InfoItem-to-Modify-Unsynchronised-ExtIEs} }		OPTIONAL,
	iE-Extensions						ProtocolExtensionContainer OPTIONAL,
	...
}

--PriorityQueue-InfoItem-to-Modify-Unsynchronised-ExtIEs RNSAP-PROTOCOL-EXTENSION ::= {
--	...
--}

PropagationDelay			::= INTEGER (0..255)

ProvidedInformation	::= SEQUENCE {
	mBMSChannelTypeInfo		MBMSChannelTypeInfo			OPTIONAL,
	mBMSPreferredFreqLayerInfo	MBMSPreferredFreqLayerInfo		OPTIONAL,
--	iE-Extensions					ProtocolExtensionContainer { { ProvideInformation-ExtIEs} } OPTIONAL,
	iE-Extensions					ProtocolExtensionContainer OPTIONAL,
	...
}
--ProvideInformation-ExtIEs RNSAP-PROTOCOL-EXTENSION ::= {
--	...
--}

PunctureLimit				::= INTEGER (0..15)
-- 0: 40%; 1: 44%; ... 14: 96%; 15: 100

PTMCellList	::= SEQUENCE (SIZE (1..65536)) OF MBMSChannelTypeCellList

PTPCellList	::= SEQUENCE (SIZE (1..65536)) OF MBMSChannelTypeCellList


-- Q

QE-Selector ::= ENUMERATED {
	selected,
	non-selected
}

-- R

RAC					::= OCTET STRING (SIZE(1))

RANAP-RelocationInformation		::= BIT STRING

Range-Correction-Rate ::= INTEGER (-127..127)
-- scaling factor 0.032 m/s

RateMatchingAttribute 			::= INTEGER (1..256)

RB-Identity						::= INTEGER (0..31)

RB-Info ::= SEQUENCE (SIZE(1..32)) OF RB-Identity

Received-Total-Wideband-Power-Value ::= Received-total-wide-band-power

Received-Total-Wideband-Power-Value-IncrDecrThres ::= INTEGER(0..620)
-- Unit dB Step 0.1dB
-- e.g. value 100 means 10dB

Reference-E-TFCI-Information ::= SEQUENCE (SIZE (1..8)) OF Reference-E-TFCI-Information-Item

Reference-E-TFCI-Information-Item ::= SEQUENCE {
	reference-E-TFCI				E-TFCI,
	reference-E-TFCI-PO				Reference-E-TFCI-PO,
--	iE-Extensions					ProtocolExtensionContainer { { Reference-E-TFCI-Information-Item-ExtIEs} }		OPTIONAL,
	iE-Extensions					ProtocolExtensionContainer OPTIONAL,
	...
}

--Reference-E-TFCI-Information-Item-ExtIEs RNSAP-PROTOCOL-EXTENSION ::= {
--	...
--}

Reference-E-TFCI-PO ::= INTEGER (0.. 29)

RefTFCNumber ::= INTEGER (0..15)

RepetitionLength 			::= INTEGER (1..63)

RepetitionPeriod ::= ENUMERATED {
	v1,
	v2,
	v4,
	v8,
	v16,
	v32,
	v64
}

RepetitionNumber0 ::= INTEGER (0..255)

RepetitionNumber1 ::= INTEGER (1..256)

ReportCharacteristics ::= CHOICE {
	onDemand			NULL,
	periodic			Periodic,
	eventA				EventA,
	eventB				EventB,
	eventC				EventC,
	eventD				EventD,
	eventE				EventE,
	eventF				EventF,
	...,
	extension-ReportCharacteristics		Extension-ReportCharacteristics
}

--Extension-ReportCharacteristics	::= ProtocolIE-Single-Container {{ Extension-ReportCharacteristicsIE }}
Extension-ReportCharacteristics	::= ProtocolIE-Single-Container

--Extension-ReportCharacteristicsIE RNSAP-PROTOCOL-IES ::= {
--	{ ID id-OnModification	CRITICALITY reject	TYPE OnModification		PRESENCE mandatory }
--}

ReportPeriodicity ::= CHOICE {
	ten-msec 				INTEGER (1..6000,...),
-- The Report Periodicity gives the reporting periodicity in number of 10 ms periods.
-- E.g. value 6000 means 60000ms (i.e. 1min)
-- Unit ms, Step 10ms
	min				INTEGER (1..60,...),
-- Unit min, Step 1min
	...
}

RequestedDataValue ::= SEQUENCE {
	gA-AccessPointPositionwithAltitude			GA-AccessPointPositionwithOptionalAltitude	OPTIONAL,
	iPDLParameters								IPDLParameters								OPTIONAL,
	dGPSCorrections								DGPSCorrections								OPTIONAL,
	gPS-NavigationModel-and-TimeRecovery		GPS-NavigationModel-and-TimeRecovery		OPTIONAL,
	gPS-Ionospheric-Model						GPS-Ionospheric-Model						OPTIONAL,
	gPS-UTC-Model								GPS-UTC-Model								OPTIONAL,
	gPS-Almanac									GPS-Almanac									OPTIONAL,
	gPS-RealTime-Integrity						GPS-RealTime-Integrity						OPTIONAL,
	gPS-RX-POS									GPS-RX-POS									OPTIONAL,
	sFNSFN-GA-AccessPointPosition				GA-AccessPointPositionwithOptionalAltitude	OPTIONAL,
--	iE-Extensions								ProtocolExtensionContainer { { RequestedDataValue-ExtIEs} }		OPTIONAL,
	iE-Extensions								ProtocolExtensionContainer OPTIONAL,
	...
}

--RequestedDataValue-ExtIEs RNSAP-PROTOCOL-EXTENSION ::= {
--	{ ID id-Cell-Capacity-Class-Value	CRITICALITY ignore	EXTENSION Cell-Capacity-Class-Value	PRESENCE mandatory }|
--	{ ID id-NACC-Related-Data			CRITICALITY ignore	EXTENSION NACC-Related-Data			PRESENCE optional }|
--	{ ID id-MBMS-Bearer-Service-Full-Address			CRITICALITY ignore	EXTENSION MBMS-Bearer-Service-Full-Address			PRESENCE optional },
--	...
--}

RequestedDataValueInformation ::= CHOICE {
	informationAvailable		InformationAvailable,
	informationNotAvailable		InformationNotAvailable
}

RestrictionStateIndicator	::= ENUMERATED {
	cellNotResevedForOperatorUse,
	cellResevedForOperatorUse,
	...
}

RL-ID					::= INTEGER (0..31)

RL-Set-ID				::= INTEGER (0..31)

RL-Specific-DCH-Info ::= SEQUENCE (SIZE (1..128)) OF RL-Specific-DCH-Info-Item

RL-Specific-DCH-Info-Item ::= SEQUENCE {
	dCH-id					DCH-ID,
	bindingID				BindingID OPTIONAL,
    -- Shall be ignored if bearer establishment with ALCAP.
	transportLayerAddress	TransportLayerAddress		OPTIONAL,
    -- Shall be ignored if bearer establishment with ALCAP.
--	iE-Extensions			ProtocolExtensionContainer { { RL-Specific-DCH-Info-Item-ExtIEs} }	OPTIONAL,
	iE-Extensions			ProtocolExtensionContainer OPTIONAL,
	...
}

--RL-Specific-DCH-Info-Item-ExtIEs RNSAP-PROTOCOL-EXTENSION ::= {
--	...
--}

RL-Specific-EDCH-Information ::= SEQUENCE (SIZE (1..8)) OF RL-Specific-EDCH-InfoItem

RL-Specific-EDCH-InfoItem ::= SEQUENCE {
	eDCH-MACdFlow-ID					EDCH-MACdFlow-ID,
	bindingID							BindingID 			OPTIONAL,
    -- Shall be ignored if bearer establishment with ALCAP.
	transportLayerAddress				TransportLayerAddress		OPTIONAL,
    -- Shall be ignored if bearer establishment with ALCAP.
--	iE-Extensions			ProtocolExtensionContainer { { RL-Specific-EDCH-Info-Item-ExtIEs} }	OPTIONAL,
	iE-Extensions			ProtocolExtensionContainer OPTIONAL,
	...
}

--RL-Specific-EDCH-Info-Item-ExtIEs RNSAP-PROTOCOL-EXTENSION ::= {
--	...
--}

RLC-Mode	::= ENUMERATED {
	rLC-AM,
	rLC-UM,
	...
}

RNC-ID					::= INTEGER (0..4095)

Round-Trip-Time-IncrDecrThres ::= INTEGER(0..32766)

Round-Trip-Time-Value ::= INTEGER(0..32767)
-- According to mapping in [23]

RSCP-Value ::= INTEGER (0..127)
-- According to mapping in [24]

RSCP-Value-IncrDecrThres ::= INTEGER (0..126)

Received-total-wide-band-power				::= INTEGER (0..621)
-- According to mapping in [23]

RT-Load-Value-IncrDecrThres ::= INTEGER(0..100)

RT-Load-Value ::= INTEGER(0..100)

RTLoadValue ::= SEQUENCE {
		uplinkRTLoadValue		INTEGER(0..100),
		downlinkRTLoadValue		INTEGER(0..100)
}

RxTimingDeviationForTA				::= INTEGER (0..127)
-- As specified in [5], ch. 6.2.7.6
-- For 1.28Mcps TDD this IE must be set to 0.

Rx-Timing-Deviation-Value ::= INTEGER (0..8191)
--According to mapping in [24][3.84Mcps TDD only]

Rx-Timing-Deviation-Value-LCR ::= INTEGER (0..511)
--According to mapping in [24][1.28Mcps TDD only]

-- S

SAC					::= OCTET STRING (SIZE (2))

SAI ::= SEQUENCE {
	pLMN-Identity		PLMN-Identity,
	lAC					LAC,
	sAC					SAC,
--	iE-Extensions		ProtocolExtensionContainer { {SAI-ExtIEs} } OPTIONAL
	iE-Extensions		ProtocolExtensionContainer OPTIONAL
}

--SAI-ExtIEs RNSAP-PROTOCOL-EXTENSION ::= {
--	...
--}

SAT-ID ::= INTEGER (0..63)

SCH-TimeSlot				::= INTEGER (0..6)

ScaledAdjustmentRatio			::= INTEGER(0..100)
-- AdjustmentRatio  = ScaledAdjustmentRatio / 100

Secondary-CCPCH-Info-TDD::= SEQUENCE {
	dl-TFCS									TFCS,
	tFCI-Coding								TFCI-Coding,
	secondary-CCPCH-TDD-InformationList		Secondary-CCPCH-TDD-InformationList,
	fACH-InformationList					FACH-InformationList,
	pCH-InformationList						PCH-InformationList,
--	iE-Extensions							ProtocolExtensionContainer { { Secondary-CCPCH-Info-TDD-ExtIEs} } OPTIONAL,
	iE-Extensions							ProtocolExtensionContainer OPTIONAL,
	...
}

--Secondary-CCPCH-Info-TDD-ExtIEs RNSAP-PROTOCOL-EXTENSION ::= {
--	...
--}

Secondary-CPICH-Information ::= SEQUENCE {
dl-ScramblingCode							DL-ScramblingCode,
fDD-DL-ChannelisationCodeNumber			FDD-DL-ChannelisationCodeNumber,
--iE-Extensions								ProtocolExtensionContainer { { Secondary-CPICH-Information-ExtIEs} } OPTIONAL,
iE-Extensions								ProtocolExtensionContainer OPTIONAL,
	...
}

--Secondary-CPICH-Information-ExtIEs RNSAP-PROTOCOL-EXTENSION ::= {
--	...
--}

Secondary-CPICH-Information-Change ::= CHOICE {
new-secondary-CPICH					Secondary-CPICH-Information,
secondary-CPICH-shall-not-be-used	NULL,
...
}

Secondary-LCR-CCPCH-Info-TDD::= SEQUENCE {
	dl-TFCS									TFCS,
	tFCI-Coding								TFCI-Coding,
	secondary-LCR-CCPCH-TDD-InformationList	Secondary-LCR-CCPCH-TDD-InformationList,
	fACH-InformationList					FACH-InformationList,
	pCH-InformationList						PCH-InformationList,
--	iE-Extensions							ProtocolExtensionContainer { { Secondary-LCR-CCPCH-Info-TDD-ExtIEs} } OPTIONAL,
	iE-Extensions							ProtocolExtensionContainer OPTIONAL,
	...
}

--Secondary-LCR-CCPCH-Info-TDD-ExtIEs RNSAP-PROTOCOL-EXTENSION ::= {
--	...
--}

Secondary-CCPCH-TDD-InformationList ::= SEQUENCE (SIZE(0.. 8)) OF Secondary-CCPCH-TDD-InformationItem

Secondary-CCPCH-TDD-InformationItem ::= SEQUENCE {
	timeSlot						TimeSlot,
	midambleShiftAndBurstType		MidambleShiftAndBurstType,
	tFCI-Presence					TFCI-Presence,
	secondary-CCPCH-TDD-Code-Information				Secondary-CCPCH-TDD-Code-Information,
	tDD-PhysicalChannelOffset		TDD-PhysicalChannelOffset,
	repetitionLength				RepetitionLength,
	repetitionPeriod				RepetitionPeriod,
--	iE-Extensions					ProtocolExtensionContainer { { Secondary-CCPCH-TDD-InformationItem-ExtIEs} } OPTIONAL,
	iE-Extensions					ProtocolExtensionContainer OPTIONAL,
	...
}

--Secondary-CCPCH-TDD-InformationItem-ExtIEs RNSAP-PROTOCOL-EXTENSION ::= {
--	...
--}

Secondary-LCR-CCPCH-TDD-InformationList ::= SEQUENCE (SIZE(0.. 8)) OF Secondary-LCR-CCPCH-TDD-InformationItem

Secondary-LCR-CCPCH-TDD-InformationItem ::= SEQUENCE {
	timeSlotLCR									TimeSlotLCR,
	midambleShiftLCR							MidambleShiftLCR,
	tFCI-Presence								TFCI-Presence,
	secondary-LCR-CCPCH-TDD-Code-Information	Secondary-LCR-CCPCH-TDD-Code-Information,
	tDD-PhysicalChannelOffset					TDD-PhysicalChannelOffset,
	repetitionLength							RepetitionLength,
	repetitionPeriod							RepetitionPeriod,
--	iE-Extensions								ProtocolExtensionContainer { { Secondary-LCR-CCPCH-TDD-InformationItem-ExtIEs} } OPTIONAL,
	iE-Extensions								ProtocolExtensionContainer OPTIONAL,
	...
}

--Secondary-LCR-CCPCH-TDD-InformationItem-ExtIEs RNSAP-PROTOCOL-EXTENSION ::= {
--	...
--}

Secondary-CCPCH-TDD-Code-Information ::= SEQUENCE ( SIZE (1..8)) OF Secondary-CCPCH-TDD-Code-InformationItem

Secondary-CCPCH-TDD-Code-InformationItem ::= SEQUENCE {
	tDD-ChannelisationCode			TDD-ChannelisationCode,
--	iE-Extensions					ProtocolExtensionContainer { {Secondary-CCPCH-TDD-Code-InformationItem-ExtIEs} } OPTIONAL,
	iE-Extensions					ProtocolExtensionContainer OPTIONAL,
	...
}

--Secondary-CCPCH-TDD-Code-InformationItem-ExtIEs RNSAP-PROTOCOL-EXTENSION ::= {
--	...
--}

Secondary-LCR-CCPCH-TDD-Code-Information ::= SEQUENCE ( SIZE (1..8)) OF Secondary-LCR-CCPCH-TDD-Code-InformationItem

Secondary-LCR-CCPCH-TDD-Code-InformationItem ::= SEQUENCE {
	tDD-ChannelisationCodeLCR		TDD-ChannelisationCodeLCR,
	s-CCPCH-TimeSlotFormat-LCR      TDD-DL-DPCH-TimeSlotFormat-LCR,
--	iE-Extensions					ProtocolExtensionContainer { {Secondary-LCR-CCPCH-TDD-Code-InformationItem-ExtIEs} } OPTIONAL,
	iE-Extensions					ProtocolExtensionContainer OPTIONAL,
	...
}

--Secondary-LCR-CCPCH-TDD-Code-InformationItem-ExtIEs RNSAP-PROTOCOL-EXTENSION ::= {
--	...
--}

SecondInterleavingMode ::= ENUMERATED {
	frame-related,
	timeslot-related,
	...
}

Seed ::= INTEGER (0..63)

Service-ID	::=	OCTET STRING (SIZE (3))

SFN ::= INTEGER (0..4095)

SFNSFN-FDD ::= INTEGER(0..614399)

SFNSFN-TDD ::= INTEGER(0..40961)

GA-AccessPointPositionwithOptionalAltitude ::= SEQUENCE {
	geographicalCoordinate						GeographicalCoordinate,
	altitudeAndDirection						GA-AltitudeAndDirection	 OPTIONAL,
--	iE-Extensions								ProtocolExtensionContainer { { GA-AccessPointPositionwithOptionalAltitude-ExtIEs} } OPTIONAL,
	iE-Extensions								ProtocolExtensionContainer OPTIONAL,
	...
}

--GA-AccessPointPositionwithOptionalAltitude-ExtIEs RNSAP-PROTOCOL-EXTENSION ::= {
--	...
--}

SFNSFNChangeLimit ::= INTEGER (1..256)
-- Unit chip, Step 1/16 chip, Range 1/16..16 chip

SFNSFNDriftRate ::= INTEGER (-100..100)
-- Unit chip/s, Step 1/256 chip/s, Range -100/256..+100/256 chip/s

SFNSFNDriftRateQuality ::= INTEGER (0..100)
-- Unit chip/s, Step 1/256 chip/s, Range 0..100/256 chip/s

SFNSFNMeasurementThresholdInformation::= SEQUENCE {
	sFNSFNChangeLimit					SFNSFNChangeLimit					OPTIONAL,
	predictedSFNSFNDeviationLimit		PredictedSFNSFNDeviationLimit		OPTIONAL,
--	iE-Extensions					ProtocolExtensionContainer { { SFNSFNMeasurementThresholdInformation-ExtIEs} }		OPTIONAL,
	iE-Extensions					ProtocolExtensionContainer OPTIONAL,
	...
}

--SFNSFNMeasurementThresholdInformation-ExtIEs RNSAP-PROTOCOL-EXTENSION ::= {
--	...
--}

SFNSFNMeasurementValueInformation ::= SEQUENCE {
	successfullNeighbouringCellSFNSFNObservedTimeDifferenceMeasurementInformation		SEQUENCE (SIZE(1..96)) OF
		SEQUENCE {
			uC-ID		UC-ID,
			sFNSFNValue					SFNSFNValue,
			sFNSFNQuality				SFNSFNQuality					OPTIONAL,
			sFNSFNDriftRate				SFNSFNDriftRate,
			sFNSFNDriftRateQuality		SFNSFNDriftRateQuality		OPTIONAL,
			sFNSFNTimeStampInformation	SFNSFNTimeStampInformation,
--			iE-Extensions				ProtocolExtensionContainer { { SuccessfullNeighbouringCellSFNSFNObservedTimeDifferenceMeasurementInformationItem-ExtIEs} }		OPTIONAL,
			iE-Extensions				ProtocolExtensionContainer  OPTIONAL,
			...
		},
	unsuccessfullNeighbouringCellSFNSFNObservedTimeDifferenceMeasurementInformation		SEQUENCE (SIZE(0..95)) OF
		SEQUENCE {
			uC-ID		UC-ID,
--			iE-Extensions		ProtocolExtensionContainer { { UnsuccessfullNeighbouringCellSFNSFNObservedTimeDifferenceMeasurementInformationItem-ExtIEs} }		OPTIONAL,
			iE-Extensions		ProtocolExtensionContainer OPTIONAL,
			...
		},
--	iE-Extensions		ProtocolExtensionContainer { { SFNSFNMeasurementValueInformationItem-ExtIEs} }		OPTIONAL,
	iE-Extensions		ProtocolExtensionContainer OPTIONAL,
	...
}

--SFNSFNMeasurementValueInformationItem-ExtIEs RNSAP-PROTOCOL-EXTENSION ::= {
--	...
--}

--SuccessfullNeighbouringCellSFNSFNObservedTimeDifferenceMeasurementInformationItem-ExtIEs RNSAP-PROTOCOL-EXTENSION ::= {
--	...
--}

--UnsuccessfullNeighbouringCellSFNSFNObservedTimeDifferenceMeasurementInformationItem-ExtIEs RNSAP-PROTOCOL-EXTENSION ::= {
--	...
--}

SFNSFNQuality ::= INTEGER (0..255)
-- Unit chip, Step 1/16 chip, Range 0.. 255/16 chip

SFNSFNTimeStampInformation ::= CHOICE {
	sFNSFNTimeStamp-FDD		SFN,
	sFNSFNTimeStamp-TDD		SFNSFNTimeStamp-TDD,
	...
}

SFNSFNTimeStamp-TDD::= SEQUENCE {
	sFN					SFN,
	timeSlot			TimeSlot,
--	iE-Extensions					ProtocolExtensionContainer { { SFNSFNTimeStamp-ExtIEs}} OPTIONAL,
	iE-Extensions					ProtocolExtensionContainer OPTIONAL,
	...
}

--SFNSFNTimeStamp-ExtIEs RNSAP-PROTOCOL-EXTENSION ::= {
--	...
--}

SFNSFNValue ::= CHOICE {
	sFNSFN-FDD		SFNSFN-FDD,
	sFNSFN-TDD		SFNSFN-TDD,
	...
}

SID ::= INTEGER (0..7)

SIR-Error-Value			::= INTEGER (0..125)

SIR-Error-Value-IncrDecrThres			::= INTEGER (0..124)

SIR-Value				::= INTEGER (0..63)
-- According to mapping in [11]/[14]

SIR-Value-IncrDecrThres ::= INTEGER (0..62)

SNA-Information ::= SEQUENCE {
	pLMN-Identity	PLMN-Identity,
   listOfSNAs 			ListOfSNAs										OPTIONAL,
--   iE-Extensions		ProtocolExtensionContainer { { SNA-Information-ExtIEs} } OPTIONAL,
   iE-Extensions		ProtocolExtensionContainer OPTIONAL,
   ...
}

--SNA-Information-ExtIEs RNSAP-PROTOCOL-EXTENSION ::= {
--	...
--}

ListOfSNAs ::= SEQUENCE (SIZE (1.. 65536)) OF SNACode

SNACode ::= INTEGER (0..65535)

SpecialBurstScheduling ::= INTEGER (1..256)

S-RNTI					::= INTEGER (0..1048575)
-- From 0 to 2^20-1

S-RNTI-Group			::= SEQUENCE {
	sRNTI					S-RNTI,
	sRNTI-BitMaskIndex		ENUMERATED {
		b1,
		b2,
		b3,
		b4,
		b5,
		b6,
		b7,
		b8,
		b9,
		b10,
		b11,
		b12,
		b13,
		b14,
		b15,
		b16,
		b17,
		b18,
		b19,...
}
}

SRB-Delay ::= INTEGER(0..7,...)



SSDT-SupportIndicator ::= ENUMERATED {
	not-Used-sSDT-supported,
	sSDT-not-supported 
}

STTD-SupportIndicator	::= ENUMERATED {
	sTTD-Supported,
	sTTD-not-Supported
}

Support-8PSK ::= ENUMERATED {
	v8PSK-Supported
}

SyncCase ::= INTEGER (1..2,...)

SynchronisationConfiguration ::= SEQUENCE {
	n-INSYNC-IND			INTEGER (1..256),
 	n-OUTSYNC-IND			INTEGER (1..256),
 	t-RLFAILURE				INTEGER (0..255),
-- Unit seconds, Range 0s .. 25.5s, Step 0.1s
--	iE-Extensions			ProtocolExtensionContainer { { SynchronisationConfiguration-ExtIEs} }		OPTIONAL,
	iE-Extensions			ProtocolExtensionContainer OPTIONAL,
	...
}

--SynchronisationConfiguration-ExtIEs RNSAP-PROTOCOL-EXTENSION ::= {
--	...
--}

SYNC-UL-ProcParameters  ::= SEQUENCE {
	maxSYNC-UL-transmissions		ENUMERATED {v1, v2, v4, v8, ...},
	powerRampStep					INTEGER (0..3, ...),
	...
	}

-- T

T1 ::= ENUMERATED {v10,v20,v30,v40,v50,v60,v70,v80,v90,v100,v120,v140,v160,v200,v300,v400,...}

TDD-AckNack-Power-Offset ::= INTEGER (-7..8,...)
-- Unit dB, Range -7dB .. +8dB, Step 1dB

TDD-ChannelisationCode 			::= ENUMERATED {
	chCode1div1,
	chCode2div1,
	chCode2div2,
	chCode4div1,
	chCode4div2,
	chCode4div3,
	chCode4div4,
	chCode8div1,
	chCode8div2,
	chCode8div3,
	chCode8div4,
	chCode8div5,
	chCode8div6,
	chCode8div7,
	chCode8div8,
	chCode16div1,
	chCode16div2,
	chCode16div3,
	chCode16div4,
	chCode16div5,
	chCode16div6,
	chCode16div7,
	chCode16div8,
	chCode16div9,
	chCode16div10,
	chCode16div11,
	chCode16div12,
	chCode16div13,
	chCode16div14,
	chCode16div15,
	chCode16div16,
	...
}

TDD-ChannelisationCodeLCR ::= SEQUENCE {
	tDD-ChannelisationCode			TDD-ChannelisationCode,
	modulation						Modulation, -- Modulation options for 1.28Mcps TDD in contrast to 3.84Mcps TDD
	...
}

TDD-DCHs-to-Modify ::= SEQUENCE (SIZE (1..128)) OF TDD-DCHs-to-ModifyItem

TDD-DCHs-to-ModifyItem ::= SEQUENCE {
	ul-FP-Mode							UL-FP-Mode	OPTIONAL,
	toAWS								ToAWS		OPTIONAL,
	toAWE								ToAWE		OPTIONAL,
	transportBearerRequestIndicator		TransportBearerRequestIndicator,
	dCH-SpecificInformationList			TDD-DCHs-to-ModifySpecificInformationList,
--	iE-Extensions						ProtocolExtensionContainer { {TDD-DCHs-to-ModifyItem-ExtIEs} } OPTIONAL,
	iE-Extensions						ProtocolExtensionContainer OPTIONAL,
	...
}

--TDD-DCHs-to-ModifyItem-ExtIEs RNSAP-PROTOCOL-EXTENSION ::= {
--	{ ID id-TnlQos						CRITICALITY 	ignore		EXTENSION 	TnlQos	PRESENCE 	optional	},
--	...
--}

TDD-DCHs-to-ModifySpecificInformationList ::= SEQUENCE (SIZE (1..128)) OF TDD-DCHs-to-ModifySpecificItem

TDD-DCHs-to-ModifySpecificItem ::=	SEQUENCE {
	dCH-ID							DCH-ID,
	ul-CCTrCH-ID					CCTrCH-ID		OPTIONAL,
	dl-CCTrCH-ID					CCTrCH-ID		OPTIONAL,
	ul-TransportformatSet			TransportFormatSet	OPTIONAL,
	dl-TransportformatSet			TransportFormatSet	OPTIONAL,
	allocationRetentionPriority		AllocationRetentionPriority OPTIONAL,
	frameHandlingPriority			FrameHandlingPriority	OPTIONAL,
--	iE-Extensions					ProtocolExtensionContainer { {TDD-DCHs-to-ModifySpecificItem-ExtIEs} } OPTIONAL,
	iE-Extensions					ProtocolExtensionContainer OPTIONAL,
	...
}

--TDD-DCHs-to-ModifySpecificItem-ExtIEs RNSAP-PROTOCOL-EXTENSION ::= {
--	{ ID id-Guaranteed-Rate-Information		CRITICALITY ignore	EXTENSION Guaranteed-Rate-Information		PRESENCE optional	}|
--	{ ID id-TrafficClass		CRITICALITY ignore	EXTENSION TrafficClass		PRESENCE optional},
--	...
--}

TDD-DL-Code-Information ::= SEQUENCE ( SIZE (1..240)) OF TDD-DL-Code-InformationItem

TDD-DL-Code-InformationItem ::= SEQUENCE {
	dPCH-ID							DPCH-ID,
	tDD-ChannelisationCode			TDD-ChannelisationCode,
--	iE-Extensions					ProtocolExtensionContainer { {TDD-DL-Code-InformationItem-ExtIEs} } OPTIONAL,
	iE-Extensions					ProtocolExtensionContainer OPTIONAL,
	...
}

--TDD-DL-Code-InformationItem-ExtIEs RNSAP-PROTOCOL-EXTENSION ::= {
--	...
--}

TDD-DL-Code-LCR-Information ::= SEQUENCE (SIZE (1..240)) OF TDD-DL-Code-LCR-InformationItem

TDD-DL-Code-LCR-InformationItem ::= SEQUENCE {
	dPCH-ID									DPCH-ID,
	tdd-ChannelisationCodeLCR				TDD-ChannelisationCodeLCR,
	tdd-DL-DPCH-TimeSlotFormat-LCR  		TDD-DL-DPCH-TimeSlotFormat-LCR,
--	iE-Extensions							ProtocolExtensionContainer { { TDD-DL-Code-LCR-InformationItem-ExtIEs} }		OPTIONAL,
	iE-Extensions							ProtocolExtensionContainer OPTIONAL,
	...
}

--TDD-DL-Code-LCR-InformationItem-ExtIEs RNSAP-PROTOCOL-EXTENSION ::= {
--	...
--}

TDD-DL-DPCH-TimeSlotFormat-LCR ::= CHOICE {
	qPSK						QPSK-DL-DPCH-TimeSlotFormatTDD-LCR,
	eightPSK					EightPSK-DL-DPCH-TimeSlotFormatTDD-LCR,
	...
}

QPSK-DL-DPCH-TimeSlotFormatTDD-LCR ::= INTEGER(0..24,...)

EightPSK-DL-DPCH-TimeSlotFormatTDD-LCR ::= INTEGER(0..24,...)

TDD-DPCHOffset ::= CHOICE {
	initialOffset		INTEGER (0..255),
	noinitialOffset		INTEGER (0..63)
}

TDD-PhysicalChannelOffset		::= INTEGER (0..63)

TDD-TPC-DownlinkStepSize ::= ENUMERATED {
	step-size1,
	step-size2,
	step-size3,
	...
}

TDD-TPC-UplinkStepSize-LCR ::= ENUMERATED {
	step-size1,
	step-size2,
	step-size3,
	...
}

TDD-UL-Code-Information ::= SEQUENCE ( SIZE (1..240)) OF TDD-UL-Code-InformationItem

TDD-UL-Code-InformationItem ::= SEQUENCE {
	dPCH-ID							DPCH-ID,
	tDD-ChannelisationCode			TDD-ChannelisationCode,
--	iE-Extensions					ProtocolExtensionContainer { {TDD-UL-Code-InformationItem-ExtIEs} } OPTIONAL,
	iE-Extensions					ProtocolExtensionContainer OPTIONAL,
	...
}

--TDD-UL-Code-InformationItem-ExtIEs RNSAP-PROTOCOL-EXTENSION ::= {
--	...
--}

TDD-UL-Code-LCR-Information ::= SEQUENCE (SIZE (1..240)) OF TDD-UL-Code-LCR-InformationItem

TDD-UL-Code-LCR-InformationItem ::= SEQUENCE {
	dPCH-ID									DPCH-ID,
	tdd-ChannelisationCodeLCR				TDD-ChannelisationCodeLCR,
	tdd-UL-DPCH-TimeSlotFormat-LCR  		TDD-UL-DPCH-TimeSlotFormat-LCR,
--	iE-Extensions							ProtocolExtensionContainer { { TDD-UL-Code-LCR-InformationItem-ExtIEs} }		OPTIONAL,
	iE-Extensions							ProtocolExtensionContainer OPTIONAL,
	...
}

--TDD-UL-Code-LCR-InformationItem-ExtIEs RNSAP-PROTOCOL-EXTENSION ::= {
--	...
--}

TDD-UL-DPCH-TimeSlotFormat-LCR ::= CHOICE {
	qPSK						QPSK-UL-DPCH-TimeSlotFormatTDD-LCR,
	eightPSK					EightPSK-UL-DPCH-TimeSlotFormatTDD-LCR,
	...
}

QPSK-UL-DPCH-TimeSlotFormatTDD-LCR ::= INTEGER(0..69,...)

EightPSK-UL-DPCH-TimeSlotFormatTDD-LCR ::= INTEGER(0..24,...)

TFCI-Coding ::= ENUMERATED {
	v4,
	v8,
	v16,
	v32,
	...
}

TFCI-Presence ::= ENUMERATED {
	present,
	not-present
}

TFCI-SignallingMode ::= ENUMERATED {
	normal,
	not-Used-split
}
-- The value "Not Used" shall not be used by the SRNC. The procedure shall be rejected by the DRNC if the value "Not Used" is received.

--TGD					::= INTEGER (0|15..269)
TGD					::= INTEGER (0..269)
-- 0 = Undefined, only one transmission gap in the transmission gap pattern sequence 

TGPRC 				::= INTEGER (0..511)
-- 0 = infinity

TGPSID				::= INTEGER (1.. 6)

TGSN				::= INTEGER (0..14)

TimeSlot				::= INTEGER (0..14)

TimeSlotLCR ::= INTEGER (0..6)

TimingAdvanceApplied ::= ENUMERATED {
	yes,
	no
}

SynchronisationIndicator ::= ENUMERATED {
	timingMaintainedSynchronisation,
	...
}

TMGI	::=	SEQUENCE	{
	plmn-id		PLMN-Identity,
	service-id	Service-ID,
--	iE-Extensions					ProtocolExtensionContainer { { TMGI-ExtIEs} }		OPTIONAL,
	iE-Extensions					ProtocolExtensionContainer OPTIONAL,
	...
}

--TMGI-ExtIEs RNSAP-PROTOCOL-EXTENSION ::= {
--	...
--}

TnlQos ::= CHOICE {
	dsField						DsField,
	genericTrafficCategory		GenericTrafficCategory,
	...
}

ToAWE					::= INTEGER (0..2559)

ToAWS					::= INTEGER (0..1279)

TraceDepth						::= ENUMERATED { 
	minimum,
	medium,
	maximum,
	...
}

TraceRecordingSessionReference	::= INTEGER (0..65535)

TraceReference					::= OCTET STRING (SIZE (2..3))

TrafficClass ::= ENUMERATED { 
	conversational, 
	streaming, 
	interactive, 
	background,
	...
}

Transmission-Gap-Pattern-Sequence-Information ::= SEQUENCE (SIZE (1..6)) OF
	SEQUENCE {
		tGPSID			TGPSID,
		tGSN			TGSN,
		tGL1			GapLength,
		tGL2			GapLength	OPTIONAL,
		tGD				TGD,
		tGPL1			GapDuration,
		not-to-be-used-1			GapDuration	OPTIONAL,
			-- This IE shall never be included in the SEQUENCE. If received it shall be ignored
		uL-DL-mode		UL-DL-mode,
		downlink-Compressed-Mode-Method		Downlink-Compressed-Mode-Method		OPTIONAL,
			-- This IE shall be present if the value of the UL/DL mode IE is "DL only" or "UL/DL"
		uplink-Compressed-Mode-Method		Uplink-Compressed-Mode-Method		OPTIONAL,
			-- This IE shall be present if the value of the UL/DL mode IE is "UL only" or "UL/DL"
		dL-FrameType		DL-FrameType,
		delta-SIR1		DeltaSIR,
		delta-SIR-after1	DeltaSIR,
		delta-SIR2		DeltaSIR	OPTIONAL,
		delta-SIR-after2	DeltaSIR	OPTIONAL,
--		iE-Extensions			ProtocolExtensionContainer { {Transmission-Gap-Pattern-Sequence-Information-ExtIEs} } OPTIONAL,
		iE-Extensions			ProtocolExtensionContainer OPTIONAL,
		...
	}

--Transmission-Gap-Pattern-Sequence-Information-ExtIEs RNSAP-PROTOCOL-EXTENSION ::= {
--	...
--}

Transmission-Gap-Pattern-Sequence-ScramblingCode-Information 	::= ENUMERATED{
code-change,
nocode-change
}

Transmission-Gap-Pattern-Sequence-Status-List ::= SEQUENCE (SIZE (0..6)) OF
	SEQUENCE {
		tGPSID			TGPSID,
		tGPRC			TGPRC,
		tGCFN			CFN,
--		iE-Extensions		ProtocolExtensionContainer { { Transmission-Gap-Pattern-Sequence-Status-List-ExtIEs } } OPTIONAL,
		iE-Extensions		ProtocolExtensionContainer OPTIONAL,
		...
}

--Transmission-Gap-Pattern-Sequence-Status-List-ExtIEs RNSAP-PROTOCOL-EXTENSION ::= {
--	...
--}

TransmissionMode	::=ENUMERATED {
	p-t-p, 
	p-t-m, 
	not-provided,
	...
}

TransmissionTimeIntervalDynamic ::= ENUMERATED {
	msec-10,
	msec-20,
	msec-40,
	msec-80,
	...
}

TransmissionTimeIntervalSemiStatic ::= ENUMERATED {
	msec-10,
	msec-20,
	msec-40,
	msec-80,
	dynamic,
	...
}

TransmitDiversityIndicator ::= ENUMERATED {
	active,
	inactive
}

Transmitted-Carrier-Power-Value ::= INTEGER(0..100)
-- according to mapping in [23] and [24]

Transmitted-Carrier-Power-Value-IncrDecrThres ::= INTEGER(0..100)
-- according to mapping in [23] and [24]

TUTRANGPS ::= SEQUENCE {
	ms-part 	INTEGER (0..16383),
	ls-part		INTEGER (0..4294967295)
}

TUTRANGPSChangeLimit ::= INTEGER (1..256)
-- Unit chip, Step 1/16 chip, Range 1/16..16 chip

TUTRANGPSDriftRate ::= INTEGER (-50..50)
-- Unit chip/s, Step 1/256 chip/s, Range -50/256..+50/256 chip/s

TUTRANGPSDriftRateQuality ::= INTEGER (0..50)
-- Unit chip/s, Step 1/256 chip/s, Range 0..50/256 chip/s

TUTRANGPSAccuracyClass ::= ENUMERATED {
	accuracy-class-A,
	accuracy-class-B,
	accuracy-class-C,
	...
}

TUTRANGPSMeasurementThresholdInformation ::= SEQUENCE {
	tUTRANGPSChangeLimit					TUTRANGPSChangeLimit					OPTIONAL,
	predictedTUTRANGPSDeviationLimit		PredictedTUTRANGPSDeviationLimit		OPTIONAL,
--	iE-Extensions					ProtocolExtensionContainer { { TUTRANGPSMeasurementThresholdInformation-ExtIEs} }		OPTIONAL,
	iE-Extensions					ProtocolExtensionContainer OPTIONAL,
	...
}

--TUTRANGPSMeasurementThresholdInformation-ExtIEs RNSAP-PROTOCOL-EXTENSION ::= {
--	...
--}

TUTRANGPSMeasurementValueInformation ::= SEQUENCE {
		tUTRANGPS						TUTRANGPS,
		tUTRANGPSQuality				TUTRANGPSQuality				OPTIONAL,
		tUTRANGPSDriftRate				TUTRANGPSDriftRate,
		tUTRANGPSDriftRateQuality		TUTRANGPSDriftRateQuality		OPTIONAL,
--		iEe-Extensions					ProtocolExtensionContainer { { TUTRANGPSMeasurementValueInformationItem-ExtIEs} }		OPTIONAL,
		iEe-Extensions					ProtocolExtensionContainer OPTIONAL,
		...
}

--TUTRANGPSMeasurementValueInformationItem-ExtIEs RNSAP-PROTOCOL-EXTENSION ::= {
--	...
--}

TUTRANGPSQuality ::= INTEGER (0..255)
-- Unit chip, Step 1/16 chip, Range 0.. 255/16 chip

TransportBearerID		::= INTEGER (0..4095)

TransportBearerRequestIndicator		::= ENUMERATED {
	bearer-requested,
	bearer-not-requested,
	...
}

TransportBlockSize			::= INTEGER (0..5000)
-- Unit is bits

TransportFormatCombination-Beta ::= CHOICE {
	signalledGainFactors 	SEQUENCE {
		betaC					BetaCD,
		betaD					BetaCD,
	    refTFCNumber			RefTFCNumber	OPTIONAL,
--		iE-Extensions			ProtocolExtensionContainer { { SignalledGainFactors-ExtIEs} } OPTIONAL,
		iE-Extensions			ProtocolExtensionContainer OPTIONAL,
		...
	},
	refTFCNumber			RefTFCNumber,
	...
}

--SignalledGainFactors-ExtIEs RNSAP-PROTOCOL-EXTENSION ::= {
--	...
--}

TFCS ::= SEQUENCE {
	tFCSvalues			CHOICE {
		no-Split-in-TFCI			TFCS-TFCSList,
		not-Used-split-in-TFCI		NULL,
		-- This choice shall never be made by the SRNC and the DRNC shall consider the procedure as failed if it is received.
		...
	},
--	iE-Extensions		ProtocolExtensionContainer  { { TFCS-ExtIEs} }		OPTIONAL,
	iE-Extensions		ProtocolExtensionContainer  OPTIONAL,
	...
}

--TFCS-ExtIEs RNSAP-PROTOCOL-EXTENSION ::= {
--	...
--}

TFCS-TFCSList ::= SEQUENCE (SIZE (1..1024)) OF
	SEQUENCE {
		cTFC				TFCS-CTFC,
		tFC-Beta		TransportFormatCombination-Beta 	OPTIONAL,
        -- The IE shall be present if the TFCS concerns a UL DPCH [FDD - or PRACH channel in FDD]
--		iE-Extensions		ProtocolExtensionContainer  { { TFCS-TFCSList-ExtIEs} }		OPTIONAL,
		iE-Extensions		ProtocolExtensionContainer  OPTIONAL,
	...
}

--TFCS-TFCSList-ExtIEs RNSAP-PROTOCOL-EXTENSION ::= {
--	...
--}

TFCS-CTFC ::= CHOICE {
	ctfc2bit							INTEGER (0..3),
	ctfc4bit							INTEGER (0..15),
	ctfc6bit							INTEGER (0..63),
	ctfc8bit							INTEGER (0..255),
	ctfc12bit							INTEGER (0..4095),
	ctfc16bit							INTEGER (0..65535),
	ctfcmaxbit							INTEGER (0..16777215)
}

TransportFormatSet ::= SEQUENCE {
	dynamicParts			TransportFormatSet-DynamicPartList,
	semi-staticPart			TransportFormatSet-Semi-staticPart,
--	iE-Extensions			ProtocolExtensionContainer { {TransportFormatSet-ExtIEs} } OPTIONAL,
	iE-Extensions			ProtocolExtensionContainer OPTIONAL,
	...
}

--TransportFormatSet-ExtIEs RNSAP-PROTOCOL-EXTENSION ::= {
--	...
--}

TransportFormatSet-DynamicPartList ::= SEQUENCE (SIZE (1..32)) OF
	SEQUENCE {
		nrOfTransportBlocks		NrOfTransportBlocks,
		transportBlockSize		TransportBlockSize		OPTIONAL
		-- This IE shall be present if nrOfTransportBlocks is greater than 0 --,
		mode				TransportFormatSet-ModeDP,
--		iE-Extensions			ProtocolExtensionContainer { {TransportFormatSet-DynamicPartList-ExtIEs} } OPTIONAL,
		iE-Extensions			ProtocolExtensionContainer OPTIONAL,
		...
	}

--TransportFormatSet-DynamicPartList-ExtIEs RNSAP-PROTOCOL-EXTENSION ::= {
--	...
--}

TransportFormatSet-ModeDP ::= CHOICE {
	tdd 				TDD-TransportFormatSet-ModeDP,
	notApplicable		NULL,
	...
}

TDD-TransportFormatSet-ModeDP ::= SEQUENCE {
	transmissionTimeIntervalInformation		TransmissionTimeIntervalInformation		OPTIONAL,
	-- This IE shall be present if the “Transmission Time Interval” of the “Semi-static Transport Format Information” is “dynamic”. Otherwise it is absent.
--	iE-Extensions							ProtocolExtensionContainer { {TDD-TransportFormatSet-ModeDP-ExtIEs} } OPTIONAL,
	iE-Extensions							ProtocolExtensionContainer OPTIONAL,
	...
	}

--TDD-TransportFormatSet-ModeDP-ExtIEs RNSAP-PROTOCOL-EXTENSION ::= {
--	...
--}

TransmissionTimeIntervalInformation ::= SEQUENCE (SIZE (1..4)) OF
	SEQUENCE {
		transmissionTimeInterval	TransmissionTimeIntervalDynamic,
--		iE-Extensions			ProtocolExtensionContainer { {TransmissionTimeIntervalInformation-ExtIEs} } OPTIONAL,
		iE-Extensions			ProtocolExtensionContainer OPTIONAL,
		...
	}

--TransmissionTimeIntervalInformation-ExtIEs RNSAP-PROTOCOL-EXTENSION ::= {
--	...
--}

Transmitted-Code-Power-Value ::= INTEGER (0..127)
-- According to mapping in [11]/[14]

Transmitted-Code-Power-Value-IncrDecrThres ::= INTEGER (0..112,...)

TransportFormatManagement ::= ENUMERATED {
	cell-based,
	ue-based,
	...
}

TransportFormatSet-Semi-staticPart ::= SEQUENCE {
	transmissionTime 		TransmissionTimeIntervalSemiStatic,
	channelCoding			ChannelCodingType,
	codingRate			CodingRate				OPTIONAL
	-- This IE shall be present if channelCoding is 'convolutional' or 'turbo' --,
	rateMatcingAttribute		RateMatchingAttribute,
	cRC-Size			CRC-Size,
	mode				TransportFormatSet-ModeSSP,
--	iE-Extensions			ProtocolExtensionContainer { {TransportFormatSet-Semi-staticPart-ExtIEs} } OPTIONAL,
	iE-Extensions			ProtocolExtensionContainer OPTIONAL,
	...
}

--TransportFormatSet-Semi-staticPart-ExtIEs RNSAP-PROTOCOL-EXTENSION ::= {
--	...
--}

TransportFormatSet-ModeSSP ::= CHOICE {
	tdd				SecondInterleavingMode,
	notApplicable			NULL,
	...
}

TransportLayerAddress			::= BIT STRING (SIZE(1..160, ...))

TrCH-SrcStatisticsDescr		::= ENUMERATED {
	speech,
	rRC,
	unknown,
	...
}

TSTD-Indicator ::= ENUMERATED {
	active,
	inactive
}

TSTD-Support-Indicator ::= ENUMERATED {
	tSTD-supported,
	tSTD-not-supported
}

TxDiversityIndicator	::= ENUMERATED {
	true,
	false
}

TypeOfError ::= ENUMERATED {
	not-understood,
	missing,
	...
}

-- U

UARFCN					::= INTEGER (0..16383,...)
-- Corresponds to: 0.0Hz..3276.6Mhz. See [7], [43]

UDRE ::= ENUMERATED {
	lessThan1,
	between1-and-4,
	between4-and-8,
	over8,
	...
}

UE-Capabilities-Info ::= SEQUENCE {
	hSDSCH-Physical-Layer-Category		INTEGER (1..64,...),
--	iE-Extensions						ProtocolExtensionContainer { { UE-Capabilities-Info-ExtIEs } }			OPTIONAL,
	iE-Extensions						ProtocolExtensionContainer OPTIONAL,
	...
}

--UE-Capabilities-Info-ExtIEs RNSAP-PROTOCOL-EXTENSION ::= {
--	...
--}

UEIdentity					::= CHOICE {
	imsi		IMSI,
	imei		IMEI,
	imeisv		IMEISV,
	...
}

UEMeasurementHysteresisTime	::= INTEGER (0..15)
	-- Unit dB
	-- Range 0..7.5 dB
	-- Step 0.5 dB

UEMeasurementParameterModAllow ::= ENUMERATED {
	parameterModificationAllowed,
	...
}

UEMeasurementReportCharacteristics ::= CHOICE {
	periodic			UEMeasurementReportCharacteristicsPeriodic,
	event1h				UEMeasurementReportCharacteristicsEvent1h,
	event1i				UEMeasurementReportCharacteristicsEvent1i,
	event6a				UEMeasurementReportCharacteristicsEvent6a,
	event6b				UEMeasurementReportCharacteristicsEvent6b,
	event6c				UEMeasurementReportCharacteristicsEvent6c,
	event6d				UEMeasurementReportCharacteristicsEvent6d,
	...,
	extension-ReportCharacteristics		UEMeasurementReportCharacteristics-Extension
}

UEMeasurementReportCharacteristicsEvent1h ::= SEQUENCE {
	uEMeasurementTreshold		UEMeasurementThreshold,
	uEMeasurementTimeToTrigger	UEMeasurementTimeToTrigger,
	uEMeasurementHysteresisTime	UEMeasurementHysteresisTime,
--	iE-Extensions				ProtocolExtensionContainer { { UEMeasurementReportCharacteristicsEvent1h-ExtIEs} } OPTIONAL,
	iE-Extensions				ProtocolExtensionContainer OPTIONAL,
	...
}

--UEMeasurementReportCharacteristicsEvent1h-ExtIEs RNSAP-PROTOCOL-EXTENSION ::= {
--	...
--}

UEMeasurementReportCharacteristicsEvent1i ::= SEQUENCE {
	uEMeasurementTreshold		UEMeasurementThreshold,
	uEMeasurementTimeToTrigger	UEMeasurementTimeToTrigger,
	uEMeasurementHysteresisTime	UEMeasurementHysteresisTime,
--	iE-Extensions				ProtocolExtensionContainer { { UEMeasurementReportCharacteristicsEvent1i-ExtIEs} } OPTIONAL,
	iE-Extensions				ProtocolExtensionContainer OPTIONAL,
	...
}

--UEMeasurementReportCharacteristicsEvent1i-ExtIEs RNSAP-PROTOCOL-EXTENSION ::= {
--	...
--}

UEMeasurementReportCharacteristicsEvent6a ::= SEQUENCE {
	uEMeasurementTreshold		UEMeasurementThreshold,
	uEMeasurementTimeToTrigger	UEMeasurementTimeToTrigger,
--	iE-Extensions				ProtocolExtensionContainer { { UEMeasurementReportCharacteristicsEvent6a-ExtIEs} } OPTIONAL,
	iE-Extensions				ProtocolExtensionContainer OPTIONAL,
	...
}

--UEMeasurementReportCharacteristicsEvent6a-ExtIEs RNSAP-PROTOCOL-EXTENSION ::= {
--	...
--}

UEMeasurementReportCharacteristicsEvent6b ::= SEQUENCE {
	uEMeasurementTreshold		UEMeasurementThreshold,
	uEMeasurementTimeToTrigger	UEMeasurementTimeToTrigger,
--	iE-Extensions				ProtocolExtensionContainer { { UEMeasurementReportCharacteristicsEvent6b-ExtIEs} } OPTIONAL,
	iE-Extensions				ProtocolExtensionContainer OPTIONAL,
	...
}

--UEMeasurementReportCharacteristicsEvent6b-ExtIEs RNSAP-PROTOCOL-EXTENSION ::= {
--	...
--}

UEMeasurementReportCharacteristicsEvent6c ::= SEQUENCE {
	uEMeasurementTimeToTrigger	UEMeasurementTimeToTrigger,
--	iE-Extensions				ProtocolExtensionContainer { { UEMeasurementReportCharacteristicsEvent6c-ExtIEs} } OPTIONAL,
	iE-Extensions				ProtocolExtensionContainer OPTIONAL,
	...
}

--UEMeasurementReportCharacteristicsEvent6c-ExtIEs RNSAP-PROTOCOL-EXTENSION ::= {
--	...
--}

UEMeasurementReportCharacteristicsEvent6d ::= SEQUENCE {
	uEMeasurementTimeToTrigger	UEMeasurementTimeToTrigger,
--	iE-Extensions				ProtocolExtensionContainer { { UEMeasurementReportCharacteristicsEvent6d-ExtIEs} } OPTIONAL,
	iE-Extensions				ProtocolExtensionContainer OPTIONAL,
	...
}

--UEMeasurementReportCharacteristicsEvent6d-ExtIEs RNSAP-PROTOCOL-EXTENSION ::= {
--	...
--}

UEMeasurementReportCharacteristicsPeriodic ::= SEQUENCE {
	amountofReporting		UEMeasurementReportCharacteristicsPeriodicAmountofReporting,
	reportingInterval		UEMeasurementReportCharacteristicsPeriodicReportingInterval,
--	iE-Extensions			ProtocolExtensionContainer { {UEMeasurementReportCharacteristicsPeriodic-ExtIEs} } OPTIONAL,
	iE-Extensions			ProtocolExtensionContainer OPTIONAL,
	...
}

UEMeasurementReportCharacteristicsPeriodicAmountofReporting::= ENUMERATED {
	r1,
	r2,
	r4,
	r8,
	r16,
	r32,
	r64,
	rInfinity
}

UEMeasurementReportCharacteristicsPeriodicReportingInterval::= ENUMERATED {
	r250,
	r500,
	r1000,
	r2000,
	r3000,
	r4000,
	r6000,
	r8000,
	r12000,
	r16000,
	r20000,
	r24000,
	r28000,
	r32000,
	r64000
}

--UEMeasurementReportCharacteristicsPeriodic-ExtIEs RNSAP-PROTOCOL-EXTENSION ::= {
--	...
--}

--UEMeasurementReportCharacteristics-Extension	::= ProtocolIE-Single-Container {{ UEMeasurementReportCharacteristics-ExtensionIE }}
UEMeasurementReportCharacteristics-Extension	::= ProtocolIE-Single-Container

--UEMeasurementReportCharacteristics-ExtensionIE RNSAP-PROTOCOL-IES ::= {
--	...
--}

UEMeasurementThreshold 			::= CHOICE {
	timeslotISCP					UEMeasurementThresholdDLTimeslotISCP,
	uETransmitPower					UEMeasurementThresholdUETransmitPower,
	...,
	extension-UEMeasurementThreshold	UEMeasurementThreshold-Extension
}

UEMeasurementThresholdDLTimeslotISCP ::=	INTEGER(-115..-25)

UEMeasurementThresholdUETransmitPower ::=	INTEGER(-50..33)

--UEMeasurementThreshold-Extension	::= ProtocolIE-Single-Container {{ UEMeasurementThreshold-ExtensionIE }}
UEMeasurementThreshold-Extension	::= ProtocolIE-Single-Container

--UEMeasurementThreshold-ExtensionIE RNSAP-PROTOCOL-IES ::= {
--	...
--}

UEMeasurementTimeslotInfoHCR::= SEQUENCE (SIZE (1..15)) OF UEMeasurementTimeslotInfoHCR-IEs

UEMeasurementTimeslotInfoHCR-IEs ::= SEQUENCE {
	timeSlot						TimeSlot,
	burstType						UEMeasurementTimeslotInfoHCRBurstType,
--	iE-Extensions					ProtocolExtensionContainer { { UEMeasurementTimeslotInfoHCR-IEs-ExtIEs} }		OPTIONAL,
	iE-Extensions					ProtocolExtensionContainer OPTIONAL,
	...
}

UEMeasurementTimeslotInfoHCRBurstType ::= ENUMERATED {
	type1,
	type2,
	type3,
	...
}

--UEMeasurementTimeslotInfoHCR-IEs-ExtIEs RNSAP-PROTOCOL-EXTENSION ::= {
--	...
--}

UEMeasurementTimeslotInfoLCR::= SEQUENCE (SIZE (1..6)) OF UEMeasurementTimeslotInfoLCR-IEs

UEMeasurementTimeslotInfoLCR-IEs ::= SEQUENCE {
	timeSlot						TimeSlotLCR,
--	iE-Extensions					ProtocolExtensionContainer { { UEMeasurementTimeslotInfoLCR-IEs-ExtIEs} }		OPTIONAL,
	iE-Extensions					ProtocolExtensionContainer OPTIONAL,
	...

}

--UEMeasurementTimeslotInfoLCR-IEs-ExtIEs RNSAP-PROTOCOL-EXTENSION ::= {
--	...
--}

UEMeasurementTimeToTrigger ::= ENUMERATED { 
	r0,
	r10,
	r20,
	r40,
	r60,
	r80,
	r100,
	r120,
	r160,
	r200,
	r240,
	r320,
	r640,
	r1280,
	r2560,
	r5000
}

UEMeasurementType ::= ENUMERATED { 
	primary-CCPCH-RSCP, 
	dL-Timeslot-ISCP,
	uE-Transmitted-power, 
	...
}

UEMeasurementValue ::= CHOICE {
	uE-Transmitted-Power		UE-MeasurementValue-UE-Transmitted-Power, 
	primary-CCPCH-RSCP			UE-MeasurementValue-Primary-CCPCH-RSCP,
	dL-Timeslot-ISCP			UE-MeasurementValue-DL-Timeslot-ISCP,
	...,
	extension-UEMeasurementValue		UEMeasurementValue-Extension
}

UE-MeasurementValue-UE-Transmitted-Power ::= SEQUENCE {
	uEMeasurementTransmittedPowerListHCR		UEMeasurementValueTransmittedPowerListHCR	OPTIONAL,
-- Mandatory for 3.84Mcps TDD, Not applicable for 1.28Mcps TDD
	uEMeasurementTransmittedPowerListLCR		UEMeasurementValueTransmittedPowerListLCR	OPTIONAL,
-- Mandatory for 1.28Mcps TDD, Not applicable for 3.84Mcps TDD
--	iE-Extensions								ProtocolExtensionContainer { { UE-MeasurementValue-UE-Transmitted-Power-ExtIEs} }		OPTIONAL,
	iE-Extensions								ProtocolExtensionContainer OPTIONAL,
	...
}

--UE-MeasurementValue-UE-Transmitted-Power-ExtIEs RNSAP-PROTOCOL-EXTENSION ::= {
--	...
--}

UEMeasurementValueTransmittedPowerListHCR	::= SEQUENCE (SIZE (1..15)) OF UEMeasurementValueTransmittedPowerListHCR-IEs

UEMeasurementValueTransmittedPowerListHCR-IEs ::= SEQUENCE {
	timeSlot						TimeSlot,
	uETransmitPower					INTEGER(0..104),
	-- mapping according to [24],values 0..20 not used
--	iE-Extensions								ProtocolExtensionContainer { { UEMeasurementValueTransmittedPowerListHCR-IEs-ExtIEs} }		OPTIONAL,
	iE-Extensions								ProtocolExtensionContainer OPTIONAL,
	...

}

--UEMeasurementValueTransmittedPowerListHCR-IEs-ExtIEs RNSAP-PROTOCOL-EXTENSION ::= {
--	...
--}
UEMeasurementValueTransmittedPowerListLCR	::= SEQUENCE (SIZE (1..6)) OF UEMeasurementValueTransmittedPowerListLCR-IEs

UEMeasurementValueTransmittedPowerListLCR-IEs ::= SEQUENCE {
	timeSlotLCR						TimeSlotLCR,
	uETransmitPower					INTEGER(0..104),
	-- mapping according to [24],values 0..20 not used
--	iE-Extensions								ProtocolExtensionContainer { { UEMeasurementValueTransmittedPowerListLCR-IEs-ExtIEs} }		OPTIONAL,
	iE-Extensions								ProtocolExtensionContainer OPTIONAL,
	...

}
--UEMeasurementValueTransmittedPowerListLCR-IEs-ExtIEs RNSAP-PROTOCOL-EXTENSION ::= {
--	...
--}


UE-MeasurementValue-Primary-CCPCH-RSCP::= SEQUENCE {
	primaryCCPCH-RSCP					PrimaryCCPCH-RSCP				OPTIONAL,
	primaryCCPCH-RSCP-Delta				PrimaryCCPCH-RSCP-Delta			OPTIONAL,
--	iE-Extensions						ProtocolExtensionContainer { { UE-MeasurementValue-Primary-CCPCH-RSCP-ExtIEs} }		OPTIONAL,
	iE-Extensions						ProtocolExtensionContainer OPTIONAL,
	...
}

--UE-MeasurementValue-Primary-CCPCH-RSCP-ExtIEs RNSAP-PROTOCOL-EXTENSION ::= {
--	...
--}

UE-MeasurementValue-DL-Timeslot-ISCP ::= SEQUENCE {
	uEMeasurementTimeslotISCPListHCR		UEMeasurementValueTimeslotISCPListHCR	OPTIONAL,
-- Mandatory for 3.84Mcps TDD, Not applicable for 1.28Mcps TDD
	uEMeasurementTimeslotISCPListLCR		UEMeasurementValueTimeslotISCPListLCR	OPTIONAL,
-- Mandatory for 1.28Mcps TDD, Not applicable for 3.84Mcps TDD
--	iE-Extensions								ProtocolExtensionContainer { { UE-MeasurementValue-DL-Timeslot-ISCP-ExtIEs} }		OPTIONAL,
	iE-Extensions								ProtocolExtensionContainer OPTIONAL,
	...
}

--UE-MeasurementValue-DL-Timeslot-ISCP-ExtIEs RNSAP-PROTOCOL-EXTENSION ::= {
--	...
--}

UEMeasurementValueTimeslotISCPListHCR	::= SEQUENCE (SIZE (1..15)) OF UEMeasurementValueTimeslotISCPListHCR-IEs

UEMeasurementValueTimeslotISCPListHCR-IEs ::= SEQUENCE {
	timeSlot						TimeSlot,
	dL-TimeslotISCP					DL-TimeslotISCP,
--	iE-Extensions					ProtocolExtensionContainer { { UEMeasurementValueTimeslotISCPListHCR-IEs-ExtIEs} }		OPTIONAL,
	iE-Extensions					ProtocolExtensionContainer OPTIONAL,
	...

}
--UEMeasurementValueTimeslotISCPListHCR-IEs-ExtIEs RNSAP-PROTOCOL-EXTENSION ::= {
--	...
--}
UEMeasurementValueTimeslotISCPListLCR	::= SEQUENCE (SIZE (1..6)) OF UEMeasurementValueTimeslotISCPListLCR-IEs

UEMeasurementValueTimeslotISCPListLCR-IEs ::= SEQUENCE {
	timeSlotLCR						TimeSlotLCR,
	dL-TimeslotISCP					DL-TimeslotISCP,
--	iE-Extensions					ProtocolExtensionContainer { { UEMeasurementValueTimeslotISCPListLCR-IEs-ExtIEs} }		OPTIONAL,
	iE-Extensions					ProtocolExtensionContainer OPTIONAL,
	...

}
--UEMeasurementValueTimeslotISCPListLCR-IEs-ExtIEs RNSAP-PROTOCOL-EXTENSION ::= {
--	...
--}

--UEMeasurementValue-Extension	::= ProtocolIE-Single-Container {{ UEMeasurementValue-ExtensionIE }}
UEMeasurementValue-Extension	::= ProtocolIE-Single-Container 

--UEMeasurementValue-ExtensionIE RNSAP-PROTOCOL-IES ::= {
--	...
--}

UEMeasurementValueInformation ::= CHOICE {
	measurementAvailable		UEMeasurementValueInformationAvailable,
	measurementnotAvailable		UEMeasurementValueInformationnotAvailable
}

UEMeasurementValueInformationAvailable::= SEQUENCE {
	uEmeasurementValue			UEMeasurementValue,
--	ie-Extensions				ProtocolExtensionContainer { { UEMeasurementValueInformationAvailableItem-ExtIEs} }		OPTIONAL,
	iE-Extensions				ProtocolExtensionContainer OPTIONAL,
	...
}

--UEMeasurementValueInformationAvailableItem-ExtIEs RNSAP-PROTOCOL-EXTENSION ::= {
--	...
--}

UEMeasurementValueInformationnotAvailable ::= NULL

UE-State ::= CHOICE {
	cell-fach-pch												Cell-Fach-Pch-State,
	ura-pch														Ura-Pch-State,
	...
}



Cell-Fach-Pch-State ::= SEQUENCE {
	d-RNTI							D-RNTI, 
--	iE-Extensions					ProtocolExtensionContainer  { { Cell-Fach-Pch-State-ExtIEs} }		OPTIONAL,
	iE-Extensions					ProtocolExtensionContainer  OPTIONAL,
	...
}

--Cell-Fach-Pch-State-ExtIEs RNSAP-PROTOCOL-EXTENSION ::= {
--	...
--}

Ura-Pch-State ::= SEQUENCE {
	srnc-id							RNC-ID, 
	ura-id							URA-ID,
--	iE-Extensions					ProtocolExtensionContainer  { { Ura-Pch-State-ExtIEs} }		OPTIONAL,
	iE-Extensions					ProtocolExtensionContainer  OPTIONAL,
	...
}

--Ura-Pch-State-ExtIEs RNSAP-PROTOCOL-EXTENSION ::= {
--	...
--}



UL-DL-mode ::= ENUMERATED {
	ul-only,
	dl-only,
	both-ul-and-dl
}

UL-DPDCHIndicatorEDCH ::= ENUMERATED {
	uL-DPDCH-present,
	uL-DPDCH-not-present}

UL-Timeslot-Information::= SEQUENCE ( SIZE (1..15)) OF UL-Timeslot-InformationItem

UL-Timeslot-InformationItem ::= SEQUENCE {
	timeSlot						TimeSlot,
	midambleShiftAndBurstType		MidambleShiftAndBurstType,
	tFCI-Presence					TFCI-Presence,
	uL-Code-Information				TDD-UL-Code-Information,
--	iE-Extensions					ProtocolExtensionContainer { {UL-Timeslot-InformationItem-ExtIEs} } OPTIONAL,
	iE-Extensions					ProtocolExtensionContainer OPTIONAL,
	...
}

--UL-Timeslot-InformationItem-ExtIEs RNSAP-PROTOCOL-EXTENSION ::= {
--	...
--}

UL-TimeslotLCR-Information ::= SEQUENCE (SIZE (1..6)) OF UL-TimeslotLCR-InformationItem

UL-TimeslotLCR-InformationItem ::= SEQUENCE {
	timeSlotLCR								TimeSlotLCR,
	midambleShiftLCR						MidambleShiftLCR,
	tFCI-Presence							TFCI-Presence,
	uL-Code-LCR-InformationList			TDD-UL-Code-LCR-Information,
--	iE-Extensions							ProtocolExtensionContainer { { UL-TimeslotLCR-InformationItem-ExtIEs} }		OPTIONAL,
	iE-Extensions							ProtocolExtensionContainer OPTIONAL,
	...
}

--UL-TimeslotLCR-InformationItem-ExtIEs RNSAP-PROTOCOL-EXTENSION ::= {
--	...
--}

UL-TimeSlot-ISCP-Info ::= SEQUENCE (SIZE (1..15)) OF UL-TimeSlot-ISCP-InfoItem

UL-TimeSlot-ISCP-InfoItem ::= SEQUENCE {
	timeSlot					TimeSlot,
	uL-TimeslotISCP				UL-TimeslotISCP,
--	iE-Extensions				ProtocolExtensionContainer { { UL-TimeSlot-ISCP-InfoItem-ExtIEs} } OPTIONAL,
	iE-Extensions				ProtocolExtensionContainer OPTIONAL,
	...
}

--UL-TimeSlot-ISCP-InfoItem-ExtIEs RNSAP-PROTOCOL-EXTENSION ::= {
--	...
--}

UL-TimeSlot-ISCP-LCR-Info ::= SEQUENCE (SIZE (1..6)) OF	UL-TimeSlot-ISCP-LCR-InfoItem

UL-TimeSlot-ISCP-LCR-InfoItem ::= SEQUENCE {
 	timeSlotLCR						TimeSlotLCR,
	iSCP							UL-Timeslot-ISCP-Value,
--	iE-Extensions					ProtocolExtensionContainer { { UL-TimeSlot-ISCP-LCR-InfoItem-ExtIEs} }		OPTIONAL,
	iE-Extensions					ProtocolExtensionContainer OPTIONAL,
	...
 }

--UL-TimeSlot-ISCP-LCR-InfoItem-ExtIEs RNSAP-PROTOCOL-EXTENSION ::= {
--	...
--}

UL-Timeslot-ISCP-Value ::= UL-TimeslotISCP

UL-Timeslot-ISCP-Value-IncrDecrThres ::= INTEGER(0..126)
-- Unit dB. Step 0.5dB
-- e.g. Value 100 means 50dB

UL-TimingAdvanceCtrl-LCR ::= SEQUENCE {
	sync-UL-codes-bitmap						BIT STRING (SIZE(8)),
	fPACH-info									FPACH-Information,
	prxUpPCHdes									INTEGER (-120 .. -58, ...),
	syncUL-procParameter						SYNC-UL-ProcParameters,
	mMax										INTEGER (1..32),
	...
	}

Uplink-Compressed-Mode-Method 	::= ENUMERATED {
	sFdiv2,
	higher-layer-scheduling,
	...
}

UL-SIR					::= INTEGER (-82..173)
-- The UL-SIR gives the UL-SIR in number of 0.1 dB steps.
-- E.g. Value 173 means 17.3 dB
-- Unit dB. Step 0.1 dB.

UC-ID ::= SEQUENCE {
	rNC-ID				RNC-ID,
	c-ID				C-ID,
--	iE-Extensions			ProtocolExtensionContainer { {UC-ID-ExtIEs} } OPTIONAL,
	iE-Extensions			ProtocolExtensionContainer OPTIONAL,
	...
}

--UC-ID-ExtIEs RNSAP-PROTOCOL-EXTENSION ::= {
--	...
--}

UL-DPCCH-SlotFormat			::= INTEGER (0..5,...)

UL-FP-Mode ::= ENUMERATED {
	normal,
	silent,
	...
}

UL-PhysCH-SF-Variation ::= ENUMERATED {
	sf-variation-supported,
	sf-variation-not-supported
}

UL-ScramblingCode ::= SEQUENCE {
	ul-ScramblingCodeNumber		UL-ScramblingCodeNumber,
	ul-ScramblingCodeLength		UL-ScramblingCodeLength,
--	iE-Extensions			ProtocolExtensionContainer { {UL-ScramblingCode-ExtIEs} } OPTIONAL
	iE-Extensions			ProtocolExtensionContainer OPTIONAL
}

--UL-ScramblingCode-ExtIEs RNSAP-PROTOCOL-EXTENSION ::= {
--	...
--}

UL-ScramblingCodeLength ::= ENUMERATED {
	short,
	long
}

UL-ScramblingCodeNumber			::= INTEGER (0..16777215)

UL-Synchronisation-Parameters-LCR ::= SEQUENCE {
	uL-Synchronisation-StepSize			UL-Synchronisation-StepSize,
	uL-Synchronisation-Frequency			UL-Synchronisation-Frequency,
--	iE-Extensions					ProtocolExtensionContainer { { UL-Synchronisation-Parameters-LCR-ExtIEs } }		OPTIONAL,
	iE-Extensions					ProtocolExtensionContainer OPTIONAL,
	...
}

--UL-Synchronisation-Parameters-LCR-ExtIEs RNSAP-PROTOCOL-EXTENSION ::= {
--	...
--}

UL-Synchronisation-StepSize ::= INTEGER (1..8)

UL-Synchronisation-Frequency ::= INTEGER (1..8)

UL-TimeslotISCP			::= INTEGER (0..127)
-- According to mapping in [14]

UpPTSInterferenceValue	::=	INTEGER (0..127,...)

Unidirectional-DCH-Indicator	::= ENUMERATED {
	downlink-DCH-only,
	uplink-DCH-only
}

URA-ID					::= INTEGER (0..65535)

URA-Information ::= SEQUENCE {
	uRA-ID								URA-ID,
	multipleURAsIndicator				MultipleURAsIndicator,
	rNCsWithCellsInTheAccessedURA-List	RNCsWithCellsInTheAccessedURA-List	OPTIONAL,
--	iE-Extensions						ProtocolExtensionContainer { {URA-Information-ExtIEs} } OPTIONAL,
	iE-Extensions						ProtocolExtensionContainer OPTIONAL,
	...
}

--URA-Information-ExtIEs RNSAP-PROTOCOL-EXTENSION ::= {
--	...
--}

RNCsWithCellsInTheAccessedURA-List ::= SEQUENCE (SIZE (1..15)) OF RNCsWithCellsInTheAccessedURA-Item

RNCsWithCellsInTheAccessedURA-Item ::= SEQUENCE {
	rNC-ID							RNC-ID,
--	iE-Extensions					ProtocolExtensionContainer { {RNCsWithCellsInTheAccessedURA-Item-ExtIEs} } OPTIONAL,
	iE-Extensions					ProtocolExtensionContainer OPTIONAL,
	...
}

--RNCsWithCellsInTheAccessedURA-Item-ExtIEs RNSAP-PROTOCOL-EXTENSION ::= {
--	...
--}

USCH-ID					::= INTEGER (0..255)

USCH-Information ::=  SEQUENCE (SIZE (1..10)) OF USCH-InformationItem

USCH-InformationItem ::= SEQUENCE {
	uSCH-ID								USCH-ID,
	ul-CCTrCH-ID						CCTrCH-ID,
	trChSourceStatisticsDescriptor		TrCH-SrcStatisticsDescr,
	transportFormatSet					TransportFormatSet,
	allocationRetentionPriority 		AllocationRetentionPriority,
	schedulingPriorityIndicator			SchedulingPriorityIndicator,
	rb-Info								RB-Info,
--	iE-Extensions						ProtocolExtensionContainer { {USCH-InformationItem-ExtIEs} } OPTIONAL,
	iE-Extensions						ProtocolExtensionContainer OPTIONAL,
	...
}

--USCH-InformationItem-ExtIEs RNSAP-PROTOCOL-EXTENSION ::= {
--	{ ID id-TrafficClass		CRITICALITY ignore	EXTENSION TrafficClass		PRESENCE mandatory	}|
--	{ ID id-BindingID						CRITICALITY	ignore		EXTENSION 	BindingID	PRESENCE 	optional	}|
	-- Shall be ignored if bearer establishment with ALCAP.
--	{ ID id-TransportLayerAddress			CRITICALITY	ignore		EXTENSION 	TransportLayerAddress		PRESENCE 	optional	},
	-- Shall be ignored if bearer establishment with ALCAP.
--	...
--}

User-Plane-Congestion-Fields-Inclusion		::= ENUMERATED { shall-be-included }

-- V
-- W
-- X
-- Y
-- Z

--END


--9.3.5	Common Definitions
-- **************************************************************
--
-- Common definitions
--
-- **************************************************************

--RNSAP-CommonDataTypes {
--itu-t (0) identified-organization (4) etsi (0) mobileDomain (0) 
--umts-Access (20) modules (3) rnsap (1) version1 (1) rnsap-CommonDataTypes (3)  }

--DEFINITIONS AUTOMATIC TAGS ::= 

--BEGIN

-- **************************************************************
--
-- Extension constants
--
-- **************************************************************

--maxPrivateIEs 									INTEGER ::= 65535
--maxProtocolExtensions 							INTEGER ::= 65535
--maxProtocolIEs									INTEGER ::= 65535

-- **************************************************************
--
-- Common Data Types
--
-- **************************************************************

Criticality		::= ENUMERATED { reject, ignore, notify }

Presence		::= ENUMERATED { optional, conditional, mandatory }

PrivateIE-ID	::= CHOICE {
	local				INTEGER (0.. 65535),
	global				OBJECT IDENTIFIER
}

ProcedureCode		::= INTEGER{
id-commonTransportChannelResourcesInitialisation			( 0),
id-commonTransportChannelResourcesRelease					( 1),
id-compressedModeCommand									( 2),
id-downlinkPowerControl										( 3),
id-downlinkPowerTimeslotControl								( 4),
id-downlinkSignallingTransfer								( 5),
id-errorIndication											( 6),
id-dedicatedMeasurementFailure								( 7),
id-dedicatedMeasurementInitiation							( 8),
id-dedicatedMeasurementReporting							( 9),
id-dedicatedMeasurementTermination							( 10),
id-paging													( 11),
id-physicalChannelReconfiguration							( 12),
id-privateMessage											( 13),
id-radioLinkAddition										( 14),
id-radioLinkCongestion										( 34),
id-radioLinkDeletion										( 15),
id-radioLinkFailure											( 16),
id-radioLinkPreemption										( 17),
id-radioLinkRestoration										( 18),
id-radioLinkSetup											( 19),
id-relocationCommit											( 20),
id-synchronisedRadioLinkReconfigurationCancellation			( 21),
id-synchronisedRadioLinkReconfigurationCommit				( 22),
id-synchronisedRadioLinkReconfigurationPreparation			( 23),
id-unSynchronisedRadioLinkReconfiguration					( 24),
id-uplinkSignallingTransfer									( 25),
id-commonMeasurementFailure									( 26),
id-commonMeasurementInitiation								( 27),
id-commonMeasurementReporting								( 28),
id-commonMeasurementTermination								( 29),
id-informationExchangeFailure								( 30),
id-informationExchangeInitiation							( 31),
id-informationReporting										( 32),
id-informationExchangeTermination							( 33),
id-reset													( 35),
id-radioLinkActivation 										( 36),
id-gERANuplinkSignallingTransfer							( 37),
id-radioLinkParameterUpdate									( 38),
id-uEMeasurementFailure										( 39),
id-uEMeasurementInitiation									( 40),
id-uEMeasurementReporting									( 41),
id-uEMeasurementTermination									( 42),
id-iurDeactivateTrace										( 43),
id-iurInvokeTrace											( 44),
id-mBMSAttach												( 45),
id-mBMSDetach												( 46),
id-directInformationTransfer								( 48)
} (0..255)

ProcedureID ::= SEQUENCE {
	procedureCode		ProcedureCode,
	ddMode				ENUMERATED { tdd, fdd, common, ... }
}

ProtocolIE-ID		::= INTEGER {
id-AllowedQueuingTime														( 4),
id-Allowed-Rate-Information													( 42),
id-AntennaColocationIndicator												( 309),
id-BindingID																( 5),
id-C-ID																		( 6),
id-C-RNTI																	( 7),
id-Cell-Capacity-Class-Value												( 303),
id-CFN																		( 8),
id-CN-CS-DomainIdentifier													( 9),
id-CN-PS-DomainIdentifier													( 10),
id-Cause																	( 11),
id-CoverageIndicator														( 310),
id-CriticalityDiagnostics													( 20),
id-ContextInfoItem-Reset													( 211),
id-ContextGroupInfoItem-Reset												( 515),
id-D-RNTI																	( 21),
id-D-RNTI-ReleaseIndication													( 22),
id-DCHs-to-Add-FDD															( 26),
id-DCHs-to-Add-TDD															( 27),
id-DCH-DeleteList-RL-ReconfPrepFDD											( 30),
id-DCH-DeleteList-RL-ReconfPrepTDD											( 31),
id-DCH-DeleteList-RL-ReconfRqstFDD											( 32),
id-DCH-DeleteList-RL-ReconfRqstTDD											( 33),
id-DCH-FDD-Information														( 34),
id-DCH-TDD-Information														( 35),
id-FDD-DCHs-to-Modify														( 39),
id-TDD-DCHs-to-Modify														( 40),
id-DCH-InformationResponse													( 43),
id-DCH-Rate-InformationItem-RL-CongestInd									( 38),
id-DL-CCTrCH-InformationAddItem-RL-ReconfPrepTDD							( 44),
id-DL-CCTrCH-InformationListIE-RL-ReconfReadyTDD							( 45),
id-DL-CCTrCH-InformationDeleteItem-RL-ReconfRqstTDD							( 46),
id-DL-CCTrCH-InformationItem-RL-SetupRqstTDD								( 47),
id-DL-CCTrCH-InformationListIE-PhyChReconfRqstTDD							( 48),
id-DL-CCTrCH-InformationListIE-RL-AdditionRspTDD							( 49),
id-DL-CCTrCH-InformationListIE-RL-SetupRspTDD								( 50),
id-DL-CCTrCH-InformationAddList-RL-ReconfPrepTDD							( 51),
id-DL-CCTrCH-InformationDeleteList-RL-ReconfRqstTDD							( 52),
id-DL-CCTrCH-InformationList-RL-SetupRqstTDD								( 53),
id-FDD-DL-CodeInformation													( 54),
id-DL-DPCH-Information-RL-ReconfPrepFDD										( 59),
id-DL-DPCH-Information-RL-SetupRqstFDD										( 60),
id-DL-DPCH-Information-RL-ReconfRqstFDD										( 61),
id-DL-DPCH-InformationItem-PhyChReconfRqstTDD								( 62),
id-DL-DPCH-InformationItem-RL-AdditionRspTDD								( 63),
id-DL-DPCH-InformationItem-RL-SetupRspTDD									( 64),
id-DL-DPCH-TimingAdjustment													( 278),
id-DLReferencePower															( 67),
id-DLReferencePowerList-DL-PC-Rqst											( 68),
id-DL-ReferencePowerInformation-DL-PC-Rqst									( 69),
id-DPC-Mode																	( 12),
id-DRXCycleLengthCoefficient												( 70),
id-DedicatedMeasurementObjectType-DM-Fail-Ind								( 470),
id-DedicatedMeasurementObjectType-DM-Fail									( 471),
id-DedicatedMeasurementObjectType-DM-Rprt									( 71),
id-DedicatedMeasurementObjectType-DM-Rqst									( 72),
id-DedicatedMeasurementObjectType-DM-Rsp									( 73),
id-DedicatedMeasurementType													( 74),
id-FACH-InfoForUESelectedS-CCPCH-CTCH-ResourceRspFDD						( 82),
id-FACH-InfoForUESelectedS-CCPCH-CTCH-ResourceRspTDD						( 83),
id-Guaranteed-Rate-Information												( 41),
id-IMSI																		( 84),
id-HCS-Prio																	( 311),
id-L3-Information															( 85),
id-AdjustmentPeriod															( 90),
id-MaxAdjustmentStep														( 91),
id-MeasurementFilterCoefficient												( 92),
id-MessageStructure															( 57),
id-MeasurementID															( 93),
id-Neighbouring-GSM-CellInformation											( 13),
id-Neighbouring-UMTS-CellInformationItem									( 95),
id-NRT-Load-Information-Value												( 305),
id-NRT-Load-Information-Value-IncrDecrThres									( 306),
id-PagingArea-PagingRqst													( 102),
id-FACH-FlowControlInformation												( 103),
id-PartialReportingIndicator												( 472),
id-Permanent-NAS-UE-Identity												( 17),
id-PowerAdjustmentType														( 107),
id-RANAP-RelocationInformation												( 109),
id-RL-Information-PhyChReconfRqstFDD										( 110),
id-RL-Information-PhyChReconfRqstTDD										( 111),
id-RL-Information-RL-AdditionRqstFDD										( 112),
id-RL-Information-RL-AdditionRqstTDD										( 113),
id-RL-Information-RL-DeletionRqst											( 114),
id-RL-Information-RL-FailureInd												( 115),
id-RL-Information-RL-ReconfPrepFDD											( 116),
id-RL-Information-RL-RestoreInd												( 117),
id-RL-Information-RL-SetupRqstFDD											( 118),
id-RL-Information-RL-SetupRqstTDD											( 119),
id-RL-InformationItem-RL-CongestInd											( 55),
id-RL-InformationItem-DM-Rprt												( 120),
id-RL-InformationItem-DM-Rqst												( 121),
id-RL-InformationItem-DM-Rsp												( 122),
id-RL-InformationItem-RL-PreemptRequiredInd									( 2),
id-RL-InformationItem-RL-SetupRqstFDD										( 123),
id-RL-InformationList-RL-CongestInd											( 56),
id-RL-InformationList-RL-AdditionRqstFDD									( 124),
id-RL-InformationList-RL-DeletionRqst										( 125),
id-RL-InformationList-RL-PreemptRequiredInd									( 1),
id-RL-InformationList-RL-ReconfPrepFDD										( 126),
id-RL-InformationResponse-RL-AdditionRspTDD									( 127),
id-RL-InformationResponse-RL-ReconfReadyTDD									( 128),
id-RL-InformationResponse-RL-SetupRspTDD									( 129),
id-RL-InformationResponseItem-RL-AdditionRspFDD								( 130),
id-RL-InformationResponseItem-RL-ReconfReadyFDD								( 131),
id-RL-InformationResponseItem-RL-ReconfRspFDD								( 132),
id-RL-InformationResponseItem-RL-SetupRspFDD								( 133),
id-RL-InformationResponseList-RL-AdditionRspFDD								( 134),
id-RL-InformationResponseList-RL-ReconfReadyFDD								( 135),
id-RL-InformationResponseList-RL-ReconfRspFDD								( 136),
id-RL-InformationResponse-RL-ReconfRspTDD									( 28),
id-RL-InformationResponseList-RL-SetupRspFDD								( 137),
id-RL-ReconfigurationFailure-RL-ReconfFail									( 141),
id-RL-Set-InformationItem-DM-Rprt											( 143),
id-RL-Set-InformationItem-DM-Rqst											( 144),
id-RL-Set-InformationItem-DM-Rsp											( 145),
id-RL-Set-Information-RL-FailureInd											( 146),
id-RL-Set-Information-RL-RestoreInd											( 147),
id-RL-Set-Successful-InformationItem-DM-Fail								( 473),
id-RL-Set-Unsuccessful-InformationItem-DM-Fail								( 474),
id-RL-Set-Unsuccessful-InformationItem-DM-Fail-Ind							( 475),
id-RL-Successful-InformationItem-DM-Fail									( 476),
id-RL-Unsuccessful-InformationItem-DM-Fail									( 477),
id-RL-Unsuccessful-InformationItem-DM-Fail-Ind								( 478),
id-ReportCharacteristics													( 152),
id-Reporting-Object-RL-FailureInd											( 153),
id-Reporing-Object-RL-RestoreInd											( 154),
id-RT-Load-Value															( 307),
id-RT-Load-Value-IncrDecrThres												( 308),
id-S-RNTI																	( 155),
id-ResetIndicator															( 244),
id-RNC-ID																	( 245),
id-SAI																		( 156),
id-SRNC-ID																	( 157),
id-SuccessfulRL-InformationResponse-RL-AdditionFailureFDD					( 159),
id-SuccessfulRL-InformationResponse-RL-SetupFailureFDD						( 160),
id-TransportBearerID														( 163),
id-TransportBearerRequestIndicator											( 164),
id-TransportLayerAddress													( 165),
id-TypeOfError																( 140),
id-UC-ID																	( 166),
id-UL-CCTrCH-AddInformation-RL-ReconfPrepTDD								( 167),
id-UL-CCTrCH-InformationAddList-RL-ReconfPrepTDD							( 169),
id-UL-CCTrCH-InformationItem-RL-SetupRqstTDD								( 171),
id-UL-CCTrCH-InformationList-RL-SetupRqstTDD								( 172),
id-UL-CCTrCH-InformationListIE-PhyChReconfRqstTDD							( 173),
id-UL-CCTrCH-InformationListIE-RL-AdditionRspTDD							( 174),
id-UL-CCTrCH-InformationListIE-RL-ReconfReadyTDD							( 175),
id-UL-CCTrCH-InformationListIE-RL-SetupRspTDD								( 176),
id-UL-DPCH-Information-RL-ReconfPrepFDD										( 177),
id-UL-DPCH-Information-RL-ReconfRqstFDD										( 178),
id-UL-DPCH-Information-RL-SetupRqstFDD										( 179),
id-UL-DPCH-InformationItem-PhyChReconfRqstTDD								( 180),
id-UL-DPCH-InformationItem-RL-AdditionRspTDD								( 181),
id-UL-DPCH-InformationItem-RL-SetupRspTDD									( 182),
id-UL-DPCH-InformationAddListIE-RL-ReconfReadyTDD							( 183),
id-UL-SIRTarget																( 184),
id-URA-Information															( 185),
id-UnsuccessfulRL-InformationResponse-RL-AdditionFailureFDD					( 188),
id-UnsuccessfulRL-InformationResponse-RL-SetupFailureFDD					( 189),
id-UnsuccessfulRL-InformationResponse-RL-SetupFailureTDD					( 190),
id-Active-Pattern-Sequence-Information										( 193),
id-AdjustmentRatio															( 194),
id-CauseLevel-RL-AdditionFailureFDD											( 197),
id-CauseLevel-RL-AdditionFailureTDD											( 198),
id-CauseLevel-RL-ReconfFailure												( 199),
id-CauseLevel-RL-SetupFailureFDD											( 200),
id-CauseLevel-RL-SetupFailureTDD											( 201),
id-DL-CCTrCH-InformationDeleteItem-RL-ReconfPrepTDD							( 205),
id-DL-CCTrCH-InformationModifyItem-RL-ReconfPrepTDD							( 206),
id-DL-CCTrCH-InformationModifyItem-RL-ReconfRqstTDD							( 207),
id-DL-CCTrCH-InformationDeleteList-RL-ReconfPrepTDD							( 208),
id-DL-CCTrCH-InformationModifyList-RL-ReconfPrepTDD							( 209),
id-DL-CCTrCH-InformationModifyList-RL-ReconfRqstTDD							( 210),
id-DL-DPCH-InformationAddListIE-RL-ReconfReadyTDD							( 212),
id-DL-DPCH-InformationDeleteListIE-RL-ReconfReadyTDD						( 213),
id-DL-DPCH-InformationModifyListIE-RL-ReconfReadyTDD						( 214),
id-DSCHs-to-Add-TDD															( 215),
id-Unused-ProtocolIE-ID-216													( 216),
id-DSCH-DeleteList-RL-ReconfPrepTDD											( 217),
id-Unused-ProtocolIE-ID-218													( 218),
id-Unused-ProtocolIE-ID-219													( 219),
id-DSCH-InformationListIE-RL-AdditionRspTDD									( 220),
id-DSCH-InformationListIEs-RL-SetupRspTDD									( 221),
id-DSCH-TDD-Information														( 222),
id-Unused-ProtocolIE-ID-223													( 223),
id-Unused-ProtocolIE-ID-226													( 226),
id-DSCH-ModifyList-RL-ReconfPrepTDD											( 227),
id-Unused-ProtocolIE-ID-228													( 228),
id-Unused-ProtocolIE-ID-324													( 324),
id-Unused-ProtocolIE-ID-229													( 229),
id-DSCHToBeAddedOrModifiedList-RL-ReconfReadyTDD							( 230),
id-Unused-ProtocolIE-ID-29													( 29),
id-Unused-ProtocolIE-ID-225													( 225),
id-GA-Cell																	( 232),
id-GA-CellAdditionalShapes													( 3),
id-Unused-ProtocolIE-ID-246													( 246),
id-Transmission-Gap-Pattern-Sequence-Information							( 255),
id-UL-CCTrCH-DeleteInformation-RL-ReconfPrepTDD								( 256),
id-UL-CCTrCH-ModifyInformation-RL-ReconfPrepTDD								( 257),
id-UL-CCTrCH-InformationModifyItem-RL-ReconfRqstTDD							( 258),
id-UL-CCTrCH-InformationDeleteList-RL-ReconfPrepTDD							( 259),
id-UL-CCTrCH-InformationModifyList-RL-ReconfPrepTDD							( 260),
id-UL-CCTrCH-InformationModifyList-RL-ReconfRqstTDD							( 261),
id-UL-CCTrCH-InformationDeleteItem-RL-ReconfRqstTDD							( 262),
id-UL-CCTrCH-InformationDeleteList-RL-ReconfRqstTDD							( 263),
id-UL-DPCH-InformationDeleteListIE-RL-ReconfReadyTDD						( 264),
id-UL-DPCH-InformationModifyListIE-RL-ReconfReadyTDD						( 265),
id-UnsuccessfulRL-InformationResponse-RL-AdditionFailureTDD					( 266),
id-USCHs-to-Add																( 267),
id-USCH-DeleteList-RL-ReconfPrepTDD											( 268),
id-USCH-InformationListIE-RL-AdditionRspTDD									( 269),
id-USCH-InformationListIEs-RL-SetupRspTDD									( 270),
id-USCH-Information															( 271),
id-USCH-ModifyList-RL-ReconfPrepTDD											( 272),
id-USCHToBeAddedOrModifiedList-RL-ReconfReadyTDD							( 273),
id-DL-Physical-Channel-Information-RL-SetupRqstTDD							( 274),
id-UL-Physical-Channel-Information-RL-SetupRqstTDD							( 275),
id-ClosedLoopMode1-SupportIndicator											( 276),
id-Unused-ProtocolIE-ID-277													( 277),
id-STTD-SupportIndicator													( 279),
id-CFNReportingIndicator             										( 14),
id-CNOriginatedPage-PagingRqst												( 23),
id-InnerLoopDLPCStatus														( 24),
id-PropagationDelay															( 25),
id-RxTimingDeviationForTA													( 36),
id-timeSlot-ISCP															( 37),
id-CCTrCH-InformationItem-RL-FailureInd										( 15),
id-CCTrCH-InformationItem-RL-RestoreInd										( 16),
id-CommonMeasurementAccuracy												( 280),
id-CommonMeasurementObjectType-CM-Rprt										( 281),
id-CommonMeasurementObjectType-CM-Rqst										( 282),
id-CommonMeasurementObjectType-CM-Rsp										( 283),
id-CommonMeasurementType													( 284),
id-CongestionCause 															( 18),
id-SFN																		( 285),
id-SFNReportingIndicator													( 286),
id-InformationExchangeID													( 287),
id-InformationExchangeObjectType-InfEx-Rprt									( 288),
id-InformationExchangeObjectType-InfEx-Rqst									( 289),
id-InformationExchangeObjectType-InfEx-Rsp									( 290),
id-InformationReportCharacteristics											( 291),
id-InformationType															( 292),
id-neighbouring-LCR-TDD-CellInformation										( 58),
id-DL-Timeslot-ISCP-LCR-Information-RL-SetupRqstTDD							( 65),
id-RL-LCR-InformationResponse-RL-SetupRspTDD								( 66),
id-UL-CCTrCH-LCR-InformationListIE-RL-SetupRspTDD							( 75),
id-UL-DPCH-LCR-InformationItem-RL-SetupRspTDD								( 76),
id-DL-CCTrCH-LCR-InformationListIE-RL-SetupRspTDD							( 77),
id-DL-DPCH-LCR-InformationItem-RL-SetupRspTDD								( 78),
id-DSCH-LCR-InformationListIEs-RL-SetupRspTDD								( 79),
id-USCH-LCR-InformationListIEs-RL-SetupRspTDD								( 80),
id-DL-Timeslot-ISCP-LCR-Information-RL-AdditionRqstTDD						( 81),
id-RL-LCR-InformationResponse-RL-AdditionRspTDD								( 86),
id-UL-CCTrCH-LCR-InformationListIE-RL-AdditionRspTDD						( 87),
id-UL-DPCH-LCR-InformationItem-RL-AdditionRspTDD							( 88),
id-DL-CCTrCH-LCR-InformationListIE-RL-AdditionRspTDD						( 89),
id-DL-DPCH-LCR-InformationItem-RL-AdditionRspTDD							( 94),
id-DSCH-LCR-InformationListIEs-RL-AdditionRspTDD							( 96),
id-USCH-LCR-InformationListIEs-RL-AdditionRspTDD							( 97),
id-UL-DPCH-LCR-InformationAddListIE-RL-ReconfReadyTDD						( 98),
id-UL-Timeslot-LCR-InformationModifyList-RL-ReconfReadyTDD					( 100),
id-DL-DPCH-LCR-InformationAddListIE-RL-ReconfReadyTDD						( 101),
id-DL-Timeslot-LCR-InformationModifyList-RL-ReconfReadyTDD					( 104),
id-UL-Timeslot-LCR-InformationList-PhyChReconfRqstTDD						( 105),
id-DL-Timeslot-LCR-InformationList-PhyChReconfRqstTDD						( 106),
id-timeSlot-ISCP-LCR-List-DL-PC-Rqst-TDD									( 138),
id-TSTD-Support-Indicator-RL-SetupRqstTDD									( 139),
id-RestrictionStateIndicator												( 142),
id-Load-Value																( 233),
id-Load-Value-IncrDecrThres													( 234),
id-OnModification															( 235),
id-Received-Total-Wideband-Power-Value										( 236),
id-Received-Total-Wideband-Power-Value-IncrDecrThres						( 237),
id-SFNSFNMeasurementThresholdInformation									( 238),
id-Transmitted-Carrier-Power-Value											( 239),
id-Transmitted-Carrier-Power-Value-IncrDecrThres							( 240),
id-TUTRANGPSMeasurementThresholdInformation									( 241),
id-UL-Timeslot-ISCP-Value													( 242),
id-UL-Timeslot-ISCP-Value-IncrDecrThres										( 243),
id-Rx-Timing-Deviation-Value-LCR											( 293),
id-DPC-Mode-Change-SupportIndicator											( 19),
id-Unused-ProtocolIE-ID-247													( 247),
id-Unused-ProtocolIE-ID-295													( 295),
id-PrimaryCCPCH-RSCP-RL-ReconfPrepTDD										( 202),
id-DL-TimeSlot-ISCP-Info-RL-ReconfPrepTDD									( 203),
id-DL-Timeslot-ISCP-LCR-Information-RL-ReconfPrepTDD						( 204),
id-DSCH-RNTI																( 249),
id-DL-PowerBalancing-Information											( 296),
id-DL-PowerBalancing-ActivationIndicator									( 297),
id-DL-PowerBalancing-UpdatedIndicator										( 298),
id-DL-ReferencePowerInformation												( 299),
id-Enhanced-PrimaryCPICH-EcNo												( 224),
id-IPDL-TDD-ParametersLCR													( 252),
id-CellCapabilityContainer-FDD												( 300),
id-CellCapabilityContainer-TDD												( 301),
id-CellCapabilityContainer-TDD-LCR											( 302),
id-RL-Specific-DCH-Info														( 317),
id-RL-ReconfigurationRequestFDD-RL-InformationList 							( 318),
id-RL-ReconfigurationRequestFDD-RL-Information-IEs							( 319),
id-RL-ReconfigurationRequestTDD-RL-Information								( 321),
id-CommonTransportChannelResourcesInitialisationNotRequired					( 250),
id-DelayedActivation 														( 312),
id-DelayedActivationList-RL-ActivationCmdFDD								( 313),
id-DelayedActivationInformation-RL-ActivationCmdFDD							( 314),
id-DelayedActivationList-RL-ActivationCmdTDD								( 315),
id-DelayedActivationInformation-RL-ActivationCmdTDD							( 316),
id-neighbouringTDDCellMeasurementInformationLCR								( 251),
id-UL-SIR-Target-CCTrCH-InformationItem-RL-SetupRspTDD						( 150),
id-UL-SIR-Target-CCTrCH-LCR-InformationItem-RL-SetupRspTDD					( 151),
id-PrimCCPCH-RSCP-DL-PC-RqstTDD												( 451),
id-HSDSCH-FDD-Information													( 452),
id-HSDSCH-FDD-Information-Response											( 453),
id-HSDSCH-FDD-Update-Information											( 466),
id-HSDSCH-Information-to-Modify												( 456),
id-HSDSCHMacdFlowSpecificInformationList-RL-PreemptRequiredInd				( 516),
id-HSDSCHMacdFlowSpecificInformationItem-RL-PreemptRequiredInd				( 517),
id-HSDSCH-RNTI																( 457),
id-HSDSCH-TDD-Information													( 458),
id-HSDSCH-TDD-Information-Response											( 459),
id-HSDSCH-TDD-Update-Information											( 467),
id-HSPDSCH-RL-ID															( 463),
id-HSDSCH-MACdFlows-to-Add 													( 531),
id-HSDSCH-MACdFlows-to-Delete												( 532),
id-Angle-Of-Arrival-Value-LCR												( 148),
id-TrafficClass																( 158),
id-Unused-ProtocolIE-ID-248													( 248),
id-Unused-ProtocolIE-ID-253													( 253),
id-PDSCH-RL-ID																( 323),
id-TimeSlot-RL-SetupRspTDD													( 325),
id-GERAN-Cell-Capability													( 468),
id-GERAN-Classmark															( 469),
id-DSCH-InitialWindowSize													( 480),
id-UL-Synchronisation-Parameters-LCR										( 464),
id-SNA-Information															( 479),
id-MAChs-ResetIndicator														( 465),
id-TDD-DL-DPCH-TimeSlotFormatModifyItem-LCR-RL-ReconfReadyTDD				( 481),
id-TDD-UL-DPCH-TimeSlotFormatModifyItem-LCR-RL-ReconfReadyTDD				( 482),
id-TDD-TPC-UplinkStepSize-LCR-RL-SetupRqstTDD								( 483),
id-UL-CCTrCH-InformationList-RL-AdditionRqstTDD								( 484),
id-UL-CCTrCH-InformationItem-RL-AdditionRqstTDD								( 485),
id-DL-CCTrCH-InformationList-RL-AdditionRqstTDD								( 486),
id-DL-CCTrCH-InformationItem-RL-AdditionRqstTDD								( 487),
id-TDD-TPC-UplinkStepSize-InformationAdd-LCR-RL-ReconfPrepTDD				( 488),
id-TDD-TPC-UplinkStepSize-InformationModify-LCR-RL-ReconfPrepTDD			( 489),
id-TDD-TPC-DownlinkStepSize-InformationAdd-RL-ReconfPrepTDD					( 490),
id-TDD-TPC-DownlinkStepSize-InformationModify-RL-ReconfPrepTDD				( 491),
id-UL-TimingAdvanceCtrl-LCR													( 492),
id-HSPDSCH-Timeslot-InformationList-PhyChReconfRqstTDD						( 493),
id-HSPDSCH-Timeslot-InformationListLCR-PhyChReconfRqstTDD					( 494),
id-HS-SICH-Reception-Quality 												( 495),
id-HS-SICH-Reception-Quality-Measurement-Value 								( 496),
id-HSSICH-Info-DM-Rprt														( 497),
id-HSSICH-Info-DM-Rqst														( 498),
id-HSSICH-Info-DM															( 499),
id-CCTrCH-Maximum-DL-Power-RL-SetupRspTDD									( 500),
id-CCTrCH-Minimum-DL-Power-RL-SetupRspTDD									( 501),
id-CCTrCH-Maximum-DL-Power-RL-AdditionRspTDD								( 502),
id-CCTrCH-Minimum-DL-Power-RL-AdditionRspTDD								( 503),
id-CCTrCH-Maximum-DL-Power-RL-ReconfReadyTDD								( 504),
id-CCTrCH-Minimum-DL-Power-RL-ReconfReadyTDD								( 505),
id-Maximum-DL-Power-TimeslotLCR-InformationModifyItem-RL-ReconfReadyTDD		( 506),
id-Minimum-DL-Power-TimeslotLCR-InformationModifyItem-RL-ReconfReadyTDD		( 507),
id-DL-CCTrCH-InformationList-RL-ReconfRspTDD								( 508),
id-DL-DPCH-InformationModifyItem-LCR-RL-ReconfRspTDD						( 509),
id-Maximum-DL-Power-TimeslotLCR-InformationItem								( 510),
id-Minimum-DL-Power-TimeslotLCR-InformationItem								( 511),
id-TDD-Support-8PSK															( 512),
id-TDD-maxNrDLPhysicalchannels												( 513),
id-ExtendedGSMCellIndividualOffset											( 514),
id-RL-ParameterUpdateIndicationFDD-RL-InformationList 						( 518),
id-Primary-CPICH-Usage-For-Channel-Estimation								( 519),
id-Secondary-CPICH-Information												( 520),
id-Secondary-CPICH-Information-Change										( 521),
id-Unused-ProtocolIE-ID-522													( 522),
id-Unused-ProtocolIE-ID-523													( 523),
id-RL-ParameterUpdateIndicationFDD-RL-Information-Item						( 524),
id-Phase-Reference-Update-Indicator											( 525),
id-Unidirectional-DCH-Indicator												( 526),
id-RL-Information-RL-ReconfPrepTDD											( 527),
id-Multiple-RL-InformationResponse-RL-ReconfReadyTDD						( 528),
id-RL-ReconfigurationResponseTDD-RL-Information								( 529),
id-Satellite-Almanac-Information-ExtItem									( 530),
id-HSDSCH-Information-to-Modify-Unsynchronised								( 533),
id-TnlQos																	( 534),
id-RTLoadValue																( 535),
id-NRTLoadInformationValue													( 536),
id-CellPortionID															( 537),
id-UpPTSInterferenceValue													( 538),
id-PrimaryCCPCH-RSCP-Delta													( 539),
id-UEMeasurementType														( 540),
id-UEMeasurementTimeslotInfoHCR												( 541),
id-UEMeasurementTimeslotInfoLCR												( 542),
id-UEMeasurementReportCharacteristics										( 543),
id-UEMeasurementParameterModAllow											( 544),
id-UEMeasurementValueInformation											( 545),
id-InterfacesToTraceItem													( 546),
id-ListOfInterfacesToTrace													( 547),
id-TraceDepth																( 548),
id-TraceRecordingSessionReference											( 549),
id-TraceReference															( 550),
id-UEIdentity																( 551),
id-NACC-Related-Data														( 552),
id-GSM-Cell-InfEx-Rqst														( 553),
id-MeasurementRecoveryBehavior												( 554),
id-MeasurementRecoveryReportingIndicator									( 555),
id-MeasurementRecoverySupportIndicator										( 556),
id-DL-DPCH-Power-Information-RL-ReconfPrepFDD								( 557),
id-F-DPCH-Information-RL-ReconfPrepFDD										( 558),
id-F-DPCH-Information-RL-SetupRqstFDD										( 559),
id-MBMS-Bearer-Service-List													( 560),
id-MBMS-Bearer-Service-List-InfEx-Rsp										( 561),
id-Active-MBMS-Bearer-ServiceFDD											( 562),
id-Active-MBMS-Bearer-ServiceTDD											( 563),
id-Old-URA-ID																( 564),
id-UE-State																	( 568),
id-URA-ID																	( 569),
id-HARQ-Preamble-Mode														( 571),
id-SynchronisationIndicator													( 572),
id-UL-DPDCHIndicatorEDCH													( 573),
id-EDPCH-Information														( 574),
id-RL-Specific-EDCH-Information												( 575),
id-EDCH-RL-Indication														( 576),
id-EDCH-FDD-Information														( 577),
id-EDCH-RLSet-Id															( 578),
id-Serving-EDCHRL-Id														( 579),
id-EDCH-FDD-DL-ControlChannelInformation									( 580),
id-EDCH-FDD-InformationResponse												( 581),
id-EDCH-MACdFlows-To-Add													( 582),
id-EDCH-FDD-Information-To-Modify											( 583),
id-EDCH-MACdFlows-To-Delete													( 584),
id-EDPCH-Information-RLReconfRequest-FDD									( 585),
id-EDCH-MacdFlowSpecificInformationList-RL-PreemptRequiredInd				( 586),
id-EDCH-MacdFlowSpecificInformationItem-RL-PreemptRequiredInd				( 587),
id-EDCH-MacdFlowSpecificInformationList-RL-CongestInd  						( 588),
id-EDCH-MacdFlowSpecificInformationItem-RL-CongestInd						( 589),
id-MBMS-Bearer-Service-Full-Address											( 590),
id-Initial-DL-DPCH-TimingAdjustment											( 591),
id-Initial-DL-DPCH-TimingAdjustment-Allowed									( 592),
id-User-Plane-Congestion-Fields-Inclusion									( 593),
id-HARQ-Preamble-Mode-Activation-Indicator									( 594),
id-multiple-DedicatedMeasurementValueList-TDD-DM-Rsp						( 595),
id-multiple-DedicatedMeasurementValueList-LCR-TDD-DM-Rsp					( 596),
id-ProvidedInformation														( 597),
id-Active-MBMS-Bearer-ServiceFDD-PFL										( 598),
id-Active-MBMS-Bearer-ServiceTDD-PFL										( 599),
id-FrequencyBandIndicator													( 600)
}(0..65535)

TransactionID		::= CHOICE {
	shortTransActionId	INTEGER (0..127),
	longTransActionId	INTEGER (0..32767)
}

TriggeringMessage	::= ENUMERATED { initiating-message, successful-outcome, unsuccessful-outcome, outcome }

--END

--9.3.7	Container Definitions
-- **************************************************************
--
-- Container definitions
--
-- **************************************************************

--RNSAP-Containers {
--itu-t (0) identified-organization (4) etsi (0) mobileDomain (0) 
--umts-Access (20) modules (3) rnsap (1) version1 (1) rnsap-Containers (5)  }

--DEFINITIONS AUTOMATIC TAGS ::= 

--BEGIN

-- **************************************************************
--
-- IE parameter types from other modules.
--
-- **************************************************************

--IMPORTS
--	maxPrivateIEs,
--	maxProtocolExtensions,
--	maxProtocolIEs,
--	Criticality,
--	Presence,
--	PrivateIE-ID,
--	ProtocolIE-ID	
--FROM RNSAP-CommonDataTypes;

-- **************************************************************
--
-- Class Definition for Protocol IEs
--
-- **************************************************************

--RNSAP-PROTOCOL-IES ::= CLASS {
--	&id				ProtocolIE-ID 					UNIQUE,
--	&criticality			Criticality,
--	&Value,
--	&presence			Presence
--}
--WITH SYNTAX {
--	ID				&id
--	CRITICALITY			&criticality
--	TYPE				&Value
--	PRESENCE			&presence
--}

-- **************************************************************
--
-- Class Definition for Protocol IEs
--
-- **************************************************************

--RNSAP-PROTOCOL-IES-PAIR ::= CLASS {
--	&id				ProtocolIE-ID 					UNIQUE,
--	&firstCriticality		Criticality,
--	&FirstValue,
--	&secondCriticality		Criticality,
--	&SecondValue,
--	&presence			Presence
--}
--WITH SYNTAX {
--	ID				&id
--	FIRST CRITICALITY 		&firstCriticality
--	FIRST TYPE			&FirstValue
--	SECOND CRITICALITY 		&secondCriticality
--	SECOND TYPE			&SecondValue
--	PRESENCE			&presence
--}

-- **************************************************************
--
-- Class Definition for Protocol Extensions
--
-- **************************************************************

--RNSAP-PROTOCOL-EXTENSION ::= CLASS {
--	&id				ProtocolIE-ID 				UNIQUE,
--	&criticality			Criticality,
--	&Extension,
--	&presence		Presence
--}
--WITH SYNTAX {
--	ID				&id
--	CRITICALITY			&criticality
--	EXTENSION			&Extension
--	PRESENCE			&presence
--}

-- **************************************************************
--
-- Class Definition for Private IEs
--
-- **************************************************************

--RNSAP-PRIVATE-IES ::= CLASS {
--	&id				PrivateIE-ID,
--	&criticality			Criticality,
--	&Value,
--	&presence		Presence
--}
--WITH SYNTAX {
--	ID				&id
--	CRITICALITY			&criticality
--	TYPE			&Value
--	PRESENCE			&presence
--}

-- **************************************************************
--
-- Container for Protocol IEs
--
-- **************************************************************

--ProtocolIE-Container {RNSAP-PROTOCOL-IES : IEsSetParam} ::= 
--	SEQUENCE (SIZE (0..maxProtocolIEs)) OF
--	ProtocolIE-Field {{IEsSetParam}}

ProtocolIE-Container ::= 
	SEQUENCE (SIZE (0..65535)) OF
	ProtocolIE-Field

--ProtocolIE-Single-Container {RNSAP-PROTOCOL-IES : IEsSetParam} ::= 
--	ProtocolIE-Field {{IEsSetParam}}

ProtocolIE-Single-Container ::=
	ProtocolIE-Field 

--ProtocolIE-Field {RNSAP-PROTOCOL-IES : IEsSetParam} ::= SEQUENCE {
--	id				RNSAP-PROTOCOL-IES.&id				({IEsSetParam}),
--	criticality			RNSAP-PROTOCOL-IES.&criticality			({IEsSetParam}{@id}),
--	value				RNSAP-PROTOCOL-IES.&Value	        	({IEsSetParam}{@id})
--}
ProtocolIE-Field ::= SEQUENCE {
	id				ProtocolIE-ID,
	criticality		Criticality,
	value			ProtocolIEValue
}

ProtocolIEValue ::= ANY

-- **************************************************************
--
-- Container for Protocol IE Pairs
--
-- **************************************************************

--ProtocolIE-ContainerPair {RNSAP-PROTOCOL-IES-PAIR : IEsSetParam} ::= 
--	SEQUENCE (SIZE (0..maxProtocolIEs)) OF
--	ProtocolIE-FieldPair {{IEsSetParam}}

ProtocolIE-ContainerPair ::= 
	SEQUENCE (SIZE (0..65535)) OF
	ProtocolIE-FieldPair

--ProtocolIE-FieldPair {RNSAP-PROTOCOL-IES-PAIR : IEsSetParam} ::= SEQUENCE {
--	id				RNSAP-PROTOCOL-IES-PAIR.&id			({IEsSetParam}),
--	firstCriticality		RNSAP-PROTOCOL-IES-PAIR.&firstCriticality	({IEsSetParam}{@id}),
--	firstValue			RNSAP-PROTOCOL-IES-PAIR.&FirstValue	        ({IEsSetParam}{@id}),
--	secondCriticality		RNSAP-PROTOCOL-IES-PAIR.&secondCriticality	({IEsSetParam}{@id}),
--	secondValue			RNSAP-PROTOCOL-IES-PAIR.&SecondValue	        ({IEsSetParam}{@id})
--}

ProtocolIE-FieldPair ::= SEQUENCE {
	id					ProtocolIE-ID,
	firstCriticality	Criticality,
	firstValue			FirstValue,
	secondCriticality	Criticality,
	secondValue			SecondValue
}

FirstValue ::= ANY
SecondValue ::= ANY
-- **************************************************************
--
-- Container Lists for Protocol IE Containers
--
-- **************************************************************

--ProtocolIE-ContainerList {INTEGER : lowerBound, INTEGER : upperBound, RNSAP-PROTOCOL-IES : IEsSetParam} ::=
--	SEQUENCE (SIZE (lowerBound..upperBound)) OF
--	ProtocolIE-Container {{IEsSetParam}}

ProtocolIE-ContainerList ::=
	SEQUENCE (SIZE (0..65535)) OF
	ProtocolIE-Container

--ProtocolIE-ContainerPairList {INTEGER : lowerBound, INTEGER : upperBound, RNSAP-PROTOCOL-IES-PAIR : IEsSetParam} ::=
--	SEQUENCE (SIZE (lowerBound..upperBound)) OF
--	ProtocolIE-ContainerPair {{IEsSetParam}}

ProtocolIE-ContainerPairList ::=
	SEQUENCE (SIZE (0..65535)) OF
	ProtocolIE-ContainerPair
-- **************************************************************
--
-- Container for Protocol Extensions
--
-- **************************************************************

--ProtocolExtensionContainer {RNSAP-PROTOCOL-EXTENSION : ExtensionSetParam} ::= 
--	SEQUENCE (SIZE (1..maxProtocolExtensions)) OF
--	ProtocolExtensionField {{ExtensionSetParam}}

ProtocolExtensionContainer ::= 
	SEQUENCE (SIZE (1..65535)) OF
	ProtocolExtensionField

--ProtocolExtensionField {RNSAP-PROTOCOL-EXTENSION : ExtensionSetParam} ::= SEQUENCE {
--	id				RNSAP-PROTOCOL-EXTENSION.&id			({ExtensionSetParam}),
--	criticality			RNSAP-PROTOCOL-EXTENSION.&criticality		({ExtensionSetParam}{@id}),
--	extensionValue			RNSAP-PROTOCOL-EXTENSION.&Extension		({ExtensionSetParam}{@id})
--}
ProtocolExtensionField ::= SEQUENCE {
	id				ProtocolIE-ID,
	criticality		Criticality,
	extensionValue	Extension
}

Extension ::= ANY
-- **************************************************************
--
-- Container for Private IEs
--
-- **************************************************************

--PrivateIE-Container {RNSAP-PRIVATE-IES : IEsSetParam} ::= 
--	SEQUENCE (SIZE (1..maxPrivateIEs)) OF
--	PrivateIE-Field {{IEsSetParam}}

PrivateIE-Container ::= 
	SEQUENCE (SIZE (1..65535)) OF
	PrivateIE-Field

--PrivateIE-Field {RNSAP-PRIVATE-IES : IEsSetParam} ::= SEQUENCE {
--	id				RNSAP-PRIVATE-IES.&id			({IEsSetParam}),
--	criticality			RNSAP-PRIVATE-IES.&criticality		({IEsSetParam}{@id}),
--	value			RNSAP-PRIVATE-IES.&Value		({IEsSetParam}{@id})
--}

PrivateIE-Field ::= SEQUENCE {
	privateIEid			PrivateIE-ID,
	criticality			Criticality,
	privateIEvalue		PrivateIEvalue
}

PrivateIEvalue ::= ANY

END

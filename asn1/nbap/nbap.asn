-- $Id:$
-- **************************************************************
--
-- Elementary Procedure definitions
--
-- **************************************************************

NBAP-PDU-Discriptions {
itu-t (0) identified-organization (4) etsi (0) mobileDomain (0) 
umts-Access (20) modules (3) nbap (2) version1 (1) nbap-PDU-Descriptions (0) }

DEFINITIONS AUTOMATIC TAGS ::= 

BEGIN

-- **************************************************************
--
-- IE parameter types from other modules.
--
-- **************************************************************

--IMPORTS
--	Criticality,
--	ProcedureID,
--	MessageDiscriminator,
--	TransactionID
--FROM NBAP-CommonDataTypes

--	CommonTransportChannelSetupRequestFDD,
--	CommonTransportChannelSetupRequestTDD,
--	CommonTransportChannelSetupResponse,
--	CommonTransportChannelSetupFailure,
--	CommonTransportChannelReconfigurationRequestFDD,
--	CommonTransportChannelReconfigurationRequestTDD,
--	CommonTransportChannelReconfigurationResponse,
--	CommonTransportChannelReconfigurationFailure,
--	CommonTransportChannelDeletionRequest,
--	CommonTransportChannelDeletionResponse,
--	BlockResourceRequest,
--	BlockResourceResponse,
--	BlockResourceFailure,
--	UnblockResourceIndication,
--	AuditFailure,
--	AuditRequiredIndication,
--	AuditRequest,
--	AuditResponse,
--	CommonMeasurementInitiationRequest,
--	CommonMeasurementInitiationResponse,
--	CommonMeasurementInitiationFailure,
--	CommonMeasurementReport,
--	CommonMeasurementTerminationRequest,
--	CommonMeasurementFailureIndication,
--	CellSetupRequestFDD,
--	CellSetupRequestTDD,
--	CellSetupResponse,
--	CellSetupFailure,
--	CellReconfigurationRequestFDD,
--	CellReconfigurationRequestTDD,
--	CellReconfigurationResponse,
--	CellReconfigurationFailure,
--	CellDeletionRequest,
--	CellDeletionResponse,
--	InformationExchangeInitiationRequest,
--	InformationExchangeInitiationResponse,
--	InformationExchangeInitiationFailure,
--	InformationReport,
--	InformationExchangeTerminationRequest,
--	InformationExchangeFailureIndication,
--	BearerRearrangementIndication,
--	ResourceStatusIndication,
--	SystemInformationUpdateRequest,
--	SystemInformationUpdateResponse,
--	SystemInformationUpdateFailure,
--	ResetRequest,
--	ResetResponse,
--	RadioLinkActivationCommandFDD,
--	RadioLinkActivationCommandTDD,
--	RadioLinkPreemptionRequiredIndication,
--	RadioLinkSetupRequestFDD,
--	RadioLinkSetupRequestTDD,
--	RadioLinkSetupResponseFDD,
--	RadioLinkSetupResponseTDD,
--	RadioLinkSetupFailureFDD,
--	RadioLinkSetupFailureTDD,
--	RadioLinkAdditionRequestFDD,
--	RadioLinkAdditionRequestTDD,
--	RadioLinkAdditionResponseFDD,
--	RadioLinkAdditionResponseTDD,
--	RadioLinkAdditionFailureFDD,
--	RadioLinkAdditionFailureTDD,
--	RadioLinkParameterUpdateIndicationFDD,
--	RadioLinkParameterUpdateIndicationTDD,
--	RadioLinkReconfigurationPrepareFDD,
--	RadioLinkReconfigurationPrepareTDD,
--	RadioLinkReconfigurationReady,
--	RadioLinkReconfigurationFailure,
--	RadioLinkReconfigurationCommit,
--	RadioLinkReconfigurationCancel,
--	RadioLinkReconfigurationRequestFDD,
--	RadioLinkReconfigurationRequestTDD,
--	RadioLinkReconfigurationResponse,
--	RadioLinkDeletionRequest,
--	RadioLinkDeletionResponse,
--	DL-PowerControlRequest,
--	DL-PowerTimeslotControlRequest,
--	DedicatedMeasurementInitiationRequest,
--	DedicatedMeasurementInitiationResponse,
--	DedicatedMeasurementInitiationFailure,
--	DedicatedMeasurementReport,
--	DedicatedMeasurementTerminationRequest,
--	DedicatedMeasurementFailureIndication,
--	RadioLinkFailureIndication,
--	RadioLinkRestoreIndication,
--	CompressedModeCommand,
--	ErrorIndication,
--	PrivateMessage,
--	PhysicalSharedChannelReconfigurationRequestTDD,
--	PhysicalSharedChannelReconfigurationRequestFDD,
--	PhysicalSharedChannelReconfigurationResponse,
--	PhysicalSharedChannelReconfigurationFailure,
--	CellSynchronisationInitiationRequestTDD,
--	CellSynchronisationInitiationResponseTDD,
--	CellSynchronisationInitiationFailureTDD,
--	CellSynchronisationReconfigurationRequestTDD,
--	CellSynchronisationReconfigurationResponseTDD,
--	CellSynchronisationReconfigurationFailureTDD,
--	CellSynchronisationAdjustmentRequestTDD,
--	CellSynchronisationAdjustmentResponseTDD,
--	CellSynchronisationAdjustmentFailureTDD,
--	CellSynchronisationReportTDD,
--	CellSynchronisationTerminationRequestTDD,
--	CellSynchronisationFailureIndicationTDD,
--	MBMSNotificationUpdateCommand
--FROM NBAP-PDU-Contents

--	id-audit,
--	id-auditRequired,
--	id-blockResource,
--	id-cellDeletion,
--	id-cellReconfiguration,
--	id-cellSetup,
--	id-cellSynchronisationInitiation,
--	id-cellSynchronisationReconfiguration,
--	id-cellSynchronisationReporting,
--	id-cellSynchronisationTermination,
--	id-cellSynchronisationFailure,
--	id-commonMeasurementFailure,
--	id-commonMeasurementInitiation,
--	id-commonMeasurementReport,
--	id-commonMeasurementTermination,
--	id-commonTransportChannelDelete,
--	id-commonTransportChannelReconfigure,
--	id-commonTransportChannelSetup,
--	id-compressedModeCommand,
--	id-dedicatedMeasurementFailure,
--	id-dedicatedMeasurementInitiation,
--	id-dedicatedMeasurementReport,
--	id-dedicatedMeasurementTermination,
--	id-downlinkPowerControl,
--	id-downlinkPowerTimeslotControl,
--	id-errorIndicationForDedicated,
--	id-errorIndicationForCommon,
--	id-informationExchangeFailure,
--	id-informationExchangeInitiation,
--	id-informationReporting,
--	id-informationExchangeTermination,
--	id-BearerRearrangement,
--	id-mBMSNotificationUpdate,
--	id-physicalSharedChannelReconfiguration,
--	id-privateMessageForDedicated,
--	id-privateMessageForCommon,
--	id-radioLinkActivation,
--	id-radioLinkAddition,
--	id-radioLinkDeletion,
--	id-radioLinkFailure,
--	id-radioLinkParameterUpdate,
--	id-radioLinkPreemption,
--	id-radioLinkRestoration,
--	id-radioLinkSetup,
--	id-reset,
--	id-resourceStatusIndication,
--	id-cellSynchronisationAdjustment,
--	id-synchronisedRadioLinkReconfigurationCancellation,
--	id-synchronisedRadioLinkReconfigurationCommit,
--	id-synchronisedRadioLinkReconfigurationPreparation,
--	id-systemInformationUpdate,
--	id-unblockResource,
--	id-unSynchronisedRadioLinkReconfiguration
--FROM NBAP-Constants;

-- **************************************************************
--
-- Interface Elementary Procedure Class
--
-- **************************************************************

--NBAP-ELEMENTARY-PROCEDURE ::= CLASS {
--	&InitiatingMessage					,
--	&SuccessfulOutcome					OPTIONAL,
--	&UnsuccessfulOutcome				OPTIONAL,
--	&Outcome							OPTIONAL,
--	&messageDiscriminator				MessageDiscriminator,
--	&procedureID						ProcedureID 	UNIQUE,
--	&criticality						Criticality 	DEFAULT ignore
--}

--WITH SYNTAX {
--	INITIATING MESSAGE					&InitiatingMessage
--	[SUCCESSFUL OUTCOME					&SuccessfulOutcome]
--	[UNSUCCESSFUL OUTCOME				&UnsuccessfulOutcome]
--	[OUTCOME							&Outcome]
--	MESSAGE DISCRIMINATOR				&messageDiscriminator
--	PROCEDURE ID						&procedureID
--	[CRITICALITY						&criticality]
--}

-- **************************************************************
--
-- Interface PDU Definition
--
-- **************************************************************

NBAP-PDU ::= CHOICE {
	initiatingMessage		InitiatingMessage,
	succesfulOutcome		SuccessfulOutcome,
	unsuccesfulOutcome		UnsuccessfulOutcome,
	outcome					Outcome,
	...
}

--InitiatingMessage ::= SEQUENCE {
--	procedureID				NBAP-ELEMENTARY-PROCEDURE.&procedureID	({NBAP-ELEMENTARY-PROCEDURES}),
--	criticality				NBAP-ELEMENTARY-PROCEDURE.&criticality	({NBAP-ELEMENTARY-PROCEDURES}{@procedureID}),
--	messageDiscriminator	NBAP-ELEMENTARY-PROCEDURE.&messageDiscriminator({NBAP-ELEMENTARY-PROCEDURES}{@procedureID}),
--	transactionID 			TransactionID,
--	value					NBAP-ELEMENTARY-PROCEDURE.&InitiatingMessage({NBAP-ELEMENTARY-PROCEDURES}{@procedureID})
--}

InitiatingMessage ::= SEQUENCE {
	procedureID				ProcedureID,
	criticality				Criticality,
	messageDiscriminator	MessageDiscriminator,
	transactionID 			TransactionID,
	initiatingMessageValue	InitiatingMessageValue
}
InitiatingMessageValue ::= ANY

--SuccessfulOutcome ::= SEQUENCE {
--	procedureID				NBAP-ELEMENTARY-PROCEDURE.&procedureID	({NBAP-ELEMENTARY-PROCEDURES}),
--	criticality				NBAP-ELEMENTARY-PROCEDURE.&criticality	({NBAP-ELEMENTARY-PROCEDURES}{@procedureID}),
--	messageDiscriminator	NBAP-ELEMENTARY-PROCEDURE.&messageDiscriminator({NBAP-ELEMENTARY-PROCEDURES}{@procedureID}),
--	transactionID 			TransactionID,
--	value					NBAP-ELEMENTARY-PROCEDURE.&SuccessfulOutcome({NBAP-ELEMENTARY-PROCEDURES}{@procedureID})
--}

SuccessfulOutcome ::= SEQUENCE {
	procedureID				ProcedureID,
	criticality				Criticality,
	messageDiscriminator	MessageDiscriminator,
 	transactionID 			TransactionID,
	successfulOutcomeValue	SuccessfulOutcomeValue
}

SuccessfulOutcomeValue ::= ANY

--UnsuccessfulOutcome ::= SEQUENCE {
--	procedureID				NBAP-ELEMENTARY-PROCEDURE.&procedureID	({NBAP-ELEMENTARY-PROCEDURES}),
--	criticality				NBAP-ELEMENTARY-PROCEDURE.&criticality	({NBAP-ELEMENTARY-PROCEDURES}{@procedureID}),
--	messageDiscriminator	NBAP-ELEMENTARY-PROCEDURE.&messageDiscriminator({NBAP-ELEMENTARY-PROCEDURES}{@procedureID}),
--	transactionID 			TransactionID,
--	value					NBAP-ELEMENTARY-PROCEDURE.&UnsuccessfulOutcome({NBAP-ELEMENTARY-PROCEDURES}{@procedureID})
--}

UnsuccessfulOutcome ::= SEQUENCE {
	procedureID					ProcedureID,
	criticality					Criticality,
	messageDiscriminator		MessageDiscriminator,
 	transactionID 				TransactionID,
	unsuccessfulOutcomeValue	UnsuccessfulOutcomeValue
}

UnsuccessfulOutcomeValue ::= ANY

--Outcome ::= SEQUENCE {
--	procedureID				NBAP-ELEMENTARY-PROCEDURE.&procedureID	({NBAP-ELEMENTARY-PROCEDURES}),
--	criticality				NBAP-ELEMENTARY-PROCEDURE.&criticality	({NBAP-ELEMENTARY-PROCEDURES}{@procedureID}),
--	messageDiscriminator	NBAP-ELEMENTARY-PROCEDURE.&messageDiscriminator({NBAP-ELEMENTARY-PROCEDURES}{@procedureID}),
--	transactionID 			TransactionID,
--	value					NBAP-ELEMENTARY-PROCEDURE.&Outcome	({NBAP-ELEMENTARY-PROCEDURES}{@procedureID})
--}

Outcome ::= SEQUENCE {
	procedureID				ProcedureID,
	criticality				Criticality,
	messageDiscriminator	MessageDiscriminator,
 	transactionID 			TransactionID,
	outcomeValue			OutcomeValue
}

OutcomeValue ::= ANY

-- **************************************************************
--
-- Interface Elementary Procedure List
--
-- **************************************************************

--NBAP-ELEMENTARY-PROCEDURES NBAP-ELEMENTARY-PROCEDURE ::= {
--	NBAP-ELEMENTARY-PROCEDURES-CLASS-1			|
--	NBAP-ELEMENTARY-PROCEDURES-CLASS-2			,
--	...
--}

--NBAP-ELEMENTARY-PROCEDURES-CLASS-1 NBAP-ELEMENTARY-PROCEDURE ::= {
--	cellSetupFDD										|
--	cellSetupTDD										|
--	cellReconfigurationFDD								|
--	cellReconfigurationTDD								|
--	cellDeletion										|
--	commonTransportChannelSetupFDD						|
--	commonTransportChannelSetupTDD						|
--	commonTransportChannelReconfigureFDD				|
--	commonTransportChannelReconfigureTDD				|
--	commonTransportChannelDelete						|
--	audit												|
--	blockResource										|
--	radioLinkSetupFDD									|
--	radioLinkSetupTDD									|
--	systemInformationUpdate								|
--	commonMeasurementInitiation							|
--	radioLinkAdditionFDD								|
--	radioLinkAdditionTDD								|
--	radioLinkDeletion									|
--	reset												|
--	synchronisedRadioLinkReconfigurationPreparationFDD	|
--	synchronisedRadioLinkReconfigurationPreparationTDD	|
--	unSynchronisedRadioLinkReconfigurationFDD			|
--	unSynchronisedRadioLinkReconfigurationTDD			|
--	dedicatedMeasurementInitiation						|
--	physicalSharedChannelReconfigurationTDD				,
--	...,
--	informationExchangeInitiation						|
--	cellSynchronisationInitiationTDD					|
--	cellSynchronisationReconfigurationTDD				|
--	cellSynchronisationAdjustmentTDD					|
--	physicalSharedChannelReconfigurationFDD
--}

--NBAP-ELEMENTARY-PROCEDURES-CLASS-2 NBAP-ELEMENTARY-PROCEDURE ::= {
--	resourceStatusIndication							|
--	auditRequired										|
--	commonMeasurementReport								|
--	commonMeasurementTermination						|
--	commonMeasurementFailure							|
--	synchronisedRadioLinkReconfigurationCommit			|
--	synchronisedRadioLinkReconfigurationCancellation	|
--	radioLinkFailure									|
--	radioLinkPreemption									|
--	radioLinkRestoration								|
--	dedicatedMeasurementReport							|
--	dedicatedMeasurementTermination						|
--	dedicatedMeasurementFailure							|
--	downlinkPowerControlFDD								|
--	downlinkPowerTimeslotControl						|
--	compressedModeCommand								|
--	unblockResource										|
--	errorIndicationForDedicated							|
--	errorIndicationForCommon							|
--	privateMessageForDedicated							|
--	privateMessageForCommon								,
--	...,
--	informationReporting								|
--	informationExchangeTermination						|
--	informationExchangeFailure							|
--	cellSynchronisationReportingTDD						|
--	cellSynchronisationTerminationTDD					|
--	cellSynchronisationFailureTDD						|
--	bearerRearrangement									|
--	radioLinkActivationFDD								|
--	radioLinkActivationTDD								|
--	radioLinkParameterUpdateFDD							|
--	radioLinkParameterUpdateTDD							|
--	mBMSNotificationUpdate
--}

-- **************************************************************
--
-- Interface Elementary Procedures
--
-- **************************************************************

-- Class 1

-- *** CellSetup (FDD) ***
--cellSetupFDD NBAP-ELEMENTARY-PROCEDURE ::= {
--	INITIATING MESSAGE		CellSetupRequestFDD
--	SUCCESSFUL OUTCOME		CellSetupResponse
--	UNSUCCESSFUL OUTCOME	CellSetupFailure
--	MESSAGE DISCRIMINATOR	common
--	PROCEDURE ID 			{ procedureCode id-cellSetup, ddMode fdd } 
--	CRITICALITY 			reject
--}

-- *** CellSetup (TDD) ***
--cellSetupTDD NBAP-ELEMENTARY-PROCEDURE ::= {
--	INITIATING MESSAGE		CellSetupRequestTDD
--	SUCCESSFUL OUTCOME		CellSetupResponse
--	UNSUCCESSFUL OUTCOME	CellSetupFailure
--	MESSAGE DISCRIMINATOR	common
--	PROCEDURE ID 			{ procedureCode id-cellSetup, ddMode tdd } 
--	CRITICALITY 			reject
--}

-- *** CellReconfiguration(FDD) ***
--cellReconfigurationFDD NBAP-ELEMENTARY-PROCEDURE ::= {
--	INITIATING MESSAGE		CellReconfigurationRequestFDD
--	SUCCESSFUL OUTCOME		CellReconfigurationResponse
--	UNSUCCESSFUL OUTCOME	CellReconfigurationFailure
--	MESSAGE DISCRIMINATOR	common
--	PROCEDURE ID 			{ procedureCode id-cellReconfiguration, ddMode fdd } 
--	CRITICALITY 			reject
--}

-- *** CellReconfiguration(TDD) ***
--cellReconfigurationTDD NBAP-ELEMENTARY-PROCEDURE ::= {
--	INITIATING MESSAGE		CellReconfigurationRequestTDD
--	SUCCESSFUL OUTCOME		CellReconfigurationResponse
--	UNSUCCESSFUL OUTCOME	CellReconfigurationFailure
--	MESSAGE DISCRIMINATOR	common
--	PROCEDURE ID 			{ procedureCode id-cellReconfiguration,	ddMode tdd } 
--	CRITICALITY 			reject
--}
-- *** CellDeletion ***
--cellDeletion NBAP-ELEMENTARY-PROCEDURE ::= {
--	INITIATING MESSAGE		CellDeletionRequest
--	SUCCESSFUL OUTCOME		CellDeletionResponse
--	MESSAGE DISCRIMINATOR	common
--	PROCEDURE ID 			{ procedureCode id-cellDeletion, ddMode common } 
--	CRITICALITY 			reject
--}

-- *** CommonTransportChannelSetup (FDD) ***
--commonTransportChannelSetupFDD NBAP-ELEMENTARY-PROCEDURE ::= {
--	INITIATING MESSAGE		CommonTransportChannelSetupRequestFDD
--	SUCCESSFUL OUTCOME		CommonTransportChannelSetupResponse
--	UNSUCCESSFUL OUTCOME	CommonTransportChannelSetupFailure
--	MESSAGE DISCRIMINATOR	common
--	PROCEDURE ID 			{ procedureCode id-commonTransportChannelSetup, ddMode fdd } 
--	CRITICALITY 			reject
--}
--commonTransportChannelSetupTDD NBAP-ELEMENTARY-PROCEDURE ::= {
--	INITIATING MESSAGE		CommonTransportChannelSetupRequestTDD
--	SUCCESSFUL OUTCOME		CommonTransportChannelSetupResponse
--	UNSUCCESSFUL OUTCOME	CommonTransportChannelSetupFailure
--	MESSAGE DISCRIMINATOR	common
--	PROCEDURE ID 			{ procedureCode id-commonTransportChannelSetup, ddMode tdd } 
--	CRITICALITY 			reject
--}
--
--*** CommonTransportChannelReconfigure (FDD) ***
--commonTransportChannelReconfigureFDD NBAP-ELEMENTARY-PROCEDURE ::= {
--	INITIATING MESSAGE		CommonTransportChannelReconfigurationRequestFDD
--	SUCCESSFUL OUTCOME		CommonTransportChannelReconfigurationResponse
--	UNSUCCESSFUL OUTCOME	CommonTransportChannelReconfigurationFailure
--	MESSAGE DISCRIMINATOR	common
--	PROCEDURE ID 			{ procedureCode id-commonTransportChannelReconfigure, ddMode fdd } 
--	CRITICALITY 			reject
--}

-- *** CommonTransportChannelReconfigure (TDD) ***
--commonTransportChannelReconfigureTDD NBAP-ELEMENTARY-PROCEDURE ::= {
--	INITIATING MESSAGE		CommonTransportChannelReconfigurationRequestTDD
--	SUCCESSFUL OUTCOME		CommonTransportChannelReconfigurationResponse
--	UNSUCCESSFUL OUTCOME	CommonTransportChannelReconfigurationFailure
--	MESSAGE DISCRIMINATOR	common
--	PROCEDURE ID 			{ procedureCode id-commonTransportChannelReconfigure, ddMode tdd } 
--	CRITICALITY 			reject
--}

-- *** CommonTransportChannelDelete ***
--commonTransportChannelDelete NBAP-ELEMENTARY-PROCEDURE ::= {
--	INITIATING MESSAGE		CommonTransportChannelDeletionRequest
--	SUCCESSFUL OUTCOME		CommonTransportChannelDeletionResponse
--	MESSAGE DISCRIMINATOR	common
--	PROCEDURE ID 			{ procedureCode id-commonTransportChannelDelete, ddMode common } 
--	CRITICALITY 			reject
--}

-- *** Audit ***
--audit NBAP-ELEMENTARY-PROCEDURE ::= {
--	INITIATING MESSAGE		AuditRequest
--	SUCCESSFUL OUTCOME		AuditResponse
--	UNSUCCESSFUL OUTCOME	AuditFailure
--	MESSAGE DISCRIMINATOR	common
--	PROCEDURE ID 			{ procedureCode id-audit, ddMode common } 
--	CRITICALITY 			reject
--}
-- *** BlockResourceRequest ***
--blockResource NBAP-ELEMENTARY-PROCEDURE ::= {
--	INITIATING MESSAGE		BlockResourceRequest
--	SUCCESSFUL OUTCOME		BlockResourceResponse
--	UNSUCCESSFUL OUTCOME	BlockResourceFailure
--	MESSAGE DISCRIMINATOR	common
--	PROCEDURE ID 			{ procedureCode id-blockResource, ddMode common } 
--	CRITICALITY 			reject
--}
-- *** RadioLinkSetup (FDD) ***
--radioLinkSetupFDD NBAP-ELEMENTARY-PROCEDURE ::= {
--	INITIATING MESSAGE		RadioLinkSetupRequestFDD
--	SUCCESSFUL OUTCOME		RadioLinkSetupResponseFDD
--	UNSUCCESSFUL OUTCOME	RadioLinkSetupFailureFDD
--	MESSAGE DISCRIMINATOR	common
--	PROCEDURE ID 			{ procedureCode id-radioLinkSetup, ddMode fdd } 
--	CRITICALITY 			reject
--}

-- *** RadioLinkSetup (TDD) ***
--radioLinkSetupTDD NBAP-ELEMENTARY-PROCEDURE ::= {
--	INITIATING MESSAGE		RadioLinkSetupRequestTDD
--	SUCCESSFUL OUTCOME		RadioLinkSetupResponseTDD
--	UNSUCCESSFUL OUTCOME	RadioLinkSetupFailureTDD
--	MESSAGE DISCRIMINATOR	common
--	PROCEDURE ID 			{ procedureCode id-radioLinkSetup, ddMode tdd } 
--	CRITICALITY 			reject
--}

-- *** SystemInformationUpdate ***
--systemInformationUpdate NBAP-ELEMENTARY-PROCEDURE ::= {
--	INITIATING MESSAGE		SystemInformationUpdateRequest
--	SUCCESSFUL OUTCOME		SystemInformationUpdateResponse
--	UNSUCCESSFUL OUTCOME	SystemInformationUpdateFailure
--	MESSAGE DISCRIMINATOR	common
--	PROCEDURE ID 			{ procedureCode id-systemInformationUpdate, ddMode common } 
--	CRITICALITY 			reject
--}
-- *** Reset ***
--reset NBAP-ELEMENTARY-PROCEDURE ::= {
--	INITIATING MESSAGE		ResetRequest
--	SUCCESSFUL OUTCOME		ResetResponse
--	MESSAGE DISCRIMINATOR	common
--	PROCEDURE ID 			{ procedureCode id-reset, ddMode common } 
--	CRITICALITY 			reject
--}
-- *** CommonMeasurementInitiation ***
--commonMeasurementInitiation NBAP-ELEMENTARY-PROCEDURE ::= {
--	INITIATING MESSAGE		CommonMeasurementInitiationRequest
--	SUCCESSFUL OUTCOME		CommonMeasurementInitiationResponse
--	UNSUCCESSFUL OUTCOME	CommonMeasurementInitiationFailure
--	MESSAGE DISCRIMINATOR	common
--	PROCEDURE ID 			{ procedureCode id-commonMeasurementInitiation,	ddMode common } 
--	CRITICALITY 			reject
--}
-- *** RadioLinkAddition (FDD) ***
--radioLinkAdditionFDD NBAP-ELEMENTARY-PROCEDURE ::= {
--	INITIATING MESSAGE		RadioLinkAdditionRequestFDD
--	SUCCESSFUL OUTCOME		RadioLinkAdditionResponseFDD
--	UNSUCCESSFUL OUTCOME	RadioLinkAdditionFailureFDD
--	MESSAGE DISCRIMINATOR	dedicated
--	PROCEDURE ID 			{ procedureCode id-radioLinkAddition, ddMode fdd } 
--	CRITICALITY 			reject
--}
-- *** RadioLinkAddition (TDD) ***
--radioLinkAdditionTDD NBAP-ELEMENTARY-PROCEDURE ::= {
--	INITIATING MESSAGE		RadioLinkAdditionRequestTDD
--	SUCCESSFUL OUTCOME		RadioLinkAdditionResponseTDD
--	UNSUCCESSFUL OUTCOME	RadioLinkAdditionFailureTDD
--	MESSAGE DISCRIMINATOR	dedicated
--	PROCEDURE ID 			{ procedureCode id-radioLinkAddition, ddMode tdd } 
--	CRITICALITY 			reject
--}
-- *** RadioLinkDeletion	***
--radioLinkDeletion NBAP-ELEMENTARY-PROCEDURE ::= {
--	INITIATING MESSAGE		RadioLinkDeletionRequest
--	SUCCESSFUL OUTCOME		RadioLinkDeletionResponse
--	MESSAGE DISCRIMINATOR	dedicated
--	PROCEDURE ID 			{ procedureCode id-radioLinkDeletion, ddMode common }
--	CRITICALITY 			reject
--}
-- *** SynchronisedRadioLinkReconfigurationPreparation (FDD) ***
--synchronisedRadioLinkReconfigurationPreparationFDD NBAP-ELEMENTARY-PROCEDURE ::= {
--	INITIATING MESSAGE		RadioLinkReconfigurationPrepareFDD
--	SUCCESSFUL OUTCOME		RadioLinkReconfigurationReady
--	UNSUCCESSFUL OUTCOME	RadioLinkReconfigurationFailure
--	MESSAGE DISCRIMINATOR	dedicated
--	PROCEDURE ID 			{ procedureCode id-synchronisedRadioLinkReconfigurationPreparation, ddMode fdd } 
--	CRITICALITY 			reject
--}

-- *** SynchronisedRadioLinkReconfigurationPreparation (TDD) ***
--synchronisedRadioLinkReconfigurationPreparationTDD NBAP-ELEMENTARY-PROCEDURE ::= {
--	INITIATING MESSAGE		RadioLinkReconfigurationPrepareTDD
--	SUCCESSFUL OUTCOME		RadioLinkReconfigurationReady
--	UNSUCCESSFUL OUTCOME	RadioLinkReconfigurationFailure
--	MESSAGE DISCRIMINATOR	dedicated
--	PROCEDURE ID 			{ procedureCode id-synchronisedRadioLinkReconfigurationPreparation, ddMode tdd } 
--	CRITICALITY 			reject
--}
-- *** UnSynchronisedRadioLinkReconfiguration (FDD) ***
--unSynchronisedRadioLinkReconfigurationFDD NBAP-ELEMENTARY-PROCEDURE ::= {
--	INITIATING MESSAGE		RadioLinkReconfigurationRequestFDD
--	SUCCESSFUL OUTCOME		RadioLinkReconfigurationResponse
--	UNSUCCESSFUL OUTCOME	RadioLinkReconfigurationFailure
--	MESSAGE DISCRIMINATOR	dedicated
--	PROCEDURE ID 			{ procedureCode id-unSynchronisedRadioLinkReconfiguration, ddMode fdd } 
--	CRITICALITY 			reject
--}

-- *** UnSynchronisedRadioLinkReconfiguration (TDD) ***
--unSynchronisedRadioLinkReconfigurationTDD NBAP-ELEMENTARY-PROCEDURE ::= {
--	INITIATING MESSAGE		RadioLinkReconfigurationRequestTDD
--	SUCCESSFUL OUTCOME		RadioLinkReconfigurationResponse
--	UNSUCCESSFUL OUTCOME	RadioLinkReconfigurationFailure
--	MESSAGE DISCRIMINATOR	dedicated
--	PROCEDURE ID 			{ procedureCode id-unSynchronisedRadioLinkReconfiguration, ddMode tdd } 
--	CRITICALITY 			reject
--}

-- *** DedicatedMeasurementInitiation  ***
--dedicatedMeasurementInitiation NBAP-ELEMENTARY-PROCEDURE ::= {
--	INITIATING MESSAGE		DedicatedMeasurementInitiationRequest
--	SUCCESSFUL OUTCOME		DedicatedMeasurementInitiationResponse
--	UNSUCCESSFUL OUTCOME	DedicatedMeasurementInitiationFailure
--	MESSAGE DISCRIMINATOR	dedicated
--	PROCEDURE ID 			{ procedureCode id-dedicatedMeasurementInitiation, ddMode common }
--	CRITICALITY 			reject
--}
-- *** PhysicalSharedChannelReconfiguration (FDD) ***
--physicalSharedChannelReconfigurationFDD NBAP-ELEMENTARY-PROCEDURE ::= {
--	INITIATING MESSAGE	PhysicalSharedChannelReconfigurationRequestFDD
--	SUCCESSFUL OUTCOME	PhysicalSharedChannelReconfigurationResponse
--	UNSUCCESSFUL OUTCOME	PhysicalSharedChannelReconfigurationFailure
--	MESSAGE DISCRIMINATOR	common
--	PROCEDURE ID 		{ procedureCode id-physicalSharedChannelReconfiguration, ddMode fdd } 
--	CRITICALITY 		reject
--}

-- *** PhysicalSharedChannelReconfiguration (TDD) ***
--physicalSharedChannelReconfigurationTDD NBAP-ELEMENTARY-PROCEDURE ::= {
--	INITIATING MESSAGE	PhysicalSharedChannelReconfigurationRequestTDD
--	SUCCESSFUL OUTCOME	PhysicalSharedChannelReconfigurationResponse
--	UNSUCCESSFUL OUTCOME	PhysicalSharedChannelReconfigurationFailure
--	MESSAGE DISCRIMINATOR	common
--	PROCEDURE ID 		{ procedureCode id-physicalSharedChannelReconfiguration, ddMode tdd } 
--	CRITICALITY 		reject
--}
-- *** InformationExchangeInitiation ***
--informationExchangeInitiation NBAP-ELEMENTARY-PROCEDURE ::= {
--    INITIATING MESSAGE		InformationExchangeInitiationRequest
--	SUCCESSFUL OUTCOME		InformationExchangeInitiationResponse
--	UNSUCCESSFUL OUTCOME	InformationExchangeInitiationFailure
--	MESSAGE DISCRIMINATOR	common
--	PROCEDURE ID 			{ procedureCode id-informationExchangeInitiation,	ddMode common } 
--	CRITICALITY 			reject
--}

-- *** CellSynchronisationInitiation (TDD only) ***
--cellSynchronisationInitiationTDD NBAP-ELEMENTARY-PROCEDURE ::= {
--	INITIATING MESSAGE	CellSynchronisationInitiationRequestTDD
--	SUCCESSFUL OUTCOME	CellSynchronisationInitiationResponseTDD
--	UNSUCCESSFUL OUTCOME	CellSynchronisationInitiationFailureTDD
--	MESSAGE DISCRIMINATOR	common
--	PROCEDURE ID 		{ procedureCode id-cellSynchronisationInitiation, ddMode tdd } 
--	CRITICALITY 		reject
--}
-- *** CellSynchronisationReconfiguration (TDD only) ***
--cellSynchronisationReconfigurationTDD NBAP-ELEMENTARY-PROCEDURE ::= {
--	INITIATING MESSAGE	CellSynchronisationReconfigurationRequestTDD
--	SUCCESSFUL OUTCOME	CellSynchronisationReconfigurationResponseTDD
--	UNSUCCESSFUL OUTCOME	CellSynchronisationReconfigurationFailureTDD
--	MESSAGE DISCRIMINATOR	common
--	PROCEDURE ID 		{ procedureCode id-cellSynchronisationReconfiguration, ddMode tdd } 
--	CRITICALITY 		reject
--}
-- *** CellSynchronisationAdjustment (TDD only) ***
--cellSynchronisationAdjustmentTDD NBAP-ELEMENTARY-PROCEDURE ::= {
--	INITIATING MESSAGE	CellSynchronisationAdjustmentRequestTDD
--	SUCCESSFUL OUTCOME	CellSynchronisationAdjustmentResponseTDD
--	UNSUCCESSFUL OUTCOME	CellSynchronisationAdjustmentFailureTDD
--	MESSAGE DISCRIMINATOR	common
--	PROCEDURE ID 		{ procedureCode id-cellSynchronisationAdjustment, ddMode tdd } 
--	CRITICALITY 		reject
--}
-- Class 2

-- *** ResourceStatusIndication ***
--resourceStatusIndication NBAP-ELEMENTARY-PROCEDURE ::= {
--	INITIATING MESSAGE		ResourceStatusIndication
--	MESSAGE DISCRIMINATOR	common
--	PROCEDURE ID 			{ procedureCode id-resourceStatusIndication, ddMode common } 
--	CRITICALITY 			ignore
--}

-- *** AuditRequired ***
--auditRequired NBAP-ELEMENTARY-PROCEDURE ::= {
--	INITIATING MESSAGE		AuditRequiredIndication
--	MESSAGE DISCRIMINATOR	common
--	PROCEDURE ID 			{ procedureCode id-auditRequired, ddMode common } 
--	CRITICALITY 			ignore
--}

-- *** CommonMeasurementReport ***
--commonMeasurementReport NBAP-ELEMENTARY-PROCEDURE ::= {
--	INITIATING MESSAGE		CommonMeasurementReport
--	MESSAGE DISCRIMINATOR	common
--	PROCEDURE ID 			{ procedureCode id-commonMeasurementReport, ddMode common } 
--	CRITICALITY 			ignore
--}

-- *** CommonMeasurementTermination ***
--commonMeasurementTermination NBAP-ELEMENTARY-PROCEDURE ::= {
--	INITIATING MESSAGE		CommonMeasurementTerminationRequest
--	MESSAGE DISCRIMINATOR	common
--	PROCEDURE ID 			{ procedureCode id-commonMeasurementTermination, ddMode common } 
--	CRITICALITY 			ignore
--}
-- *** CommonMeasurementFailure ***
--commonMeasurementFailure NBAP-ELEMENTARY-PROCEDURE ::= {
--	INITIATING MESSAGE		CommonMeasurementFailureIndication
--	MESSAGE DISCRIMINATOR	common
--	PROCEDURE ID 			{ procedureCode id-commonMeasurementFailure, ddMode common } 
--	CRITICALITY 			ignore
--}
-- *** SynchronisedRadioLinkReconfigurationCommit ***
--synchronisedRadioLinkReconfigurationCommit NBAP-ELEMENTARY-PROCEDURE ::= {
--	INITIATING MESSAGE		RadioLinkReconfigurationCommit
--	MESSAGE DISCRIMINATOR	dedicated
--	PROCEDURE ID 			{ procedureCode id-synchronisedRadioLinkReconfigurationCommit, ddMode common } 
--	CRITICALITY 			ignore
--}

-- *** SynchronisedRadioReconfigurationCancellation ***
--synchronisedRadioLinkReconfigurationCancellation NBAP-ELEMENTARY-PROCEDURE ::= {
--	INITIATING MESSAGE		RadioLinkReconfigurationCancel
--	MESSAGE DISCRIMINATOR	dedicated
--	PROCEDURE ID 			{ procedureCode id-synchronisedRadioLinkReconfigurationCancellation, ddMode common } 
--	CRITICALITY 			ignore
--}
-- *** RadioLinkFailure ***
--radioLinkFailure NBAP-ELEMENTARY-PROCEDURE ::= {
--	INITIATING MESSAGE		RadioLinkFailureIndication
--	MESSAGE DISCRIMINATOR	dedicated
--	PROCEDURE ID 			{ procedureCode id-radioLinkFailure, ddMode common }
--	CRITICALITY 			ignore
--}
-- *** RadioLinkPreemption ***
--radioLinkPreemption NBAP-ELEMENTARY-PROCEDURE ::= {
--	INITIATING MESSAGE	RadioLinkPreemptionRequiredIndication
--	MESSAGE DISCRIMINATOR	dedicated
--	PROCEDURE ID		{ procedureCode id-radioLinkPreemption, ddMode common }
--	CRITICALITY		ignore
--}

-- *** RadioLinkRestoration ***
--radioLinkRestoration NBAP-ELEMENTARY-PROCEDURE ::= {
--	INITIATING MESSAGE		RadioLinkRestoreIndication
--	MESSAGE DISCRIMINATOR	dedicated
--	PROCEDURE ID 			{ procedureCode id-radioLinkRestoration, ddMode common }
--	CRITICALITY 			ignore
--}

-- *** DedicatedMeasurementReport ***
--dedicatedMeasurementReport NBAP-ELEMENTARY-PROCEDURE ::= {
--	INITIATING MESSAGE		DedicatedMeasurementReport
--	MESSAGE DISCRIMINATOR	dedicated
--	PROCEDURE ID 			{ procedureCode id-dedicatedMeasurementReport, ddMode common }
--	CRITICALITY 			ignore
--}
-- *** DedicatedMeasurementTermination  ***
--dedicatedMeasurementTermination NBAP-ELEMENTARY-PROCEDURE ::= {
--	INITIATING MESSAGE		DedicatedMeasurementTerminationRequest
--	MESSAGE DISCRIMINATOR	dedicated
--	PROCEDURE ID 			{ procedureCode id-dedicatedMeasurementTermination, ddMode common }
--	CRITICALITY 			ignore
--}

-- *** DedicatedMeasurementFailure ***
--dedicatedMeasurementFailure NBAP-ELEMENTARY-PROCEDURE ::= {
--	INITIATING MESSAGE		DedicatedMeasurementFailureIndication
--	MESSAGE DISCRIMINATOR	dedicated
--	PROCEDURE ID 			{ procedureCode id-dedicatedMeasurementFailure, ddMode common }
--	CRITICALITY 			ignore
--}
-- *** DLPowerControl (FDD only) ***
--downlinkPowerControlFDD NBAP-ELEMENTARY-PROCEDURE ::= {
--	INITIATING MESSAGE		DL-PowerControlRequest
--	MESSAGE DISCRIMINATOR	dedicated
--	PROCEDURE ID 			{ procedureCode id-downlinkPowerControl, ddMode fdd }
--	CRITICALITY 			ignore
--}
-- *** DLPowerTimeslotControl (TDD only) ***
--downlinkPowerTimeslotControl NBAP-ELEMENTARY-PROCEDURE ::= {
--	INITIATING MESSAGE		DL-PowerTimeslotControlRequest
--	MESSAGE DISCRIMINATOR	dedicated
--	PROCEDURE ID 			{ procedureCode id-downlinkPowerTimeslotControl, ddMode tdd }
--	CRITICALITY 			ignore
--}
-- *** CompressedModeCommand (FDD only) ***
--compressedModeCommand NBAP-ELEMENTARY-PROCEDURE ::= {
--	INITIATING MESSAGE		CompressedModeCommand
--	MESSAGE DISCRIMINATOR	dedicated
--	PROCEDURE ID 			{ procedureCode id-compressedModeCommand, ddMode fdd }
--	CRITICALITY 			ignore
--}
-- *** UnblockResourceIndication ***
--unblockResource NBAP-ELEMENTARY-PROCEDURE ::= {
--	INITIATING MESSAGE		UnblockResourceIndication
--	MESSAGE DISCRIMINATOR	common
--	PROCEDURE ID 			{ procedureCode id-unblockResource, ddMode common } 
--	CRITICALITY 			ignore
--}
-- *** ErrorIndication for Dedicated procedures ***
--errorIndicationForDedicated NBAP-ELEMENTARY-PROCEDURE ::= {
--	INITIATING MESSAGE		ErrorIndication
--	MESSAGE DISCRIMINATOR	dedicated
--	PROCEDURE ID 			{ procedureCode	id-errorIndicationForDedicated, ddMode common }
--	CRITICALITY 			ignore
--}
-- *** ErrorIndication for Common procedures ***
--errorIndicationForCommon NBAP-ELEMENTARY-PROCEDURE ::= {
--	INITIATING MESSAGE		ErrorIndication
--	MESSAGE DISCRIMINATOR	common
--	PROCEDURE ID 			{ procedureCode	id-errorIndicationForCommon, ddMode common }
--	CRITICALITY 			ignore
--}
-- *** CellSynchronisationReporting (TDD only) ***
--cellSynchronisationReportingTDD NBAP-ELEMENTARY-PROCEDURE ::= {
--	INITIATING MESSAGE		CellSynchronisationReportTDD
--	MESSAGE DISCRIMINATOR	common
--	PROCEDURE ID 			{ procedureCode	id-cellSynchronisationReporting, ddMode tdd }
--	CRITICALITY 			ignore
--}
-- *** CellSynchronisationTermination (TDD only) ***
--cellSynchronisationTerminationTDD NBAP-ELEMENTARY-PROCEDURE ::= {
--	INITIATING MESSAGE		CellSynchronisationTerminationRequestTDD
--	MESSAGE DISCRIMINATOR	common
--	PROCEDURE ID 			{ procedureCode	id-cellSynchronisationTermination, ddMode tdd }
--	CRITICALITY 			ignore
--}
-- *** CellSynchronisationFailure (TDD only) ***
--cellSynchronisationFailureTDD NBAP-ELEMENTARY-PROCEDURE ::= {
--	INITIATING MESSAGE		CellSynchronisationFailureIndicationTDD
--	MESSAGE DISCRIMINATOR	common
--	PROCEDURE ID 			{ procedureCode	id-cellSynchronisationFailure, ddMode tdd }
--	CRITICALITY 			ignore
--}
-- *** PrivateMessage for Dedicated procedures ***
--privateMessageForDedicated NBAP-ELEMENTARY-PROCEDURE ::= {
--	INITIATING MESSAGE		PrivateMessage
--	MESSAGE DISCRIMINATOR	dedicated
--	PROCEDURE ID			{ procedureCode	id-privateMessageForDedicated, ddMode common }
--	CRITICALITY				ignore
--}
-- *** PrivateMessage for Common procedures ***
--privateMessageForCommon NBAP-ELEMENTARY-PROCEDURE ::= {
--	INITIATING MESSAGE		PrivateMessage
--	MESSAGE DISCRIMINATOR	common
--	PROCEDURE ID			{ procedureCode	id-privateMessageForCommon, ddMode common }
--	CRITICALITY				ignore
--}
-- *** InformationReporting ***
--informationReporting NBAP-ELEMENTARY-PROCEDURE ::= {
--	INITIATING MESSAGE		InformationReport
--	MESSAGE DISCRIMINATOR	common
--	PROCEDURE ID 			{ procedureCode id-informationReporting, ddMode common } 
--	CRITICALITY 			ignore
--}
-- *** InformationExchangeTermination ***
--informationExchangeTermination NBAP-ELEMENTARY-PROCEDURE ::= {
--	INITIATING MESSAGE		InformationExchangeTerminationRequest
--	MESSAGE DISCRIMINATOR	common
--	PROCEDURE ID 			{ procedureCode id-informationExchangeTermination, ddMode common } 
--	CRITICALITY 			ignore
--}

-- *** InformationExchangeFailure ***
--informationExchangeFailure NBAP-ELEMENTARY-PROCEDURE ::= {
--	INITIATING MESSAGE		InformationExchangeFailureIndication
--	MESSAGE DISCRIMINATOR	common
--	PROCEDURE ID 			{ procedureCode id-informationExchangeFailure, ddMode common } 
--	CRITICALITY 			ignore
--}
-- *** BearerRearrangement ***
--bearerRearrangement NBAP-ELEMENTARY-PROCEDURE ::= {
--	INITIATING MESSAGE		BearerRearrangementIndication
--	MESSAGE DISCRIMINATOR	dedicated
--	PROCEDURE ID 			{ procedureCode id-BearerRearrangement, ddMode common }
--	CRITICALITY 			ignore
--}

-- *** RadioLinkActivation (FDD) ***
--radioLinkActivationFDD NBAP-ELEMENTARY-PROCEDURE ::= {
--	INITIATING MESSAGE		RadioLinkActivationCommandFDD
--	MESSAGE DISCRIMINATOR	dedicated
--	PROCEDURE ID			{ procedureCode id-radioLinkActivation, ddMode fdd }
--	CRITICALITY				ignore
--}
-- *** RadioLinkActivation (TDD) ***
--radioLinkActivationTDD NBAP-ELEMENTARY-PROCEDURE ::= {
--	INITIATING MESSAGE		RadioLinkActivationCommandTDD
--	MESSAGE DISCRIMINATOR	dedicated
--	PROCEDURE ID			{ procedureCode id-radioLinkActivation, ddMode tdd }
--	CRITICALITY				ignore
--}
-- *** RadioLinkParameterUpdate (FDD) ***
--radioLinkParameterUpdateFDD NBAP-ELEMENTARY-PROCEDURE ::= {
--	INITIATING MESSAGE		RadioLinkParameterUpdateIndicationFDD
--	MESSAGE DISCRIMINATOR	dedicated
--	PROCEDURE ID 			{ procedureCode id-radioLinkParameterUpdate, ddMode fdd }
--	CRITICALITY 			ignore
--}

-- *** RadioLinkParameterUpdate (TDD) ***
--radioLinkParameterUpdateTDD NBAP-ELEMENTARY-PROCEDURE ::= {
--	INITIATING MESSAGE		RadioLinkParameterUpdateIndicationTDD
--	MESSAGE DISCRIMINATOR	dedicated
--	PROCEDURE ID 			{ procedureCode id-radioLinkParameterUpdate, ddMode tdd }
--	CRITICALITY 			ignore
--}
-- *** MBMSNotificationUpdate ***
--mBMSNotificationUpdate NBAP-ELEMENTARY-PROCEDURE ::= {
--	INITIATING MESSAGE		MBMSNotificationUpdateCommand
--	MESSAGE DISCRIMINATOR	common
--	PROCEDURE ID 			{ procedureCode id-mBMSNotificationUpdate, ddMode common }
--	CRITICALITY 			ignore
--}
DummyInitiatingmessages ::= CHOICE{
	id-audit 											AuditRequest,							--(0),
	id-auditRequired 									AuditRequiredIndication,				--(1),
	id-blockResource 									BlockResourceRequest,					--(2),
	id-cellDeletion										CellDeletionRequest,					-- (3),
	id-cellReconfiguration 								CellReconfigurationRequestFDD,			-- (4),
	id-cellReconfiguration-tdd							CellReconfigurationRequestTDD,			-- (4),
	id-cellSetup										CellSetupRequestFDD,					-- (5),
	id-cellSetup-tdd									CellSetupRequestTDD,					-- (5),
	id-commonMeasurementFailure 						CommonMeasurementFailureIndication,		--	(6),
	id-commonMeasurementInitiation 						CommonMeasurementInitiationRequest,		--	(7),
	id-commonMeasurementReport							CommonMeasurementReport,				-- (8),
	id-commonMeasurementTermination 					CommonMeasurementTerminationRequest,		--	(9),
	id-commonTransportChannelDelete 					CommonTransportChannelDeletionRequest,			--(10),
	id-commonTransportChannelReconfigure 				CommonTransportChannelReconfigurationRequestFDD, --	(11),
	id-commonTransportChannelReconfigure-tdd			CommonTransportChannelReconfigurationRequestTDD, --	(11),
	id-commonTransportChannelSetup 						CommonTransportChannelSetupRequestFDD,	--	(12),
	id-commonTransportChannelSetup-tdd 					CommonTransportChannelSetupRequestTDD,	--	(12),
	id-reset											ResetRequest,							--	(13),
	id-compressedModeCommand 							CompressedModeCommand,					--	(14),
	id-dedicatedMeasurementFailure 						DedicatedMeasurementFailureIndication,	--	(16),
	id-dedicatedMeasurementInitiation 					DedicatedMeasurementInitiationRequest,	--	(17),
	id-dedicatedMeasurementReport 						DedicatedMeasurementReport,				--	(18),
	id-dedicatedMeasurementTermination 					DedicatedMeasurementTerminationRequest,	--	(19),
	id-downlinkPowerControl 							DL-PowerControlRequest,					--	(20),
	id-errorIndicationForDedicated						ErrorIndication,						--	(21),
	id-privateMessageForDedicated						PrivateMessage,							--	(22),
	id-radioLinkAddition 								RadioLinkAdditionRequestFDD,			--	(23),
	id-radioLinkDeletion 								RadioLinkDeletionRequest,				--	(24),
	id-radioLinkFailure 								RadioLinkFailureIndication,				--	(25),
	id-radioLinkRestoration 							RadioLinkRestoreIndication,				--	(26),
	id-radioLinkSetup 									RadioLinkSetupRequestFDD,				--	(27),
	id-radioLinkSetup-tdd								RadioLinkSetupRequestTDD,				--	(27),
	id-resourceStatusIndication 						ResourceStatusIndication,				--	(28),
	id-synchronisedRadioLinkReconfigurationCancellation	RadioLinkReconfigurationCancel,			--	(29),
	id-synchronisedRadioLinkReconfigurationCommit		RadioLinkReconfigurationCommit,			--	(30),
	id-synchronisedRadioLinkReconfigurationPreparation 	RadioLinkReconfigurationPrepareFDD,		--	(31),
	id-synchronisedRadioLinkReconfigurationPreparation-tdd 	RadioLinkReconfigurationPrepareTDD,	--	(31),
	id-systemInformationUpdate 							SystemInformationUpdateRequest,			--	(32),
	id-unblockResource 									UnblockResourceIndication,				--	(33),
	id-unSynchronisedRadioLinkReconfiguration 			RadioLinkReconfigurationRequestFDD,		--	(34),
	id-unSynchronisedRadioLinkReconfiguration-tdd		RadioLinkReconfigurationRequestTDD,		--	(34),
	id-downlinkPowerTimeslotControl 					DL-PowerTimeslotControlRequest,			--	(38),
	id-errorIndicationForCommon							ErrorIndication,						--	(35),
	id-privateMessageForCommon							PrivateMessage,							--	(36),
	id-physicalSharedChannelReconfiguration 			PhysicalSharedChannelReconfigurationRequestFDD,	--	(37),
	id-physicalSharedChannelReconfiguration-tdd			PhysicalSharedChannelReconfigurationRequestTDD,	--	(37),
	id-radioLinkPreemption								RadioLinkPreemptionRequiredIndication,			--	(39),
	id-informationExchangeFailure						InformationExchangeFailureIndication,			--	(40),
	id-informationExchangeInitiation					InformationExchangeInitiationRequest,			--	(41),
	id-informationExchangeTermination					InformationExchangeTerminationRequest,			--	(42),
	id-informationReporting								InformationReport,								--	(43),
	id-cellSynchronisationAdjustment					CellSynchronisationAdjustmentRequestTDD,		--	(44),
	id-cellSynchronisationInitiation					CellSynchronisationInitiationRequestTDD,		--	(45),
	id-cellSynchronisationReconfiguration				CellSynchronisationReconfigurationRequestTDD,	--	(46),
	id-cellSynchronisationReporting						CellSynchronisationReportTDD,					--	(47),
	id-cellSynchronisationTermination					CellSynchronisationTerminationRequestTDD,		--	(48),
	id-cellSynchronisationFailure						CellSynchronisationFailureIndicationTDD,		--	(49),
	id-BearerRearrangement								BearerRearrangementIndication,					--	(50),
	id-radioLinkActivation								RadioLinkActivationCommandFDD,					--	(51),
	id-radioLinkActivation-tdd							RadioLinkActivationCommandTDD,					--	(51),
	id-radioLinkParameterUpdate							RadioLinkParameterUpdateIndicationFDD,			--	(52)	
	id-radioLinkParameterUpdate-tdd						RadioLinkParameterUpdateIndicationTDD,			--	(52)	
	id-mBMSNotificationUpdate							MBMSNotificationUpdateCommand,					--	(53),
...
}

DummySuccessfullOutcomemessages ::= CHOICE{
	id-audit 											AuditResponse,							--	(0),
	id-blockResource 									BlockResourceResponse,					--	(2),
	id-cellDeletion										CellDeletionResponse,					-- (3),
	id-cellReconfiguration 								CellReconfigurationResponse,			-- (4),
	id-cellSetup										CellSetupResponse,						-- (5),
	id-commonMeasurementInitiation 						CommonMeasurementInitiationFailure,		--	(7),
	id-commonTransportChannelDelete 					CommonTransportChannelDeletionResponse,	--	(10),
	id-commonTransportChannelReconfigure 				CommonTransportChannelReconfigurationResponse, --	(11),
	id-commonTransportChannelSetup 						CommonTransportChannelSetupResponse,	-- (12),
	id-reset											ResetResponse,							--	(13),
	id-dedicatedMeasurementInitiation 					DedicatedMeasurementInitiationResponse,	--	(17),
	id-radioLinkAddition 								RadioLinkAdditionResponseFDD,			--	(23),
	id-radioLinkAddition-tdd 							RadioLinkAdditionResponseTDD,			--	(23),
	id-radioLinkDeletion 								RadioLinkDeletionResponse,				--	(24),
	id-radioLinkSetup 									RadioLinkSetupResponseFDD,				--	(27),
	id-radioLinkSetup-tdd								RadioLinkSetupResponseTDD,				--	(27),
	id-synchronisedRadioLinkReconfigurationPreparation 	RadioLinkReconfigurationReady,		--	(31),
	id-systemInformationUpdate 							SystemInformationUpdateResponse,			--	(32),
	id-unSynchronisedRadioLinkReconfiguration			RadioLinkReconfigurationResponse,		--	(34),
	id-physicalSharedChannelReconfiguration 			PhysicalSharedChannelReconfigurationResponse,	--	(37),
	id-informationExchangeInitiation					InformationExchangeInitiationResponse,			--	(41),
	id-cellSynchronisationAdjustment					CellSynchronisationAdjustmentResponseTDD,		--	(44),
	id-cellSynchronisationInitiation					CellSynchronisationInitiationResponseTDD,		--	(45),
	id-cellSynchronisationReconfiguration				CellSynchronisationReconfigurationResponseTDD,	--	(46),
	...
}

DummyUnsuccessfullOutcomemessages ::= CHOICE{
	id-audit 											AuditFailure,							--	(0),
	id-blockResource 									BlockResourceFailure,					--	(2),
	id-cellReconfiguration 								CellReconfigurationFailure,				-- (4),
	id-cellSetup										CellSetupFailure,						-- (5),
	id-commonMeasurementInitiation 						CommonMeasurementInitiationResponse,		--	(7),
	id-commonTransportChannelReconfigure 				CommonTransportChannelReconfigurationFailure, --	(11),
	id-commonTransportChannelSetup 						CommonTransportChannelSetupFailure,		-- (12),
	id-dedicatedMeasurementInitiation 					DedicatedMeasurementInitiationFailure,	--	(17),
	id-radioLinkAddition 								RadioLinkAdditionFailureFDD,			--	(23),
	id-radioLinkAddition-tdd							RadioLinkAdditionFailureTDD,			--	(23),
	id-radioLinkSetup 									RadioLinkSetupFailureFDD,				--	(27),
	id-radioLinkSetup-tdd								RadioLinkSetupFailureTDD,				--	(27),
	id-synchronisedRadioLinkReconfigurationPreparation 	RadioLinkReconfigurationFailure,		--	(31),
	id-systemInformationUpdate 							SystemInformationUpdateFailure,			--	(32),
	id-unSynchronisedRadioLinkReconfiguration			RadioLinkReconfigurationFailure,		--	(34),
	id-physicalSharedChannelReconfiguration 			PhysicalSharedChannelReconfigurationFailure,	--	(37),
	id-informationExchangeInitiation					InformationExchangeInitiationFailure,			--	(41),
	id-cellSynchronisationAdjustment					CellSynchronisationAdjustmentFailureTDD,		--	(44),
	id-cellSynchronisationInitiation					CellSynchronisationInitiationFailureTDD,		--	(45),
	id-cellSynchronisationReconfiguration				CellSynchronisationReconfigurationFailureTDD,	--	(46),
	...
}

-- 9.3.3	PDU Definitions
-- **************************************************************
--
-- PDU definitions for NBAP.
--
-- **************************************************************

--NBAP-PDU-Contents {
--itu-t (0) identified-organization (4) etsi (0) mobileDomain (0) 
--umts-Access (20) modules (3) nbap (2) version1 (1) nbap-PDU-Contents (1) }

--DEFINITIONS AUTOMATIC TAGS ::= 

--BEGIN

-- **************************************************************
--
-- IE parameter types from other modules.
--
-- **************************************************************

-- :
-- :
DymmyProtocolIE-ID ::= CHOICE {
	id-AICH-Information											Common-PhysicalChannel-Status-Information,	--	(0),
--	id-AICH-InformationItem-ResourceStatusInd					AICH-InformationItem-ResourceStatusInd,			(1),
	id-BCH-Information											Common-TransportChannel-Status-Information,	--	(7),
--	id-BCH-InformationItem-ResourceStatusInd					BCH-InformationItem-ResourceStatusInd,			(8),
	id-BCCH-ModificationTime									BCCH-ModificationTime,						--	(9),
	id-BlockingPriorityIndicator								BlockingPriorityIndicator,					--	(10),
	id-Cause													Cause,										--	(13),
	id-CCP-InformationItem-AuditRsp								CCP-InformationItem-AuditRsp,				--	(14),
	id-CCP-InformationList-AuditRsp								CCP-InformationList-AuditRsp,				--	(15),
	id-CCP-InformationItem-ResourceStatusInd					CCP-InformationItem-ResourceStatusInd,		--	(16),
	id-Cell-InformationItem-AuditRsp							Cell-InformationItem-AuditRsp,				--	(17),
	id-Cell-InformationItem-ResourceStatusInd					Cell-InformationItem-ResourceStatusInd,		--	(18),
	id-Cell-InformationList-AuditRsp							Cell-InformationList-AuditRsp,				--	(19),
	id-CellParameterID											CellParameterID,							--	(23),
	id-CFN														CFN,										--	(24),
	id-C-ID														C-ID,										--	(25),
	id-CommonMeasurementAccuracy								CommonMeasurementAccuracy,					--	(39),
	id-CommonMeasurementObjectType-CM-Rprt						CommonMeasurementObjectType-CM-Rprt,		--	(31),
	id-CommonMeasurementObjectType-CM-Rqst						CommonMeasurementObjectType-CM-Rqst,		--	(32),
	id-CommonMeasurementObjectType-CM-Rsp						CommonMeasurementObjectType-CM-Rsp,			--	(33),
	id-CommonMeasurementType									CommonMeasurementType,						--	(34),
	id-CommonPhysicalChannelID									CommonPhysicalChannelID,					--	(35),
	id-CommonPhysicalChannelType-CTCH-SetupRqstFDD				CommonPhysicalChannelType-CTCH-SetupRqstFDD,--	(36),
	id-CommonPhysicalChannelType-CTCH-SetupRqstTDD				CommonPhysicalChannelType-CTCH-SetupRqstTDD,--	(37),
	id-CommunicationControlPortID								CommunicationControlPortID,					--	(40),
	id-ConfigurationGenerationID								ConfigurationGenerationID,					--	(43),
	id-CRNC-CommunicationContextID								CRNC-CommunicationContextID,				--	(44),
	id-CriticalityDiagnostics									CriticalityDiagnostics,						--	(45),
	id-DCHs-to-Add-FDD											DCH-FDD-Information,						--	(48),
--	id-DCH-AddList-RL-ReconfPrepTDD								DCH-AddList-RL-ReconfPrepTDD,					(49),
	id-DCHs-to-Add-TDD											DCH-TDD-Information,						--	(50),
	id-DCH-DeleteList-RL-ReconfPrepFDD							DCH-DeleteList-RL-ReconfPrepFDD,			--	(52),
	id-DCH-DeleteList-RL-ReconfPrepTDD							DCH-DeleteList-RL-ReconfPrepTDD,			--	(53),
	id-DCH-DeleteList-RL-ReconfRqstFDD							DCH-DeleteList-RL-ReconfRqstFDD,			--	(54),
	id-DCH-DeleteList-RL-ReconfRqstTDD							DCH-DeleteList-RL-ReconfRqstTDD,			--	(55),
	id-DCH-FDD-Information										DCH-FDD-Information,						--	(56),
	id-DCH-TDD-Information										DCH-TDD-Information,						--	(57),
	id-DCH-InformationResponse									DCH-InformationResponse,					--	(59),
	id-FDD-DCHs-to-Modify										FDD-DCHs-to-Modify,							--	(62),
	id-TDD-DCHs-to-Modify										TDD-DCHs-to-Modify,							--	(63),
--	id-DCH-ModifyList-RL-ReconfRqstTDD							DCH-ModifyList-RL-ReconfRqstTDD,				(65),
	id-DCH-RearrangeList-Bearer-RearrangeInd					DCH-RearrangeList-Bearer-RearrangeInd,		--	(135),
	id-DedicatedMeasurementObjectType-DM-Rprt					DedicatedMeasurementObjectType-DM-Rprt,		--	(67),
	id-DedicatedMeasurementObjectType-DM-Rqst					DedicatedMeasurementObjectType-DM-Rqst,		--	(68),
	id-DedicatedMeasurementObjectType-DM-Rsp					DedicatedMeasurementObjectType-DM-Rsp,		--	(69),
	id-DedicatedMeasurementType									DedicatedMeasurementType,						--	(70),
	id-DL-CCTrCH-InformationItem-RL-SetupRqstTDD				DL-CCTrCH-InformationItem-RL-SetupRqstTDD,		--	(72),
	id-DL-CCTrCH-InformationList-RL-AdditionRqstTDD				DL-CCTrCH-InformationList-RL-AdditionRqstTDD,	--	(73),
	id-DL-CCTrCH-InformationList-RL-SetupRqstTDD				DL-CCTrCH-InformationList-RL-SetupRqstTDD,		--	(76),
	id-DL-DPCH-InformationItem-RL-AdditionRqstTDD				DL-DPCH-InformationItem-RL-AdditionRqstTDD,		--	(77),
	id-DL-DPCH-InformationList-RL-SetupRqstTDD					DL-DPCH-InformationItem-RL-SetupRqstTDD,		--	(79),
	id-DL-DPCH-Information-RL-ReconfPrepFDD						DL-DPCH-Information-RL-ReconfPrepFDD,			--	(81),
	id-DL-DPCH-Information-RL-ReconfRqstFDD						DL-DPCH-Information-RL-ReconfRqstFDD,			--	(82),
	id-DL-DPCH-Information-RL-SetupRqstFDD						DL-DPCH-Information-RL-SetupRqstFDD,			--	(83),
	id-DL-DPCH-TimingAdjustment									DL-DPCH-TimingAdjustment,						--	(21),
	id-DL-ReferencePowerInformationItem-DL-PC-Rqst				DL-ReferencePowerInformationItem-DL-PC-Rqst,	--	(84),
	id-DLReferencePower											DL-Power,										--	(85),
	id-DLReferencePowerList-DL-PC-Rqst							DL-ReferencePowerInformationList-DL-PC-Rqst,	--	(86),
--	id-Unused-ProtocolIE-ID-87											(87),
--	id-Unused-ProtocolIE-ID-89											(89),
--	id-Unused-ProtocolIE-ID-91											(91),
--	id-Unused-ProtocolIE-ID-93											(93),
	id-DSCHs-to-Add-TDD											DSCH-TDD-Information,								--	(96),
	id-DSCH-Information-DeleteList-RL-ReconfPrepTDD				DSCH-Information-DeleteList-RL-ReconfPrepTDD,	--	(98),
	id-DSCH-Information-ModifyList-RL-ReconfPrepTDD				DSCH-Information-ModifyList-RL-ReconfPrepTDD,	--	(100),
	id-DSCH-InformationResponse									DSCH-InformationResponse,						--	(105),
--	id-Unused-ProtocolIE-ID-106											(106),
	id-DSCH-TDD-Information										DSCH-TDD-Information,							--	(107),
--	id-Unused-ProtocolIE-ID-108											(108),
--	id-Unused-ProtocolIE-ID-112											(112),
	id-DSCH-RearrangeList-Bearer-RearrangeInd					DSCH-RearrangeList-Bearer-RearrangeInd,			--	(136),
	id-End-Of-Audit-Sequence-Indicator 							End-Of-Audit-Sequence-Indicator,				--	(113),
	id-FACH-Information											Common-TransportChannel-Status-Information,								--	(116),
--	id-FACH-InformationItem-ResourceStatusInd					Common-TransportChannel-Status-Information,			(117),
	id-FACH-ParametersList-CTCH-ReconfRqstTDD					FACH-ParametersList-CTCH-ReconfRqstTDD,			--	(120),
	id-FACH-ParametersListIE-CTCH-SetupRqstFDD					FACH-ParametersListIE-CTCH-SetupRqstFDD,		--	(121),
	id-FACH-ParametersListIE-CTCH-SetupRqstTDD					FACH-ParametersListIE-CTCH-SetupRqstTDD,		--	(122),
	id-IndicationType-ResourceStatusInd							IndicationType-ResourceStatusInd,				--	(123),
	id-Local-Cell-ID											Local-Cell-ID,									--	(124),
	id-Local-Cell-Group-InformationItem-AuditRsp				Local-Cell-Group-InformationItem-AuditRsp,		--	(2),
	id-Local-Cell-Group-InformationItem-ResourceStatusInd		Local-Cell-Group-InformationItem-ResourceStatusInd,	--	(3),
	id-Local-Cell-Group-InformationItem2-ResourceStatusInd		Local-Cell-Group-InformationItem2-ResourceStatusInd, --	(4),
	id-Local-Cell-Group-InformationList-AuditRsp				Local-Cell-Group-InformationList-AuditRsp,			--	(5),
	id-Local-Cell-InformationItem-AuditRsp						Local-Cell-InformationItem-AuditRsp,				--	(125),
	id-Local-Cell-InformationItem-ResourceStatusInd				Local-Cell-InformationItem-ResourceStatusInd,		--	(126),
	id-Local-Cell-InformationItem2-ResourceStatusInd			Local-Cell-InformationItem2-ResourceStatusInd,		--	(127),
	id-Local-Cell-InformationList-AuditRsp						Local-Cell-InformationList-AuditRsp,				--	(128),
	id-AdjustmentPeriod											AdjustmentPeriod,									--	(129),
	id-MaxAdjustmentStep										MaxAdjustmentStep,									--	(130),
	id-MaximumTransmissionPower									MaximumTransmissionPower,							--	(131),
	id-MeasurementFilterCoefficient								MeasurementFilterCoefficient,						--	(132),
	id-MeasurementID											MeasurementID,		--(133),
	id-MessageStructure											MessageStructure,	--(115),
	id-MIB-SB-SIB-InformationList-SystemInfoUpdateRqst			MIB-SB-SIB-InformationList-SystemInfoUpdateRqst,	--	(134),
	id-NodeB-CommunicationContextID								NodeB-CommunicationContextID,						--	(143),
	id-NeighbouringCellMeasurementInformation					NeighbouringCellMeasurementInformation,				--	(455),
	id-P-CCPCH-Information										Common-PhysicalChannel-Status-Information,			--	(144),
--	id-P-CCPCH-InformationItem-ResourceStatusInd						(145),
	id-P-CPICH-Information										Common-PhysicalChannel-Status-Information,			--	(146),
--	id-P-CPICH-InformationItem-ResourceStatusInd						(147),
	id-P-SCH-Information										Common-PhysicalChannel-Status-Information,			--	(148),
	id-PCCPCH-Information-Cell-ReconfRqstTDD					PCCPCH-Information-Cell-ReconfRqstTDD,				--	(150),
	id-PCCPCH-Information-Cell-SetupRqstTDD						PCCPCH-Information-Cell-SetupRqstTDD,				--	(151),
	id-PCH-Parameters-CTCH-ReconfRqstTDD						PCH-Parameters-CTCH-ReconfRqstTDD,					--	(155),
	id-PCH-ParametersItem-CTCH-SetupRqstFDD						PCH-ParametersItem-CTCH-SetupRqstFDD,				--	(156),
	id-PCH-ParametersItem-CTCH-SetupRqstTDD						PCH-ParametersItem-CTCH-SetupRqstTDD,				--	(157),
	id-PCH-Information											Common-TransportChannel-Status-Information,			--	(158),
	id-PDSCH-Information-AddListIE-PSCH-ReconfRqst				PDSCH-Information-AddItem-PSCH-ReconfRqst,			--	(161),
	id-PDSCH-Information-ModifyListIE-PSCH-ReconfRqst			PDSCH-Information-ModifyItem-PSCH-ReconfRqst,		--	(162),
	id-PDSCHSets-AddList-PSCH-ReconfRqst						PDSCHSets-AddList-PSCH-ReconfRqst,					--	(163),
	id-PDSCHSets-DeleteList-PSCH-ReconfRqst						PDSCHSets-DeleteList-PSCH-ReconfRqst,				--	(164),
	id-PDSCHSets-ModifyList-PSCH-ReconfRqst						PDSCHSets-ModifyList-PSCH-ReconfRqst,				--	(165),
	id-PICH-Information											Common-PhysicalChannel-Status-Information,			--	(166),
	id-PICH-Parameters-CTCH-ReconfRqstTDD						PICH-Parameters-CTCH-ReconfRqstTDD,					--	(168),
	id-PowerAdjustmentType										PowerAdjustmentType,								--	(169),
	id-PRACH-Information										Common-PhysicalChannel-Status-Information,			--	(170),
	id-PrimaryCCPCH-Information-Cell-ReconfRqstFDD				PrimaryCCPCH-Information-Cell-ReconfRqstFDD,		--	(175),
	id-PrimaryCCPCH-Information-Cell-SetupRqstFDD				PrimaryCCPCH-Information-Cell-SetupRqstFDD,			--	(176),
	id-PrimaryCPICH-Information-Cell-ReconfRqstFDD				PrimaryCPICH-Information-Cell-ReconfRqstFDD,		--	(177),
	id-PrimaryCPICH-Information-Cell-SetupRqstFDD				PrimaryCPICH-Information-Cell-SetupRqstFDD,			--	(178),
	id-PrimarySCH-Information-Cell-ReconfRqstFDD				PrimarySCH-Information-Cell-ReconfRqstFDD,			--	(179),
	id-PrimarySCH-Information-Cell-SetupRqstFDD					PrimarySCH-Information-Cell-SetupRqstFDD,			--	(180),
	id-PrimaryScramblingCode									PrimaryScramblingCode,								--	(181),
	id-SCH-Information-Cell-ReconfRqstTDD						SCH-Information-Cell-ReconfRqstTDD,					--	(183),
	id-SCH-Information-Cell-SetupRqstTDD						SCH-Information-Cell-SetupRqstTDD,					--	(184),
	id-PUSCH-Information-AddListIE-PSCH-ReconfRqst				PUSCH-Information-AddItem-PSCH-ReconfRqst,			--	(185),
	id-PUSCH-Information-ModifyListIE-PSCH-ReconfRqst			PUSCH-Information-ModifyItem-PSCH-ReconfRqst,		--	(186),
	id-PUSCHSets-AddList-PSCH-ReconfRqst						PUSCHSets-AddList-PSCH-ReconfRqst,					--	(187),
	id-PUSCHSets-DeleteList-PSCH-ReconfRqst						PUSCHSets-DeleteList-PSCH-ReconfRqst,				--	(188),
	id-PUSCHSets-ModifyList-PSCH-ReconfRqst						PUSCHSets-ModifyList-PSCH-ReconfRqst,				--	(189),
	id-RACH-Information											Common-TransportChannel-Status-Information,			--	(190),
	id-RACH-ParametersItem-CTCH-SetupRqstFDD					RACH-ParametersItem-CTCH-SetupRqstFDD,				--	(196),
	id-RACH-ParameterItem-CTCH-SetupRqstTDD						RACH-ParameterItem-CTCH-SetupRqstTDD,				--	(197),
	id-ReportCharacteristics									ReportCharacteristics,								--	(198),
	id-Reporting-Object-RL-FailureInd							Reporting-Object-RL-FailureInd,						--	(199),
	id-Reporting-Object-RL-RestoreInd							Reporting-Object-RL-RestoreInd,						--	(200),
	id-RL-InformationItem-DM-Rprt								RL-InformationItem-DM-Rprt,							--	(202),
	id-RL-InformationItem-DM-Rqst								RL-InformationItem-DM-Rqst,							--	(203),
	id-RL-InformationItem-DM-Rsp								RL-InformationItem-DM-Rsp,							--	(204),
	id-RL-InformationItem-RL-AdditionRqstFDD					RL-InformationItem-RL-AdditionRqstFDD,				--	(205),
	id-RL-informationItem-RL-DeletionRqst						RL-informationItem-RL-DeletionRqst,					--	(206),
	id-RL-InformationItem-RL-FailureInd							RL-InformationItem-RL-FailureInd,					--	(207),
	id-RL-InformationItem-RL-PreemptRequiredInd					RL-InformationItem-RL-PreemptRequiredInd,			--	(286),
	id-RL-InformationItem-RL-ReconfPrepFDD						RL-InformationItem-RL-ReconfPrepFDD,				--	(208),
	id-RL-InformationItem-RL-ReconfRqstFDD						RL-InformationItem-RL-ReconfPrepFDD,				--	(209),
	id-RL-InformationItem-RL-RestoreInd							RL-InformationItem-RL-RestoreInd,					--	(210),
	id-RL-InformationItem-RL-SetupRqstFDD						RL-InformationItem-RL-SetupRqstFDD,				--	(211),
	id-RL-InformationList-RL-AdditionRqstFDD					RL-InformationList-RL-AdditionRqstFDD,			--	(212),
	id-RL-informationList-RL-DeletionRqst						RL-informationList-RL-DeletionRqst,				--	(213),
	id-RL-InformationList-RL-PreemptRequiredInd					RL-InformationList-RL-PreemptRequiredInd,		--	(237),
	id-RL-InformationList-RL-ReconfPrepFDD						RL-InformationList-RL-ReconfPrepFDD,			--	(214),
	id-RL-InformationList-RL-ReconfRqstFDD						RL-InformationList-RL-ReconfRqstFDD,			--	(215),
	id-RL-InformationList-RL-SetupRqstFDD						RL-InformationList-RL-SetupRqstFDD,				--	(216),
	id-RL-InformationResponseItem-RL-AdditionRspFDD				RL-InformationResponseItem-RL-AdditionRspFDD,	--	(217),
	id-RL-InformationResponseItem-RL-ReconfReady				RL-InformationResponseItem-RL-ReconfReady,		--	(218),
	id-RL-InformationResponseItem-RL-ReconfRsp					RL-InformationResponseItem-RL-ReconfRsp,		--	(219),
	id-RL-InformationResponseItem-RL-SetupRspFDD				RL-InformationResponseItem-RL-SetupRspFDD,		--	(220),
	id-RL-InformationResponseList-RL-AdditionRspFDD				RL-InformationResponseList-RL-AdditionRspFDD,	--	(221),
	id-RL-InformationResponseList-RL-ReconfReady				RL-InformationResponseList-RL-ReconfReady,		--	(222),
	id-RL-InformationResponseList-RL-ReconfRsp					RL-InformationResponseList-RL-ReconfRsp,		--	(223),
	id-RL-InformationResponseList-RL-SetupRspFDD				RL-InformationResponseList-RL-SetupRspFDD,		--	(224),
	id-RL-InformationResponse-RL-AdditionRspTDD					RL-InformationResponse-RL-AdditionRspTDD,		--	(225),
	id-RL-InformationResponse-RL-SetupRspTDD					RL-InformationResponse-RL-SetupRspTDD,			--	(226),
	id-RL-Information-RL-AdditionRqstTDD						RL-Information-RL-AdditionRqstTDD,				--	(227),
	id-RL-Information-RL-ReconfRqstTDD							RL-Information-RL-ReconfRqstTDD,				--	(228),
	id-RL-Information-RL-ReconfPrepTDD							RL-Information-RL-ReconfPrepTDD,				--	(229),
	id-RL-Information-RL-SetupRqstTDD							RL-Information-RL-SetupRqstTDD,					--	(230),
	id-RL-ReconfigurationFailureItem-RL-ReconfFailure			RL-ReconfigurationFailureItem-RL-ReconfFailure,	--	(236),
	id-RL-Set-InformationItem-DM-Rprt							RL-Set-InformationItem-DM-Rprt,					--	(238),
	id-RL-Set-InformationItem-DM-Rsp							RL-Set-InformationItem-DM-Rsp,					--	(240),
	id-RL-Set-InformationItem-RL-FailureInd						RL-Set-InformationItem-RL-FailureInd,			--	(241),
	id-RL-Set-InformationItem-RL-RestoreInd						RL-Set-InformationItem-RL-RestoreInd,			--	(242),
	id-S-CCPCH-Information										Common-PhysicalChannel-Status-Information,		--	(247),
	id-S-CPICH-Information										Common-PhysicalChannel-Status-Information,		--	(249),
	id-SCH-Information											Common-PhysicalChannel-Status-Information,		--	(251),
	id-S-SCH-Information										Common-PhysicalChannel-Status-Information,		--	(253),
	id-Secondary-CCPCHListIE-CTCH-ReconfRqstTDD					Secondary-CCPCHListIE-CTCH-ReconfRqstTDD,		--	(257),
	id-Secondary-CCPCH-parameterListIE-CTCH-SetupRqstTDD		Secondary-CCPCH-parameterListIE-CTCH-SetupRqstTDD,	--	(258),
	id-Secondary-CCPCH-Parameters-CTCH-ReconfRqstTDD			Secondary-CCPCH-Parameters-CTCH-ReconfRqstTDD,		--	(259),
	id-SecondaryCPICH-InformationItem-Cell-ReconfRqstFDD		SecondaryCPICH-InformationItem-Cell-ReconfRqstFDD,	--	(260),
	id-SecondaryCPICH-InformationItem-Cell-SetupRqstFDD			SecondaryCPICH-InformationItem-Cell-SetupRqstFDD,	--	(261),
	id-SecondaryCPICH-InformationList-Cell-ReconfRqstFDD		SecondaryCPICH-InformationList-Cell-ReconfRqstFDD,	--	(262),
	id-SecondaryCPICH-InformationList-Cell-SetupRqstFDD			SecondaryCPICH-InformationList-Cell-SetupRqstFDD,	--	(263),
	id-SecondarySCH-Information-Cell-ReconfRqstFDD				SecondarySCH-Information-Cell-ReconfRqstFDD,		--	(264),
	id-SecondarySCH-Information-Cell-SetupRqstFDD				SecondarySCH-Information-Cell-SetupRqstFDD,			--	(265),
	id-SegmentInformationListIE-SystemInfoUpdate				SegmentInformationListIE-SystemInfoUpdate,			--	(266),
	id-SFN															SFN,											--		(268),
	id-SignallingBearerRequestIndicator								SignallingBearerRequestIndicator,				--	(138),
	id-ShutdownTimer												ShutdownTimer,									--	(269),		
	id-Start-Of-Audit-Sequence-Indicator							Start-Of-Audit-Sequence-Indicator,				--	(114),
	id-Successful-RL-InformationRespItem-RL-AdditionFailureFDD		Successful-RL-InformationRespItem-RL-AdditionFailureFDD,	--	(270),
	id-Successful-RL-InformationRespItem-RL-SetupFailureFDD			Successful-RL-InformationRespItem-RL-SetupFailureFDD,		--	(271),
	id-SyncCase														SyncCase,										--	(274),
	id-SyncCaseIndicatorItem-Cell-SetupRqstTDD-PSCH					SyncCaseIndicatorItem-Cell-SetupRqstTDD-PSCH,	--	(275),
	id-T-Cell														T-Cell,											--	(276),
	id-TargetCommunicationControlPortID								CommunicationControlPortID,				--	(139),
	id-TimeSlotConfigurationList-Cell-ReconfRqstTDD					TimeSlotConfigurationList-Cell-ReconfRqstTDD,	--	(277),
	id-TimeSlotConfigurationList-Cell-SetupRqstTDD					TimeSlotConfigurationList-Cell-SetupRqstTDD,	--	(278),
	id-TransmissionDiversityApplied									TransmissionDiversityApplied,					--	(279),
	id-TypeOfError													TypeOfError,									--	(508),
	id-UARFCNforNt													UARFCN,											--	(280),
	id-UARFCNforNd													UARFCN,											--	(281),
	id-UARFCNforNu													UARFCN,									--	(282),
	id-UL-CCTrCH-InformationItem-RL-SetupRqstTDD					UL-CCTrCH-InformationItem-RL-SetupRqstTDD,		--	(284),
	id-UL-CCTrCH-InformationList-RL-AdditionRqstTDD					UL-CCTrCH-InformationList-RL-SetupRqstTDD,		--	(285),
	id-UL-CCTrCH-InformationList-RL-SetupRqstTDD					UL-CCTrCH-InformationList-RL-SetupRqstTDD,		--	(288),
	id-UL-DPCH-InformationItem-RL-AdditionRqstTDD					UL-DPCH-InformationItem-RL-AdditionRqstTDD,		--	(289),
	id-UL-DPCH-InformationList-RL-SetupRqstTDD						UL-DPCH-InformationItem-RL-SetupRqstTDD,		--	(291),
	id-UL-DPCH-Information-RL-ReconfPrepFDD							UL-DPCH-Information-RL-ReconfPrepFDD,			--	(293),
	id-UL-DPCH-Information-RL-ReconfRqstFDD							UL-DPCH-Information-RL-ReconfRqstFDD,			--	(294),
	id-UL-DPCH-Information-RL-SetupRqstFDD							UL-DPCH-Information-RL-SetupRqstFDD,			--	(295),
	id-Unsuccessful-RL-InformationRespItem-RL-AdditionFailureFDD	Unsuccessful-RL-InformationRespItem-RL-AdditionFailureFDD,	--	(296),
	id-Unsuccessful-RL-InformationRespItem-RL-SetupFailureFDD		Unsuccessful-RL-InformationRespItem-RL-SetupFailureFDD,		--	(297),
	id-Unsuccessful-RL-InformationResp-RL-AdditionFailureTDD		Unsuccessful-RL-InformationResp-RL-AdditionFailureTDD,		--	(300),
	id-Unsuccessful-RL-InformationResp-RL-SetupFailureTDD			Unsuccessful-RL-InformationResp-RL-SetupFailureTDD,			--	(301),
	id-USCH-Information-Add											USCH-Information,								--	(302),
	id-USCH-Information-DeleteList-RL-ReconfPrepTDD					USCH-Information-DeleteList-RL-ReconfPrepTDD,	--	(304),
	id-USCH-Information-ModifyList-RL-ReconfPrepTDD					USCH-Information-ModifyList-RL-ReconfPrepTDD,	--	(306),
	id-USCH-InformationResponse										USCH-InformationResponse,						--	(309),
	id-USCH-Information												USCH-Information,								--	(310),
	id-USCH-RearrangeList-Bearer-RearrangeInd						USCH-RearrangeList-Bearer-RearrangeInd,			--	(141),
	id-Active-Pattern-Sequence-Information 							Active-Pattern-Sequence-Information,			--	(315),
	id-AICH-ParametersListIE-CTCH-ReconfRqstFDD						AICH-ParametersListIE-CTCH-ReconfRqstFDD,		--	(316),
	id-AdjustmentRatio												ScaledAdjustmentRatio,								--	(317),
--  id-Not-Used-320														(320),
--  id-Not-Used-322														(322),
	id-FACH-ParametersListIE-CTCH-ReconfRqstFDD						FACH-ParametersListIE-CTCH-ReconfRqstFDD,		--	(323),
	id-CauseLevel-PSCH-ReconfFailure								CauseLevel-PSCH-ReconfFailure,					--	(324),
	id-CauseLevel-RL-AdditionFailureFDD								CauseLevel-RL-AdditionFailureFDD,				--	(325),
	id-CauseLevel-RL-AdditionFailureTDD								CauseLevel-RL-AdditionFailureTDD,				--	(326),
	id-CauseLevel-RL-ReconfFailure									CauseLevel-RL-ReconfFailure,					--	(327),
	id-CauseLevel-RL-SetupFailureFDD								CauseLevel-RL-SetupFailureFDD,					--	(328),
	id-CauseLevel-RL-SetupFailureTDD								CauseLevel-RL-SetupFailureTDD,					--	(329),
--  id-Not-Used-330														(330),
--  id-Not-Used-332														(332),
	id-Closed-Loop-Timing-Adjustment-Mode							Closedlooptimingadjustmentmode,					--	(333),
	id-CommonPhysicalChannelType-CTCH-ReconfRqstFDD					CommonPhysicalChannelType-CTCH-ReconfRqstFDD,	--	(334),
	id-Compressed-Mode-Deactivation-Flag							Compressed-Mode-Deactivation-Flag,				--	(335),
--  id-Not-Used-336														(336),
--  id-Not-Used-342														(342),
--  id-Not-Used-343														(343),
	id-DL-CCTrCH-InformationAddList-RL-ReconfPrepTDD				DL-CCTrCH-InformationAddList-RL-ReconfPrepTDD,				--	(346),
	id-DL-CCTrCH-InformationDeleteItem-RL-ReconfRqstTDD				DL-CCTrCH-InformationDeleteItem-RL-ReconfRqstTDD,			--	(347),
	id-DL-CCTrCH-InformationDeleteList-RL-ReconfPrepTDD				DL-CCTrCH-InformationDeleteList-RL-ReconfPrepTDD,			--	(348),
	id-DL-CCTrCH-InformationDeleteList-RL-ReconfRqstTDD				DL-CCTrCH-InformationDeleteList-RL-ReconfRqstTDD,			--	(349),
	id-DL-CCTrCH-InformationModifyItem-RL-ReconfRqstTDD				DL-CCTrCH-InformationModifyItem-RL-ReconfRqstTDD,			--	(350),
	id-DL-CCTrCH-InformationModifyList-RL-ReconfPrepTDD				DL-CCTrCH-InformationModifyList-RL-ReconfPrepTDD,			--	(351),
	id-DL-CCTrCH-InformationModifyList-RL-ReconfRqstTDD				DL-CCTrCH-InformationModifyList-RL-ReconfRqstTDD,			--	(352),
	id-DL-DPCH-InformationAddListIE-RL-ReconfPrepTDD				DL-DPCH-InformationAddItem-RL-ReconfPrepTDD,				--	(353),
	id-DL-DPCH-InformationModify-AddListIE-RL-ReconfPrepTDD			DL-DPCH-InformationModify-AddItem-RL-ReconfPrepTDD,			--	(355),
	id-DL-DPCH-InformationModify-DeleteListIE-RL-ReconfPrepTDD		DL-DPCH-InformationModify-DeleteItem-RL-ReconfPrepTDD,		--	(356),
	id-DL-DPCH-InformationModify-ModifyListIE-RL-ReconfPrepTDD		DL-DPCH-InformationModify-ModifyItem-RL-ReconfPrepTDD,		--	(357),
	id-DL-TPC-Pattern01Count 										DL-TPC-Pattern01Count,										--	(358),
	id-DPC-Mode														DPC-Mode,													--	(450),
	id-DPCHConstant													ConstantValue,												--	(359),
--	id-Unused-ProtocolIE-ID-94											(94),
--  id-Unused-ProtocolIE-ID-110											(110),
--  id-Unused-ProtocolIE-ID-111											(111),
	id-FACH-ParametersList-CTCH-SetupRsp							FACH-CommonTransportChannel-InformationResponse,			--	(362),
	id-Limited-power-increase-information-Cell-SetupRqstFDD			Limited-power-increase-information-Cell-SetupRqstFDD,		--	(369),
	id-PCH-Parameters-CTCH-SetupRsp									CommonTransportChannel-InformationResponse,					--	(374),
	id-PCH-ParametersItem-CTCH-ReconfRqstFDD						PCH-ParametersItem-CTCH-ReconfRqstFDD,						--	(375),
--  id-Not-Used-376														(376),
	id-PICH-ParametersItem-CTCH-ReconfRqstFDD						PICH-ParametersItem-CTCH-ReconfRqstFDD,						--	(380),
	id-PRACHConstant												ConstantValue,												--	(381),
	id-PRACH-ParametersListIE-CTCH-ReconfRqstFDD					PRACH-ParametersListIE-CTCH-ReconfRqstFDD,					--	(383),
	id-PUSCHConstant												ConstantValue,												--	(384),
	id-RACH-Parameters-CTCH-SetupRsp								CommonTransportChannel-InformationResponse,					--	(385),
--  id-Unused-ProtocolIE-ID-443											(443),
	id-Synchronisation-Configuration-Cell-ReconfRqst				Synchronisation-Configuration-Cell-ReconfRqst,				--	(393),
	id-Synchronisation-Configuration-Cell-SetupRqst					Synchronisation-Configuration-Cell-SetupRqst,				--	(394),
	id-Transmission-Gap-Pattern-Sequence-Information				Transmission-Gap-Pattern-Sequence-Information,				--	(395),
	id-UL-CCTrCH-InformationAddList-RL-ReconfPrepTDD				UL-CCTrCH-InformationAddList-RL-ReconfPrepTDD,				--	(396),
	id-UL-CCTrCH-InformationDeleteItem-RL-ReconfRqstTDD				UL-CCTrCH-InformationDeleteItem-RL-ReconfRqstTDD,			--	(397),
	id-UL-CCTrCH-InformationDeleteList-RL-ReconfPrepTDD				UL-CCTrCH-InformationDeleteList-RL-ReconfPrepTDD,			--	(398),
	id-UL-CCTrCH-InformationDeleteList-RL-ReconfRqstTDD				UL-CCTrCH-InformationDeleteList-RL-ReconfRqstTDD,			--	(399),
	id-UL-CCTrCH-InformationModifyItem-RL-ReconfRqstTDD				UL-CCTrCH-InformationModifyItem-RL-ReconfRqstTDD,			--	(400),
	id-UL-CCTrCH-InformationModifyList-RL-ReconfPrepTDD				UL-CCTrCH-InformationModifyList-RL-ReconfPrepTDD,			--	(401),
	id-UL-CCTrCH-InformationModifyList-RL-ReconfRqstTDD				UL-CCTrCH-InformationModifyList-RL-ReconfRqstTDD,			--	(402),
	id-UL-DPCH-InformationAddListIE-RL-ReconfPrepTDD				UL-DPCH-InformationAddItem-RL-ReconfPrepTDD,				--	(403),
	id-UL-DPCH-InformationModify-AddListIE-RL-ReconfPrepTDD			UL-DPCH-InformationModify-AddItem-RL-ReconfPrepTDD,			--	(405),
	id-UL-DPCH-InformationModify-DeleteListIE-RL-ReconfPrepTDD		UL-DPCH-InformationModify-DeleteListIE-RL-ReconfPrepTDD,	--	(406),
	id-UL-DPCH-InformationModify-ModifyListIE-RL-ReconfPrepTDD		UL-DPCH-InformationModify-ModifyItem-RL-ReconfPrepTDD,		--	(407),
	id-Unsuccessful-PDSCHSetItem-PSCH-ReconfFailureTDD				Unsuccessful-PDSCHSetItem-PSCH-ReconfFailureTDD,			--	(408),
	id-Unsuccessful-PUSCHSetItem-PSCH-ReconfFailureTDD				Unsuccessful-PUSCHSetItem-PSCH-ReconfFailureTDD,			--	(409),
	id-CommunicationContextInfoItem-Reset							CommunicationContextInfoItem-Reset,							--	(412),
	id-CommunicationControlPortInfoItem-Reset						CommunicationControlPortInfoItem-Reset,						--	(414),
	id-ResetIndicator												ResetIndicator,	--	(416),
--  id-Unused-ProtocolIE-ID-417											(417),
--  id-Unused-ProtocolIE-ID-418											(418),
--  id-Unused-ProtocolIE-ID-419											(419),
--  id-Unused-ProtocolIE-ID-142											(142),
	id-TimingAdvanceApplied											TimingAdvanceApplied,										--	(287),
	id-CFNReportingIndicator										FNReportingIndicator,										--	(6),
	id-SFNReportingIndicator										FNReportingIndicator,										--	(11),
	id-InnerLoopDLPCStatus											InnerLoopDLPCStatus,										--	(12),
	id-TimeslotISCPInfo												DL-TimeslotISCPInfo,										--	(283),
	id-PICH-ParametersItem-CTCH-SetupRqstTDD						PICH-ParametersItem-CTCH-SetupRqstTDD,						--	(167),
	id-PRACH-ParametersItem-CTCH-SetupRqstTDD						PRACH-ParametersItem-CTCH-SetupRqstTDD,						--	(20),
	id-CCTrCH-InformationItem-RL-FailureInd							CCTrCH-InformationItem-RL-FailureInd,						--	(46),
	id-CCTrCH-InformationItem-RL-RestoreInd							CCTrCH-InformationItem-RL-RestoreInd,							--	(47),
	id-CauseLevel-SyncAdjustmntFailureTDD							CauseLevel-SyncAdjustmntFailureTDD,							--	(420),
	id-CellAdjustmentInfo-SyncAdjustmntRqstTDD						CellAdjustmentInfo-SyncAdjustmentRqstTDD,					--	(421),
	id-CellAdjustmentInfoItem-SyncAdjustmentRqstTDD					CellAdjustmentInfoItem-SyncAdjustmentRqstTDD,				--	(494),
	id-CellSyncBurstInfoList-CellSyncReconfRqstTDD					CellSyncBurstInfoList-CellSyncReconfRqstTDD,				--	(482),
	id-CellSyncBurstTransInit-CellSyncInitiationRqstTDD				CellSyncBurstTransInit-CellSyncInitiationRqstTDD,			--	(422),
	id-CellSyncBurstMeasureInit-CellSyncInitiationRqstTDD			CellSyncBurstMeasureInit-CellSyncInitiationRqstTDD,			--	(423),
--	id-CellSyncBurstTransReconfiguration-CellSyncReconfRqstTDD		CellSyncBurstTransReconfiguration-CellSyncReconfRqstTDD,		(424),
	id-CellSyncBurstMeasReconfiguration-CellSyncReconfRqstTDD		CellSyncBurstMeasInfo-CellSyncReconfRqstTDD,				--	(425),
--	id-CellSyncBurstTransInfoList-CellSyncReconfRqstTDD				CellSyncBurstTransInfoList-CellSyncReconfRqstTDD,				(426),
	id-CellSyncBurstMeasInfoList-CellSyncReconfRqstTDD				CellSyncBurstMeasInfoList-CellSyncReconfRqstTDD,			--	(427),
	id-CellSyncBurstTransReconfInfo-CellSyncReconfRqstTDD			CellSyncBurstTransReconfInfo-CellSyncReconfRqstTDD,			--	(428),
	id-CellSyncInfo-CellSyncReprtTDD								CellSyncInfo-CellSyncReprtTDD,								--	(429),
	id-CSBTransmissionID											CSBTransmissionID,											--	(430),
	id-CSBMeasurementID												CSBMeasurementID,											--	(431),
--	id-IntStdPhCellSyncInfoItem-CellSyncReprtTDD					IntStdPhCellSyncInfoItem-CellSyncReprtTDD,						(432),
	id-NCyclesPerSFNperiod 											NCyclesPerSFNperiod,										--	(433),
	id-NRepetitionsPerCyclePeriod									NRepetitionsPerCyclePeriod,									--	(434),
	id-SyncFrameNumber												SyncFrameNumber,											--	(437),
	id-SynchronisationReportType									SynchronisationReportType,									--	(438),
	id-SynchronisationReportCharacteristics							SynchronisationReportCharacteristics,						--	(439),
	id-Unsuccessful-cell-InformationRespItem-SyncAdjustmntFailureTDD	Unsuccessful-cell-InformationRespItem-SyncAdjustmntFailureTDD, --	(440),
--	id-LateEntranceCellSyncInfoItem-CellSyncReprtTDD				LateEntranceCellSyncInfoItem-CellSyncReprtTDD,					(119),
	id-ReferenceClockAvailability									ReferenceClockAvailability,									--	(435),
	id-ReferenceSFNoffset											ReferenceSFNoffset,											--	(436),
	id-InformationExchangeID										InformationExchangeID,										--	(444),
	id-InformationExchangeObjectType-InfEx-Rqst						InformationExchangeObjectType-InfEx-Rqst,					--	(445),
	id-InformationType												InformationReportCharacteristics,							--	(446),
	id-InformationReportCharacteristics								InformationReportCharacteristics,							--	(447),
	id-InformationExchangeObjectType-InfEx-Rsp						InformationExchangeObjectType-InfEx-Rsp,					--	(448),
	id-InformationExchangeObjectType-InfEx-Rprt						InformationExchangeObjectType-InfEx-Rprt,					--	(449),
	id-IPDLParameter-Information-Cell-ReconfRqstFDD					IPDLParameter-Information-Cell-ReconfRqstFDD,				--	(451),
	id-IPDLParameter-Information-Cell-SetupRqstFDD					IPDLParameter-Information-Cell-SetupRqstFDD,				--	(452),
	id-IPDLParameter-Information-Cell-ReconfRqstTDD					IPDLParameter-Information-Cell-SetupRqstTDD,				--	(453),
	id-IPDLParameter-Information-Cell-SetupRqstTDD					IPDLParameter-Information-Cell-SetupRqstTDD,				--	(454),
	id-DL-DPCH-LCR-Information-RL-SetupRqstTDD						DL-DPCH-LCR-Information-RL-SetupRqstTDD,					--	(74),
	id-DwPCH-LCR-Information										Common-PhysicalChannel-Status-Information,										--	(78),
	id-DwPCH-LCR-InformationList-AuditRsp                   		Common-PhysicalChannel-Status-Information,							--	(90),
	id-DwPCH-LCR-Information-Cell-SetupRqstTDD                   	DwPCH-LCR-Information-Cell-SetupRqstTDD,					--	(97),
	id-DwPCH-LCR-Information-Cell-ReconfRqstTDD						DwPCH-LCR-Information-Cell-ReconfRqstTDD,					--	(99),
	id-DwPCH-LCR-Information-ResourceStatusInd						DwPCH-LCR-Information-ResourceStatusInd,					--	(101),
	id-maxFACH-Power-LCR-CTCH-SetupRqstTDD                   		DL-Power,													--	(154),
	id-maxFACH-Power-LCR-CTCH-ReconfRqstTDD                   		DL-Power,													--	(174),
	id-FPACH-LCR-Information										Common-PhysicalChannel-Status-Information,					--	(290),
	id-FPACH-LCR-Information-AuditRsp                   			Common-PhysicalChannel-Status-Information,					--	(292),
	id-FPACH-LCR-InformationList-AuditRsp                   		FPACH-LCR-InformationList-AuditRsp,							--	(22),
	id-FPACH-LCR-InformationList-ResourceStatusInd                  FPACH-LCR-InformationList-ResourceStatusInd,				-- 	(311),
	id-FPACH-LCR-Parameters-CTCH-SetupRqstTDD                   	FPACH-LCR-Parameters-CTCH-SetupRqstTDD,						--	(312),
	id-FPACH-LCR-Parameters-CTCH-ReconfRqstTDD                   	FPACH-LCR-Parameters-CTCH-ReconfRqstTDD,					--	(314),
	id-PCCPCH-LCR-Information-Cell-SetupRqstTDD                   	PCCPCH-LCR-Information-Cell-SetupRqstTDD,					--	(456),
	id-PCH-Power-LCR-CTCH-SetupRqstTDD								DL-Power,													--	(457),
	id-PCH-Power-LCR-CTCH-ReconfRqstTDD								DL-Power,													--	(458),
	id-PICH-LCR-Parameters-CTCH-SetupRqstTDD                   		PICH-LCR-Parameters-CTCH-SetupRqstTDD,						--	(459),
	id-PRACH-LCR-ParametersList-CTCH-SetupRqstTDD                  	PRACH-LCR-ParametersList-CTCH-SetupRqstTDD,					--	(461),
	id-RL-InformationResponse-LCR-RL-SetupRspTDD	                RL-InformationResponse-LCR-RL-SetupRspTDD,					--   	(463),
	id-Secondary-CCPCH-LCR-parameterList-CTCH-SetupRqstTDD          Secondary-CCPCH-LCR-parameterList-CTCH-SetupRqstTDD,		--    (465),
	id-TimeSlot														TimeSlot,													--	(495),
	id-TimeSlotConfigurationList-LCR-Cell-ReconfRqstTDD             TimeSlotConfigurationList-LCR-Cell-ReconfRqstTDD,			--   (466),
	id-TimeSlotConfigurationList-LCR-Cell-SetupRqstTDD              TimeSlotConfigurationList-LCR-Cell-SetupRqstTDD,			--   (467),
	id-TimeslotISCP-LCR-InfoList-RL-SetupRqstTDD                   	DL-TimeslotISCPInfoLCR,										--	(468),
	id-TimeSlotLCR-CM-Rqst                   						TimeSlotLCR,												--	(469),
	id-UL-DPCH-LCR-Information-RL-SetupRqstTDD                   	UL-DPCH-LCR-Information-RL-SetupRqstTDD,					--	(470),
	id-DL-DPCH-InformationItem-LCR-RL-AdditionRqstTDD				DL-DPCH-InformationItem-LCR-RL-AdditionRqstTDD,				--	(472),
	id-UL-DPCH-InformationItem-LCR-RL-AdditionRqstTDD				UL-DPCH-InformationItem-LCR-RL-AdditionRqstTDD,				--	(473),
	id-TimeslotISCP-InformationList-LCR-RL-AdditionRqstTDD			DL-TimeslotISCPInfoLCR,										--	(474),
	id-DL-DPCH-LCR-InformationAddList-RL-ReconfPrepTDD				DL-DPCH-LCR-InformationAddList-RL-ReconfPrepTDD,			--	(475),
	id-DL-DPCH-LCR-InformationModify-AddList-RL-ReconfPrepTDD		DL-DPCH-LCR-InformationModify-AddList-RL-ReconfPrepTDD,		--	(477),
	id-DL-Timeslot-LCR-InformationModify-ModifyList-RL-ReconfPrepTDD	DL-Timeslot-LCR-InformationModify-ModifyList-RL-ReconfPrepTDD,	--	(479),
	id-TimeslotISCPInfoList-LCR-DL-PC-RqstTDD						DL-TimeslotISCPInfoLCR,										--	(480),
	id-UL-DPCH-LCR-InformationAddListIE-RL-ReconfPrepTDD			UL-DPCH-LCR-InformationAddList-RL-ReconfPrepTDD,			--	(481),
	id-UL-DPCH-LCR-InformationModify-AddList						UL-DPCH-LCR-InformationModify-AddList-RL-ReconfPrepTDD,		--	(483),
	id-UL-TimeslotLCR-Information-RL-ReconfPrepTDD					UL-TimeslotLCR-InformationModify-ModifyList-RL-ReconfPrepTDD,	--	(485),
	id-UL-SIRTarget													UL-SIR,														--	(510),
	id-PDSCH-AddInformation-LCR-PSCH-ReconfRqst						PDSCH-AddInformation-LCR-AddItem-PSCH-ReconfRqst,			--	(486),
--	id-PDSCH-AddInformation-LCR-AddListIE-PSCH-ReconfRqst			PDSCH-AddInformation-LCR-AddListIE-PSCH-ReconfRqst,				(487),
--  id-Unused-ProtocolIE-ID-26											( 26),
--  id-Unused-ProtocolIE-ID-27											( 27),
	id-PDSCH-ModifyInformation-LCR-PSCH-ReconfRqst					PDSCH-ModifyInformation-LCR-ModifyItem-PSCH-ReconfRqst,		--	(488),
--	id-PDSCH-ModifyInformation-LCR-ModifyListIE-PSCH-ReconfRqst			(489),
	id-PUSCH-AddInformation-LCR-PSCH-ReconfRqst						PUSCH-AddInformation-LCR-AddItem-PSCH-ReconfRqst,			--	(490),
--  id-PUSCH-AddInformation-LCR-AddListIE-PSCH-ReconfRqst				(491),
	id-PUSCH-ModifyInformation-LCR-PSCH-ReconfRqst					PUSCH-ModifyInformation-LCR-ModifyItem-PSCH-ReconfRqst,		--	(492),
--  id-PUSCH-ModifyInformation-LCR-ModifyListIE-PSCH-ReconfRqst			(493),
	id-timeslotInfo-CellSyncInitiationRqstTDD						TimeslotInfo-CellSyncInitiationRqstTDD,						--	(496),
	id-SyncReportType-CellSyncReprtTDD								SyncReportType-CellSyncReprtTDD,							--	(497),
	id-Power-Local-Cell-Group-InformationItem-AuditRsp				Power-Local-Cell-Group-InformationItem-AuditRsp,			--	(498),
	id-Power-Local-Cell-Group-InformationItem-ResourceStatusInd		Power-Local-Cell-Group-InformationItem-ResourceStatusInd,	--	(499),
	id-Power-Local-Cell-Group-InformationItem2-ResourceStatusInd	Power-Local-Cell-Group-InformationItem2-ResourceStatusInd,	--	(500),
	id-Power-Local-Cell-Group-InformationList-AuditRsp				Power-Local-Cell-Group-InformationList-AuditRsp,			--	(501),
	id-Power-Local-Cell-Group-InformationList-ResourceStatusInd		Power-Local-Cell-Group-InformationList-ResourceStatusInd,	--	(502),
	id-Power-Local-Cell-Group-InformationList2-ResourceStatusInd	Power-Local-Cell-Group-InformationList2-ResourceStatusInd,	--	(503),
	id-Power-Local-Cell-Group-ID									Local-Cell-ID,												--	(504),
	id-PUSCH-Info-DM-Rqst											PUSCH-Info-DM-Rqst,											--	(505),
	id-PUSCH-Info-DM-Rsp											PUSCH-Info-DM-Rsp,											--	(506),
	id-PUSCH-Info-DM-Rprt											PUSCH-Info-DM-Rprt,											--	(507),
	id-InitDL-Power													DL-Power,												--	(509),
	id-cellSyncBurstRepetitionPeriod								CellSyncBurstRepetitionPeriod,								--	(511),
	id-ReportCharacteristicsType-OnModification						ReportCharacteristicsType-OnModification,					--	(512),
	id-SFNSFNMeasurementValueInformation							SFNSFNMeasurementValueInformation,							--	(513),
	id-SFNSFNMeasurementThresholdInformation						SFNSFNMeasurementThresholdInformation,						--	(514),
	id-TUTRANGPSMeasurementValueInformation							TUTRANGPSMeasurementValueInformation,						--	(515),
	id-TUTRANGPSMeasurementThresholdInformation						TUTRANGPSMeasurementThresholdInformation,					--	(516),
	id-Rx-Timing-Deviation-Value-LCR								Rx-Timing-Deviation-Value-LCR,								--	(520),
	id-RL-InformationResponse-LCR-RL-AdditionRspTDD					RL-InformationResponse-LCR-RL-AdditionRspTDD,				--	(51),
	id-DL-PowerBalancing-Information								DL-PowerBalancing-Information,								--	(28),
	id-DL-PowerBalancing-ActivationIndicator						DL-PowerBalancing-ActivationIndicator,						--	(29),
	id-DL-PowerBalancing-UpdatedIndicator							DL-PowerBalancing-UpdatedIndicator,							--	(30),
	id-CCTrCH-Initial-DL-Power-RL-SetupRqstTDD						DL-Power,													--	(517),
	id-CCTrCH-Initial-DL-Power-RL-AdditionRqstTDD					DL-Power,													--	(518),
	id-CCTrCH-Initial-DL-Power-RL-ReconfPrepTDD						DL-Power,													--	(519),
	id-IPDLParameter-Information-LCR-Cell-SetupRqstTDD				IPDLParameter-Information-LCR-Cell-SetupRqstTDD,			--	(41),
	id-IPDLParameter-Information-LCR-Cell-ReconfRqstTDD 			IPDLParameter-Information-LCR-Cell-ReconfRqstTDD,			--	(42),
	id-HS-PDSCH-HS-SCCH-E-AGCH-E-RGCH-E-HICH-MaxPower-PSCH-ReconfRqst	MaximumTransmissionPower,								--	(522),
	id-HS-PDSCH-HS-SCCH-ScramblingCode-PSCH-ReconfRqst				DL-ScramblingCode,											--	(523),
	id-HS-PDSCH-FDD-Code-Information-PSCH-ReconfRqst				HS-PDSCH-FDD-Code-Information,								--	(524),
	id-HS-SCCH-FDD-Code-Information-PSCH-ReconfRqst					HS-SCCH-FDD-Code-Information,								--	(525),
	id-HS-PDSCH-TDD-Information-PSCH-ReconfRqst						HS-PDSCH-TDD-Information-PSCH-ReconfRqst,					--	(526),
	id-Add-To-HS-SCCH-Resource-Pool-PSCH-ReconfRqst					Add-To-HS-SCCH-Resource-Pool-PSCH-ReconfRqst,				--	(527),
	id-Modify-HS-SCCH-Resource-Pool-PSCH-ReconfRqst					Modify-HS-SCCH-Resource-Pool-PSCH-ReconfRqst,				--	(528),
	id-Delete-From-HS-SCCH-Resource-Pool-PSCH-ReconfRqst			Delete-From-HS-SCCH-Resource-Pool-PSCH-ReconfRqst,			--	(529),
	id-bindingID													BindingID,													--	(102),
	id-RL-Specific-DCH-Info											RL-Specific-DCH-Info,										--	(103),
	id-transportlayeraddress 										TransportLayerAddress,										--	(104),
	id-DelayedActivation 											DelayedActivation,											--	(231),
	id-DelayedActivationList-RL-ActivationCmdFDD					DelayedActivationInformationList-RL-ActivationCmdFDD,					--	(232),
	id-DelayedActivationInformation-RL-ActivationCmdFDD				DelayedActivationInformation-RL-ActivationCmdFDD,			--	(233),
	id-DelayedActivationList-RL-ActivationCmdTDD					DelayedActivationInformationList-RL-ActivationCmdTDD,					--	(234),
	id-DelayedActivationInformation-RL-ActivationCmdTDD				DelayedActivationInformation-RL-ActivationCmdTDD,			--	(235),
	id-neighbouringTDDCellMeasurementInformationLCR					NeighbouringTDDCellMeasurementInformationLCR,				--	(58),
	id-SYNCDlCodeId-TransInitLCR-CellSyncInitiationRqstTDD			SYNCDlCodeId-TransInitLCR-CellSyncInitiationRqstTDD,		--	(543),
	id-SYNCDlCodeId-MeasureInitLCR-CellSyncInitiationRqstTDD		SYNCDlCodeId-MeasureInitLCR-CellSyncInitiationRqstTDD,		--	(544),
	id-SYNCDlCodeIdTransReconfInfoLCR-CellSyncReconfRqstTDD			SYNCDlCodeIdTransReconfInfoLCR-CellSyncReconfRqstTDD,		--	(545),
	id-SYNCDlCodeIdMeasReconfigurationLCR-CellSyncReconfRqstTDD		SYNCDlCodeIdMeasInfoLCR-CellSyncReconfRqstTDD,				--	(546),
	id-SYNCDlCodeIdMeasInfoList-CellSyncReconfRqstTDD				SYNCDlCodeIdMeasInfoList-CellSyncReconfRqstTDD,				--	(547),
	id-SyncDLCodeIdsMeasInfoList-CellSyncReprtTDD					SyncDLCodeIdsMeasInfoList-CellSyncReprtTDD,					--	(548),
	id-SyncDLCodeIdThreInfoLCR										SyncDLCodeIdThreInfoLCR,									--	(549),
	id-NSubCyclesPerCyclePeriod-CellSyncReconfRqstTDD				NSubCyclesPerCyclePeriod,									--	(550),
	id-DwPCH-Power													DwPCH-Power,												--	(551),
	id-AccumulatedClockupdate-CellSyncReprtTDD						TimingAdjustmentValue,					--	(552),
	id-Angle-Of-Arrival-Value-LCR									Angle-Of-Arrival-Value-LCR,									--	(521),
	id-HSDSCH-FDD-Information										HSDSCH-FDD-Information,										--	(530),
	id-HSDSCH-FDD-Information-Response								HSDSCH-FDD-Information-Response,							--	(531),
	id-HSDSCH-Information-to-Modify									HSDSCH-Information-to-Modify,								--	(534),
	id-HSDSCH-RNTI													HSDSCH-RNTI,												--	(535),
	id-HSDSCH-TDD-Information										HSDSCH-TDD-Information,										--	(536),
	id-HSDSCH-TDD-Information-Response								HSDSCH-TDD-Information-Response,							--	(537),
	id-HSPDSCH-RL-ID												RL-ID,														--	(541),
	id-PrimCCPCH-RSCP-DL-PC-RqstTDD									PrimaryCCPCH-RSCP,											--	(542),
--  id-Unused-ProtocolIE-ID-64											(64),
	id-PDSCH-RL-ID													RL-ID,														--	(66),
	id-HSDSCH-RearrangeList-Bearer-RearrangeInd						HSDSCH-RearrangeList-Bearer-RearrangeInd,					--	(553),
	id-UL-Synchronisation-Parameters-LCR							UL-Synchronisation-Parameters-LCR,							--	(554),
	id-HSDSCH-FDD-Update-Information								HSDSCH-FDD-Update-Information,								--	(555),
	id-HSDSCH-TDD-Update-Information								HSDSCH-TDD-Update-Information,								--	(556),
	id-DL-DPCH-TimeSlotFormat-LCR-ModifyItem-RL-ReconfPrepTDD		TDD-DL-DPCH-TimeSlotFormat-LCR,								--	(558),
	id-UL-DPCH-TimeSlotFormat-LCR-ModifyItem-RL-ReconfPrepTDD		TDD-UL-DPCH-TimeSlotFormat-LCR,								--	(559),
	id-TDD-TPC-UplinkStepSize-LCR-RL-SetupRqstTDD					TDD-TPC-UplinkStepSize-LCR,									--	(560),
	id-TDD-TPC-UplinkStepSize-LCR-RL-AdditionRqstTDD				TDD-TPC-UplinkStepSize-LCR,									--	(561),
	id-TDD-TPC-DownlinkStepSize-RL-AdditionRqstTDD					TDD-TPC-DownlinkStepSize,									--	(562),
	id-TDD-TPC-UplinkStepSize-InformationAdd-LCR-RL-ReconfPrepTDD	TDD-TPC-UplinkStepSize-LCR,									--	(563),
	id-TDD-TPC-UplinkStepSize-InformationModify-LCR-RL-ReconfPrepTDD	TDD-TPC-UplinkStepSize-LCR,								--	(564),
	id-TDD-TPC-DownlinkStepSize-InformationModify-RL-ReconfPrepTDD	TDD-TPC-DownlinkStepSize,									--	(565),
	id-TDD-TPC-DownlinkStepSize-InformationAdd-RL-ReconfPrepTDD		TDD-TPC-DownlinkStepSize,									--	(566),
	id-CCTrCH-Maximum-DL-Power-RL-SetupRqstTDD						DL-Power,													--	(567),
	id-CCTrCH-Minimum-DL-Power-RL-SetupRqstTDD						DL-Power,													--	(568),
	id-CCTrCH-Maximum-DL-Power-RL-AdditionRqstTDD					DL-Power,													--	(569),
	id-CCTrCH-Minimum-DL-Power-RL-AdditionRqstTDD					DL-Power,													--	(570),
	id-CCTrCH-Maximum-DL-Power-InformationAdd-RL-ReconfPrepTDD		DL-Power,													--	(571),
	id-CCTrCH-Minimum-DL-Power-InformationAdd-RL-ReconfPrepTDD		DL-Power,													--	(572),
	id-CCTrCH-Maximum-DL-Power-InformationModify-RL-ReconfPrepTDD	DL-Power,													--	(573),
	id-CCTrCH-Minimum-DL-Power-InformationModify-RL-ReconfPrepTDD	DL-Power,													--	(574),
	id-Maximum-DL-Power-Modify-LCR-InformationModify-RL-ReconfPrepTDD	DL-Power,												--	(575),
	id-Minimum-DL-Power-Modify-LCR-InformationModify-RL-ReconfPrepTDD	DL-Power,												--	(576),
	id-DL-DPCH-LCR-InformationModify-ModifyList-RL-ReconfRqstTDD	DL-DPCH-LCR-InformationModify-ModifyList-RL-ReconfRqstTDD,	--	(577),
	id-CCTrCH-Maximum-DL-Power-InformationModify-RL-ReconfRqstTDD	DL-Power,													--	(578),
	id-CCTrCH-Minimum-DL-Power-InformationModify-RL-ReconfRqstTDD	DL-Power,													--	(579),
	id-Initial-DL-Power-TimeslotLCR-InformationItem					DL-Power,													--	(580),
	id-Maximum-DL-Power-TimeslotLCR-InformationItem					DL-Power,													--	(581),
	id-Minimum-DL-Power-TimeslotLCR-InformationItem					DL-Power,													--	(582),
	id-HS-DSCHProvidedBitRateValueInformation						HS-DSCHProvidedBitRate,										--	(583),
	id-HS-DSCHRequiredPowerValueInformation							HS-DSCHRequiredPower,										--	(585),
	id-HS-DSCHRequiredPowerValue									HS-DSCHRequiredPowerValue,									--	(586),
	id-TransmittedCarrierPowerOfAllCodesNotUsedForHSTransmission	TransmittedCarrierPowerOfAllCodesNotUsedForHSTransmissionValue,	--	(587),
	id-HS-SICH-Reception-Quality 									HS-SICH-Reception-Quality-Value,									--	(588),
	id-HS-SICH-Reception-Quality-Measurement-Value 					HS-SICH-Reception-Quality-Measurement-Value,				--	(589),
	id-HSSICH-Info-DM-Rprt 											HS-SICH-ID,													--	(590),
	id-HSSICH-Info-DM-Rqst											HSSICH-Info-DM-Rqst,										--	(591),
	id-HSSICH-Info-DM-Rsp											HS-SICH-ID,													--	(592),
	id-Best-Cell-Portions-Value										Best-Cell-Portions-Value,									--	(593),
	id-Primary-CPICH-Usage-for-Channel-Estimation					Primary-CPICH-Usage-for-Channel-Estimation,					--	(594),
	id-Secondary-CPICH-Information-Change							Secondary-CPICH-Information-Change,							--	(595),
	id-NumberOfReportedCellPortions									NumberOfReportedCellPortions,								--	(596),
	id-CellPortion-InformationItem-Cell-SetupRqstFDD				CellPortion-InformationItem-Cell-SetupRqstFDD,				--	(597),
	id-CellPortion-InformationList-Cell-SetupRqstFDD				CellPortion-InformationList-Cell-SetupRqstFDD,				--	(598),
	id-TimeslotISCP-LCR-InfoList-RL-ReconfPrepTDD					DL-TimeslotISCPInfoLCR,										--	(599),
	id-Secondary-CPICH-Information									CommonPhysicalChannelID,									--	(600),
	id-Received-total-wide-band-power-For-CellPortion				Received-total-wide-band-power-Value-IncrDecrThres,			--	(601),
	id-Unidirectional-DCH-Indicator									Unidirectional-DCH-Indicator,								--	(602),
	id-TimingAdjustmentValueLCR										TimingAdjustmentValueLCR,									--	(603),
--  id-multipleRL-dl-DPCH-InformationList								(604),
--  id-multipleRL-dl-DPCH-InformationModifyList						MultipleRL-DL-DPCH-InformationModifyList-RL-ReconfPrepTDD,		(605),
	id-multipleRL-ul-DPCH-InformationList							MultipleRL-UL-DPCH-InformationAddList-RL-ReconfPrepTDD,		--	(606),
	id-multipleRL-ul-DPCH-InformationModifyList						MultipleRL-UL-DPCH-InformationModifyList-RL-ReconfPrepTDD,	--	(607),
	id-RL-ID														RL-ID,														--	(608),
	id-SAT-Info-Almanac-ExtItem										SAT-Info-Almanac-ExtItem,									--	(609),
	id-HSDPA-Capability												HSDPA-Capability,											--	(610),
	id-HSDSCH-Resources-Information-AuditRsp						HS-DSCH-Resources-Information-AuditRsp,						--	(611),
	id-HSDSCH-Resources-Information-ResourceStatusInd				HS-DSCH-Resources-Information-ResourceStatusInd,			--	(612),
	id-HSDSCH-MACdFlows-to-Add										HSDSCH-MACdFlows-Information,								--	(613),
	id-HSDSCH-MACdFlows-to-Delete									HSDSCH-MACdFlows-to-Delete,									--	(614),
	id-HSDSCH-Information-to-Modify-Unsynchronised					HSDSCH-Information-to-Modify-Unsynchronised,				--	(615),
	id-TnlQos														TnlQos,														--	(616),
	id-Received-total-wide-band-power-For-CellPortion-Value			Received-total-wide-band-power-For-CellPortion-Value,		--	(617),
	id-Transmitted-Carrier-Power-For-CellPortion					Transmitted-Carrier-Power-Value,							--	(618),
	id-Transmitted-Carrier-Power-For-CellPortion-Value 				Transmitted-Carrier-Power-For-CellPortion-Value,			--	(619),
	id-TransmittedCarrierPowerOfAllCodesNotUsedForHS-PDSCH-HS-SCCH-E-AGCH-E-RGCHOrE-HICHTransmissionCellPortion	TransmittedCarrierPowerOfAllCodesNotUsedForHSTransmissionValue,	--		(620),
	id-TransmittedCarrierPowerOfAllCodesNotUsedForHS-PDSCH-HS-SCCH-E-AGCH-E-RGCHOrE-HICHTransmissionCellPortionValue	TransmittedCarrierPowerOfAllCodesNotUsedForHS-PDSCH-HS-SCCH-E-AGCH-E-RGCHOrE-HICHTransmissionCellPortionValue,	--	(621),
	id-UpPTSInterferenceValue										UpPTSInterferenceValue,										--	(622),
	id-PrimaryCCPCH-RSCP-Delta										PrimaryCCPCH-RSCP-Delta,									--	(623),
	id-MeasurementRecoveryBehavior									MeasurementRecoveryBehavior,								--	(624),
	id-MeasurementRecoveryReportingIndicator						MeasurementRecoveryReportingIndicator,						--	(625),
	id-MeasurementRecoverySupportIndicator							MeasurementRecoverySupportIndicator,						--	(626),
	id-Tstd-indicator												TSTD-Indicator,												--	(627),
	id-multiple-RL-Information-RL-ReconfPrepTDD						MultipleRL-Information-RL-ReconfPrepTDD,					--	(628),
	id-multiple-RL-Information-RL-ReconfRqstTDD						Multiple-RL-Information-RL-ReconfRqstTDD,					--	(629),
	id-DL-DPCH-Power-Information-RL-ReconfPrepFDD					DL-DPCH-Power-Information-RL-ReconfPrepFDD,					--	(630),
	id-F-DPCH-Information-RL-ReconfPrepFDD							F-DPCH-Information-RL-ReconfPrepFDD,						--	(631),
	id-F-DPCH-Information-RL-SetupRqstFDD							F-DPCH-Information-RL-SetupRqstFDD,							--	(632),
	id-Additional-S-CCPCH-Parameters-CTCH-ReconfRqstTDD				Secondary-CCPCH-parameterExtendedList-CTCH-ReconfRqstTDD,	--	(633),
	id-Additional-S-CCPCH-Parameters-CTCH-SetupRqstTDD				Secondary-CCPCH-parameterExtendedList-CTCH-SetupRqstTDD,		--	(634),
	id-Additional-S-CCPCH-LCR-Parameters-CTCH-ReconfRqstTDD			Secondary-CCPCH-LCR-parameterExtendedList-CTCH-ReconfRqstTDD,	--	(635),
	id-Additional-S-CCPCH-LCR-Parameters-CTCH-SetupRqstTDD			Secondary-CCPCH-LCR-parameterExtendedList-CTCH-SetupRqstTDD,--	(636),
	id-MICH-CFN														MICH-CFN,													--	(637),
	id-MICH-Information-AuditRsp									Common-PhysicalChannel-Status-Information,					--	(638),
	id-MICH-Information-ResourceStatusInd							Common-PhysicalChannel-Status-Information,					--	(639),
	id-MICH-Parameters-CTCH-ReconfRqstFDD							MICH-Parameters-CTCH-ReconfRqstFDD,							--	(640),
	id-MICH-Parameters-CTCH-ReconfRqstTDD							MICH-Parameters-CTCH-ReconfRqstTDD,							--	(641),
	id-MICH-Parameters-CTCH-SetupRqstFDD							MICH-Parameters-CTCH-SetupRqstFDD,							--	(642),
	id-MICH-Parameters-CTCH-SetupRqstTDD							MICH-Parameters-CTCH-SetupRqstTDD,							--	(643),
	id-Modification-Period											Modification-Period,										--	(644),
	id-NI-Information-NotifUpdateCmd								NI-Information,												--	(645),
	id-S-CCPCH-InformationListExt-AuditRsp							S-CCPCH-InformationListExt-AuditRsp,						--	(646),
	id-S-CCPCH-InformationListExt-ResourceStatusInd					S-CCPCH-InformationListExt-ResourceStatusInd,				--	(647),
	id-S-CCPCH-LCR-InformationListExt-AuditRsp						S-CCPCH-LCR-InformationListExt-AuditRsp,					--	(648),
	id-S-CCPCH-LCR-InformationListExt-ResourceStatusInd				S-CCPCH-LCR-InformationListExt-ResourceStatusInd,			--	(649),
	id-HARQ-Preamble-Mode											HARQ-Preamble-Mode,											--	(650),
	id-Initial-DL-DPCH-TimingAdjustment								DL-DPCH-TimingAdjustment,									--	(651),
	id-Initial-DL-DPCH-TimingAdjustment-Allowed						Initial-DL-DPCH-TimingAdjustment-Allowed,					--	(652),
	id-DLTransmissionBranchLoadValue								DLTransmissionBranchLoadValue,								--	(653),
	id-Power-Local-Cell-Group-choice-CM-Rqst						PowerLocalCellGroup-CM-Rqst,								--	(654),
	id-Power-Local-Cell-Group-choice-CM-Rsp							PowerLocalCellGroup-CM-Rsp,									--	(655),
	id-Power-Local-Cell-Group-choice-CM-Rprt						PowerLocalCellGroup-CM-Rprt,								--	(656),
	id-SynchronisationIndicator										SynchronisationIndicator,									--	(657),
	id-HSDPA-And-EDCH-CellPortion-Information-PSCH-ReconfRqst		HSDPA-And-EDCH-CellPortion-Information-PSCH-ReconfRqst,		--	(658),
	id-HSDPA-And-EDCH-CellPortion-InformationList-PSCH-ReconfRqst	HSDPA-And-EDCH-CellPortion-InformationList-PSCH-ReconfRqst,	--	(659),
	id-HS-DSCHRequiredPowerValue-For-Cell-Portion					HS-DSCHRequiredPowerValue,									--	(660),
	id-HS-DSCHRequiredPowerValueInformation-For-CellPortion			HS-DSCHRequiredPowerValueInformation-For-CellPortion,		--	(661),
	id-HS-DSCHProvidedBitRateValueInformation-For-CellPortion		HS-DSCHProvidedBitRateValueInformation-For-CellPortion,		--	(662),
	id-E-AGCH-And-E-RGCH-E-HICH-FDD-Scrambling-Code					DL-ScramblingCode,											--	(663),
	id-E-AGCH-FDD-Code-Information									E-AGCH-FDD-Code-Information,								--	(664),
	id-E-DCH-Capability												E-DCH-Capability,											--	(665),
	id-E-DCH-FDD-DL-Control-Channel-Information						E-DCH-FDD-DL-Control-Channel-Information,					--	(666),
	id-E-DCH-FDD-Information										E-DCH-FDD-Information,										--	(667),
	id-E-DCH-FDD-Information-Response								E-DCH-FDD-Information-Response,								--	(668),
	id-E-DCH-FDD-Information-to-Modify								E-DCH-FDD-Information-to-Modify,							--	(669),
	id-E-DCH-MACdFlows-to-Add										E-DCH-MACdFlows-Information,										--	(670),
	id-E-DCH-MACdFlows-to-Delete									E-DCH-MACdFlows-to-Delete,									--	(671),
	id-E-DCH-Resources-Information-AuditRsp							E-DCH-Resources-Information-AuditRsp,						--	(672),
	id-E-DCH-Resources-Information-ResourceStatusInd				E-DCH-Resources-Information-ResourceStatusInd,				--	(673),
	id-E-DCH-RL-Indication											E-DCH-RL-Indication,										--	(674),
	id-E-DCH-RL-Set-ID												RL-Set-ID,														--	(675),
	id-E-DPCH-Information-RL-ReconfPrepFDD							E-DPCH-Information-RL-ReconfPrepFDD,						--	(676),
	id-E-DPCH-Information-RL-SetupRqstFDD							E-DPCH-Information-RL-SetupRqstFDD,							--	(677),
	id-E-RGCH-E-HICH-FDD-Code-Information							E-RGCH-E-HICH-FDD-Code-Information,							--	(678),
	id-Serving-E-DCH-RL-ID											Serving-E-DCH-RL-ID,										--	(679),
	id-UL-DPDCH-Indicator-For-E-DCH-Operation						UL-DPDCH-Indicator-For-E-DCH-Operation,						--	(680),
	id-FDD-S-CCPCH-FrameOffset-CTCH-SetupRqstFDD					FDD-S-CCPCH-FrameOffset,									--	(681),
	id-E-DPCH-Information-RL-ReconfRqstFDD							E-DPCH-Information-RL-ReconfRqstFDD,						--	(682),
	id-Maximum-Target-ReceivedTotalWideBandPower					Maximum-Target-ReceivedTotalWideBandPower,					--	(683),
	id-E-DCHProvidedBitRateValueInformation							E-DCHProvidedBitRate,										--	(684),
	id-HARQ-Preamble-Mode-Activation-Indicator						HARQ-Preamble-Mode-Activation-Indicator,					--	(685),
	id-RL-Specific-E-DCH-Info										RL-Specific-E-DCH-Info,										--	(686),
	id-E-DCH-CapacityConsumptionLaw									DedicatedChannelsCapacityConsumptionLaw,					--	(687),
	id-multiple-DedicatedMeasurementValueList-TDD-DM-Rsp			Multiple-DedicatedMeasurementValueList-TDD-DM-Rsp,			--	(688),
	id-multiple-DedicatedMeasurementValueList-LCR-TDD-DM-Rsp		Multiple-DedicatedMeasurementValueList-LCR-TDD-DM-Rsp,		--	(689),
	id-E-DCH-RearrangeList-Bearer-RearrangeInd						E-DCH-RearrangeList-Bearer-RearrangeInd,					--	(690),
--	id-HSDPA-And-EDCH-CellPortion-InformationListIE-PSCH-ReconfRqst	HSDPA-And-EDCH-CellPortion-InformationListIE-PSCH-ReconfRqst,		(691),
	id-multipleRL-dl-CCTrCH-InformationModifyList-RL-ReconfRqstTDD	MultipleRL-DL-CCTrCH-InformationModifyList-RL-ReconfRqstTDD,	--	(692),
	id-Target-NonServing-EDCH-To-Total-EDCH-Power-Ratio				Target-NonServing-EDCH-To-Total-EDCH-Power-Ratio,			--	(693),
	id-CellPortion-InformationItem-Cell-ReconfRqstFDD				CellPortion-InformationItem-Cell-ReconfRqstFDD,				--	(694),
	id-CellPortion-InformationList-Cell-ReconfRqstFDD				CellPortion-InformationList-Cell-ReconfRqstFDD,				--	(695),
	id-multiple-PUSCH-InfoList-DM-Rsp								Multiple-PUSCH-InfoList-DM-Rsp,								--	(696),
	id-multiple-PUSCH-InfoList-DM-Rprt								Multiple-PUSCH-InfoList-DM-Rprt,							--	(697),
	id-Reference-ReceivedTotalWideBandPower							Reference-ReceivedTotalWideBandPower,						--	(698),
	...
}
-- **************************************************************
--
-- COMMON TRANSPORT CHANNEL SETUP REQUEST FDD
--
-- **************************************************************
--CommonTransportChannelSetupRequestFDD ::= SEQUENCE {
--	protocolIEs				ProtocolIE-Container	{{CommonTransportChannelSetupRequestFDD-IEs}},
--	protocolExtensions		ProtocolExtensionContainer	{{CommonTransportChannelSetupRequestFDD-Extensions}}     OPTIONAL,
--	...
--}

CommonTransportChannelSetupRequestFDD ::= SEQUENCE {
	protocolIEs				ProtocolIE-Container,
	protocolExtensions		ProtocolExtensionContainer OPTIONAL,
	...
}

--CommonTransportChannelSetupRequestFDD-Extensions NBAP-PROTOCOL-EXTENSION ::= {
--	...
--}

--CommonTransportChannelSetupRequestFDD-IEs NBAP-PROTOCOL-IES ::= {
--	{ ID	id-C-ID												CRITICALITY reject		TYPE	C-ID				PRESENCE mandatory	}|
--	{ ID	id-ConfigurationGenerationID						CRITICALITY reject		TYPE	ConfigurationGenerationID		PRESENCE mandatory	}|
--	{ ID	id-CommonPhysicalChannelType-CTCH-SetupRqstFDD		CRITICALITY ignore		TYPE	CommonPhysicalChannelType-CTCH-SetupRqstFDD		PRESENCE 	mandatory	},
--	...
--}

CommonPhysicalChannelType-CTCH-SetupRqstFDD ::= CHOICE {
	secondary-CCPCH-parameters		Secondary-CCPCH-CTCH-SetupRqstFDD,
	pRACH-parameters				PRACH-CTCH-SetupRqstFDD,
	notUsed-pCPCHes-parameters		NULL,
	...
}

Secondary-CCPCH-CTCH-SetupRqstFDD ::= SEQUENCE {
	commonPhysicalChannelID					CommonPhysicalChannelID,
	fdd-S-CCPCH-Offset						FDD-S-CCPCH-Offset,
	dl-ScramblingCode						DL-ScramblingCode	OPTIONAL,
	-- This IE shall be present if the PCH Parameters IE is not present
	fdd-DL-ChannelisationCodeNumber			FDD-DL-ChannelisationCodeNumber,
	tFCS									TFCS,
	secondary-CCPCH-SlotFormat				SecondaryCCPCH-SlotFormat,
	tFCI-Presence							TFCI-Presence	OPTIONAL,
	-- This IE shall be present if the Secondary CCPCH Slot Format is set to any of the values from 8 to 17
	multiplexingPosition					MultiplexingPosition,
	powerOffsetInformation					PowerOffsetInformation-CTCH-SetupRqstFDD,
	sTTD-Indicator							STTD-Indicator,
	fACH-Parameters							FACH-ParametersList-CTCH-SetupRqstFDD		OPTIONAL,
	pCH-Parameters							PCH-Parameters-CTCH-SetupRqstFDD			OPTIONAL,
--	iE-Extensions							ProtocolExtensionContainer  { { Secondary-CCPCHItem-CTCH-SetupRqstFDD-ExtIEs} }		OPTIONAL,
	iE-Extensions							ProtocolExtensionContainer OPTIONAL,
	...
}

--Secondary-CCPCHItem-CTCH-SetupRqstFDD-ExtIEs NBAP-PROTOCOL-EXTENSION ::= {
--	{ ID id-MICH-Parameters-CTCH-SetupRqstFDD			CRITICALITY reject	EXTENSION MICH-Parameters-CTCH-SetupRqstFDD		PRESENCE optional	}|
--	{ ID id-FDD-S-CCPCH-FrameOffset-CTCH-SetupRqstFDD	CRITICALITY reject	EXTENSION FDD-S-CCPCH-FrameOffset				PRESENCE optional	},
--	...
--}

PowerOffsetInformation-CTCH-SetupRqstFDD ::= SEQUENCE {
	pO1-ForTFCI-Bits						PowerOffset,
	pO3-ForPilotBits						PowerOffset,
--	iE-Extensions							ProtocolExtensionContainer { { PowerOffsetInformation-CTCH-SetupRqstFDD-ExtIEs} }	OPTIONAL,
	iE-Extensions							ProtocolExtensionContainer OPTIONAL,
	...
}

--PowerOffsetInformation-CTCH-SetupRqstFDD-ExtIEs NBAP-PROTOCOL-EXTENSION ::= {
--	...
--}

--FACH-ParametersList-CTCH-SetupRqstFDD ::= ProtocolIE-Single-Container {{ FACH-ParametersListIEs-CTCH-SetupRqstFDD }}
FACH-ParametersList-CTCH-SetupRqstFDD ::= ProtocolIE-Single-Container 

--FACH-ParametersListIEs-CTCH-SetupRqstFDD NBAP-PROTOCOL-IES ::= {
--	{ ID id-FACH-ParametersListIE-CTCH-SetupRqstFDD   CRITICALITY reject	TYPE FACH-ParametersListIE-CTCH-SetupRqstFDD	PRESENCE mandatory }
--}

--FACH-ParametersListIE-CTCH-SetupRqstFDD ::= SEQUENCE (SIZE (1..maxNrOfFACHs)) OF FACH-ParametersItem-CTCH-SetupRqstFDD
FACH-ParametersListIE-CTCH-SetupRqstFDD ::= SEQUENCE (SIZE (1..8)) OF FACH-ParametersItem-CTCH-SetupRqstFDD

FACH-ParametersItem-CTCH-SetupRqstFDD ::= SEQUENCE {
	commonTransportChannelID			CommonTransportChannelID,
	transportFormatSet					TransportFormatSet,
	toAWS								ToAWS,
	toAWE								ToAWE,
	maxFACH-Power						DL-Power,
--	iE-Extensions						ProtocolExtensionContainer  { { FACH-ParametersItem-CTCH-SetupRqstFDD-ExtIEs} }		OPTIONAL,
	iE-Extensions						ProtocolExtensionContainer  OPTIONAL,
	...
}

--FACH-ParametersItem-CTCH-SetupRqstFDD-ExtIEs NBAP-PROTOCOL-EXTENSION ::= {
--{ ID	id-bindingID						CRITICALITY	ignore		EXTENSION 	BindingID			PRESENCE 	optional	}|
--{ ID	id-transportlayeraddress			CRITICALITY	ignore		EXTENSION 	TransportLayerAddress	PRESENCE 	optional	},
--	...
--}

--PCH-Parameters-CTCH-SetupRqstFDD ::= ProtocolIE-Single-Container {{ PCH-ParametersIE-CTCH-SetupRqstFDD }}
PCH-Parameters-CTCH-SetupRqstFDD ::= ProtocolIE-Single-Container

--PCH-ParametersIE-CTCH-SetupRqstFDD NBAP-PROTOCOL-IES ::= {
--	{ ID id-PCH-ParametersItem-CTCH-SetupRqstFDD   CRITICALITY reject	TYPE PCH-ParametersItem-CTCH-SetupRqstFDD	PRESENCE mandatory }
--}

PCH-ParametersItem-CTCH-SetupRqstFDD ::= SEQUENCE {
	commonTransportChannelID			CommonTransportChannelID,
	transportFormatSet					TransportFormatSet,
	toAWS								ToAWS,
	toAWE								ToAWE,	
	pCH-Power							DL-Power,
	pICH-Parameters						PICH-Parameters-CTCH-SetupRqstFDD,
--	iE-Extensions						ProtocolExtensionContainer  { { PCH-ParametersItem-CTCH-SetupRqstFDD-ExtIEs} }		OPTIONAL,
	iE-Extensions						ProtocolExtensionContainer OPTIONAL,
	...
}

--PCH-ParametersItem-CTCH-SetupRqstFDD-ExtIEs NBAP-PROTOCOL-EXTENSION ::= {
--	{ ID	id-bindingID						CRITICALITY	ignore		EXTENSION 	BindingID		PRESENCE 	optional	}|
--	{ ID	id-transportlayeraddress			CRITICALITY	ignore		EXTENSION 	TransportLayerAddress	PRESENCE 	optional	},
--	...
--}

PICH-Parameters-CTCH-SetupRqstFDD ::= SEQUENCE {
	commonPhysicalChannelID						CommonPhysicalChannelID,
	fdd-dl-ChannelisationCodeNumber				FDD-DL-ChannelisationCodeNumber,
	pICH-Power									PICH-Power,
	pICH-Mode									PICH-Mode,	
	sTTD-Indicator								STTD-Indicator,
--	iE-Extensions								ProtocolExtensionContainer { { PICH-Parameters-CTCH-SetupRqstFDD-ExtIEs} }		OPTIONAL,
	iE-Extensions								ProtocolExtensionContainer OPTIONAL,
	...
}

--PICH-Parameters-CTCH-SetupRqstFDD-ExtIEs NBAP-PROTOCOL-EXTENSION ::= {
--	...
--}

MICH-Parameters-CTCH-SetupRqstFDD ::= SEQUENCE {
	commonPhysicalChannelID						CommonPhysicalChannelID,
	fdd-dl-ChannelisationCodeNumber				FDD-DL-ChannelisationCodeNumber,
	mICH-Power									PICH-Power,
	mICH-Mode									MICH-Mode,
	sTTD-Indicator								STTD-Indicator,
--	iE-Extensions								ProtocolExtensionContainer { { MICH-Parameters-CTCH-SetupRqstFDD-ExtIEs} }		OPTIONAL,
	iE-Extensions								ProtocolExtensionContainer OPTIONAL,
	...
}

--MICH-Parameters-CTCH-SetupRqstFDD-ExtIEs NBAP-PROTOCOL-EXTENSION ::= {
--	...
--}

PRACH-CTCH-SetupRqstFDD ::= SEQUENCE {
	commonPhysicalChannelID						CommonPhysicalChannelID,
	scramblingCodeNumber						ScramblingCodeNumber,
	tFCS										TFCS,
	preambleSignatures							PreambleSignatures,
	allowedSlotFormatInformation				AllowedSlotFormatInformationList-CTCH-SetupRqstFDD,
	rACH-SubChannelNumbers						RACH-SubChannelNumbers,
	ul-punctureLimit							PunctureLimit,
	preambleThreshold							PreambleThreshold,
	rACH-Parameters								RACH-Parameters-CTCH-SetupRqstFDD,
    aICH-Parameters                             AICH-Parameters-CTCH-SetupRqstFDD,
--	iE-Extensions								ProtocolExtensionContainer { { PRACHItem-CTCH-SetupRqstFDD-ExtIEs} }		OPTIONAL,
	iE-Extensions								ProtocolExtensionContainer OPTIONAL,
	...
}

--PRACHItem-CTCH-SetupRqstFDD-ExtIEs NBAP-PROTOCOL-EXTENSION ::= {
--	...
--}

--AllowedSlotFormatInformationList-CTCH-SetupRqstFDD ::= SEQUENCE (SIZE (1.. maxNrOfSlotFormatsPRACH)) OF AllowedSlotFormatInformationItem-CTCH-SetupRqstFDD
AllowedSlotFormatInformationList-CTCH-SetupRqstFDD ::= SEQUENCE (SIZE (1.. 8)) OF AllowedSlotFormatInformationItem-CTCH-SetupRqstFDD

AllowedSlotFormatInformationItem-CTCH-SetupRqstFDD ::= SEQUENCE {
	rACHSlotFormat								RACH-SlotFormat,
--	iE-Extensions								ProtocolExtensionContainer  { { AllowedSlotFormatInformationItem-CTCH-SetupRqstFDD-ExtIEs} }		OPTIONAL,
	iE-Extensions								ProtocolExtensionContainer OPTIONAL,
	...
}

--AllowedSlotFormatInformationItem-CTCH-SetupRqstFDD-ExtIEs NBAP-PROTOCOL-EXTENSION ::= {
--	...
--}

--RACH-Parameters-CTCH-SetupRqstFDD ::= ProtocolIE-Single-Container {{ RACH-ParametersIE-CTCH-SetupRqstFDD }}
RACH-Parameters-CTCH-SetupRqstFDD ::= ProtocolIE-Single-Container

--RACH-ParametersIE-CTCH-SetupRqstFDD NBAP-PROTOCOL-IES ::= {
--	{ ID id-RACH-ParametersItem-CTCH-SetupRqstFDD   CRITICALITY reject	TYPE RACH-ParametersItem-CTCH-SetupRqstFDD	PRESENCE mandatory }
--}

RACH-ParametersItem-CTCH-SetupRqstFDD ::= SEQUENCE {
 	commonTransportChannelID					CommonTransportChannelID,
 	transportFormatSet							TransportFormatSet,
--	iE-Extensions								ProtocolExtensionContainer  { { RACH-ParametersItem-CTCH-SetupRqstFDD-ExtIEs} }		OPTIONAL,
	iE-Extensions								ProtocolExtensionContainer OPTIONAL,
	...
 }

--RACH-ParametersItem-CTCH-SetupRqstFDD-ExtIEs NBAP-PROTOCOL-EXTENSION ::= {
--	{ ID	id-bindingID						CRITICALITY	ignore		EXTENSION 	BindingID		PRESENCE 	optional	}|
--	{ ID	id-transportlayeraddress			CRITICALITY	ignore		EXTENSION 	TransportLayerAddress	PRESENCE 	optional	},
--	...
--}

AICH-Parameters-CTCH-SetupRqstFDD ::= SEQUENCE {
	commonPhysicalChannelID						CommonPhysicalChannelID,
	aICH-TransmissionTiming						AICH-TransmissionTiming,
	fdd-dl-ChannelisationCodeNumber				FDD-DL-ChannelisationCodeNumber,
	aICH-Power									AICH-Power,
	sTTD-Indicator								STTD-Indicator,
--	iE-Extensions								ProtocolExtensionContainer  { { AICH-Parameters-CTCH-SetupRqstFDD-ExtIEs} }		OPTIONAL,
	iE-Extensions								ProtocolExtensionContainer OPTIONAL,
	...
}

--AICH-Parameters-CTCH-SetupRqstFDD-ExtIEs NBAP-PROTOCOL-EXTENSION ::= {
--	...
--}

-- **************************************************************
--
-- COMMON TRANSPORT CHANNEL SETUP REQUEST TDD
--
-- **************************************************************

--CommonTransportChannelSetupRequestTDD ::= SEQUENCE {
--	protocolIEs				ProtocolIE-Container	{{CommonTransportChannelSetupRequestTDD-IEs}},
--	protocolExtensions 		ProtocolExtensionContainer	{{CommonTransportChannelSetupRequestTDD-Extensions}}		OPTIONAL,
--	...
--}
CommonTransportChannelSetupRequestTDD ::= SEQUENCE {
	protocolIEs				ProtocolIE-Container,
	protocolExtensions 		ProtocolExtensionContainer OPTIONAL,
	...
}

--CommonTransportChannelSetupRequestTDD-IEs NBAP-PROTOCOL-IES ::= {
--	{ ID	id-C-ID											CRITICALITY reject	TYPE C-ID					PRESENCE mandatory	}|
--	{ ID	id-ConfigurationGenerationID					CRITICALITY reject	TYPE ConfigurationGenerationID			PRESENCE mandatory	}|
--	{ ID	id-CommonPhysicalChannelType-CTCH-SetupRqstTDD	CRITICALITY ignore	TYPE CommonPhysicalChannelType-CTCH-SetupRqstTDD		PRESENCE 	mandatory	},
--	...
--}

--CommonTransportChannelSetupRequestTDD-Extensions NBAP-PROTOCOL-EXTENSION ::= {
--	...
--}

CommonPhysicalChannelType-CTCH-SetupRqstTDD ::= CHOICE {
	secondary-CCPCH-parameters					Secondary-CCPCH-CTCH-SetupRqstTDD,
	pRACH-parameters							PRACH-CTCH-SetupRqstTDD,
	...
}

Secondary-CCPCH-CTCH-SetupRqstTDD ::= SEQUENCE {
	sCCPCH-CCTrCH-ID							CCTrCH-ID,	-- For DL CCTrCH supporting one or several Secondary CCPCHs
	tFCS										TFCS,		-- For DL CCTrCH supporting one or several Secondary CCPCHs
	tFCI-Coding									TFCI-Coding,
	punctureLimit								PunctureLimit,
	secondaryCCPCH-parameterList				Secondary-CCPCH-parameterList-CTCH-SetupRqstTDD,
	fACH-ParametersList							FACH-ParametersList-CTCH-SetupRqstTDD		OPTIONAL,
	pCH-Parameters								PCH-Parameters-CTCH-SetupRqstTDD			OPTIONAL,
--	iE-Extensions								ProtocolExtensionContainer	{{Secondary-CCPCHItem-CTCH-SetupRqstTDD-ExtIEs}}		OPTIONAL,
	iE-Extensions								ProtocolExtensionContainer OPTIONAL,
	...
}

--Secondary-CCPCHItem-CTCH-SetupRqstTDD-ExtIEs NBAP-PROTOCOL-EXTENSION ::= {
--	{ ID id-Tstd-indicator								CRITICALITY reject	EXTENSION TSTD-Indicator				PRESENCE optional	}|
--	{ ID id-MICH-Parameters-CTCH-SetupRqstTDD			CRITICALITY reject	EXTENSION MICH-Parameters-CTCH-SetupRqstTDD		PRESENCE optional	}|
--	{ ID id-Additional-S-CCPCH-Parameters-CTCH-SetupRqstTDD			CRITICALITY reject	EXTENSION Secondary-CCPCH-parameterExtendedList-CTCH-SetupRqstTDD		PRESENCE optional	}|
	-- Applicable to 3.84Mcps TDD only, used when more than maxNrOfSCCPCHs SCCPCHs are to be established.
--	{ ID id-Additional-S-CCPCH-LCR-Parameters-CTCH-SetupRqstTDD		CRITICALITY reject	EXTENSION Secondary-CCPCH-LCR-parameterExtendedList-CTCH-SetupRqstTDD		PRESENCE optional	},
	-- Applicable to 1.28Mcps TDD only, used when more than maxNrOfSCCPCHLCRs SCCPCHs are to be established.
--	...
--}

--Secondary-CCPCH-parameterList-CTCH-SetupRqstTDD ::= ProtocolIE-Single-Container {{ Secondary-CCPCH-parameterListIEs-CTCH-SetupRqstTDD }}
Secondary-CCPCH-parameterList-CTCH-SetupRqstTDD ::= ProtocolIE-Single-Container

--Secondary-CCPCH-parameterListIEs-CTCH-SetupRqstTDD NBAP-PROTOCOL-IES ::= {
--	{ ID id-Secondary-CCPCH-parameterListIE-CTCH-SetupRqstTDD	CRITICALITY reject	TYPE Secondary-CCPCH-parameterListIE-CTCH-SetupRqstTDD		PRESENCE optional }|
--	{ ID id-Secondary-CCPCH-LCR-parameterList-CTCH-SetupRqstTDD	CRITICALITY reject	TYPE Secondary-CCPCH-LCR-parameterList-CTCH-SetupRqstTDD	PRESENCE optional }
--}

--Secondary-CCPCH-parameterListIE-CTCH-SetupRqstTDD ::= SEQUENCE (SIZE (1..maxNrOfSCCPCHs)) OF Secondary-CCPCH-parameterItem-CTCH-SetupRqstTDD
Secondary-CCPCH-parameterListIE-CTCH-SetupRqstTDD ::= SEQUENCE (SIZE (1..8)) OF Secondary-CCPCH-parameterItem-CTCH-SetupRqstTDD

Secondary-CCPCH-parameterItem-CTCH-SetupRqstTDD ::= SEQUENCE {
	commonPhysicalChannelID						CommonPhysicalChannelID,
	tdd-ChannelisationCode						TDD-ChannelisationCode,
	timeslot									TimeSlot,
	midambleShiftandBurstType					MidambleShiftAndBurstType,
	tdd-PhysicalChannelOffset					TDD-PhysicalChannelOffset,
	repetitionPeriod							RepetitionPeriod,
	repetitionLength							RepetitionLength,
	s-CCPCH-Power								DL-Power,
--	iE-Extensions								ProtocolExtensionContainer { { Secondary-CCPCH-parameterItem-CTCH-SetupRqstTDD-ExtIEs} }		OPTIONAL,
	iE-Extensions								ProtocolExtensionContainer OPTIONAL,
	...
}

--Secondary-CCPCH-parameterItem-CTCH-SetupRqstTDD-ExtIEs NBAP-PROTOCOL-EXTENSION ::= {
--	...
--}

--FACH-ParametersList-CTCH-SetupRqstTDD ::= ProtocolIE-Single-Container {{ FACH-ParametersListIEs-CTCH-SetupRqstTDD }}
FACH-ParametersList-CTCH-SetupRqstTDD ::= ProtocolIE-Single-Container

--FACH-ParametersListIEs-CTCH-SetupRqstTDD NBAP-PROTOCOL-IES ::= {
--	{ ID id-FACH-ParametersListIE-CTCH-SetupRqstTDD   CRITICALITY reject	TYPE FACH-ParametersListIE-CTCH-SetupRqstTDD	PRESENCE mandatory }
--}

--FACH-ParametersListIE-CTCH-SetupRqstTDD ::= SEQUENCE (SIZE (1..maxNrOfFACHs)) OF FACH-ParametersItem-CTCH-SetupRqstTDD
FACH-ParametersListIE-CTCH-SetupRqstTDD ::= SEQUENCE (SIZE (1..8)) OF FACH-ParametersItem-CTCH-SetupRqstTDD

FACH-ParametersItem-CTCH-SetupRqstTDD ::= SEQUENCE {
	commonTransportChannelID				CommonTransportChannelID,
	fACH-CCTrCH-ID							CCTrCH-ID,
	dl-TransportFormatSet					TransportFormatSet,
	toAWS									ToAWS,
	toAWE									ToAWE,
--	iE-Extensions							ProtocolExtensionContainer  { { FACH-ParametersItem-CTCH-SetupRqstTDD-ExtIEs} }		OPTIONAL,
	iE-Extensions							ProtocolExtensionContainer OPTIONAL,
	...
}

--FACH-ParametersItem-CTCH-SetupRqstTDD-ExtIEs NBAP-PROTOCOL-EXTENSION ::= {
--	{ ID	id-maxFACH-Power-LCR-CTCH-SetupRqstTDD	CRITICALITY	reject	EXTENSION DL-Power			PRESENCE optional	}|
	-- Applicable to 1.28Mcps TDD only
--	{ ID	id-bindingID							CRITICALITY	ignore	EXTENSION BindingID			PRESENCE optional	}|
	-- Shall be ignored if bearer establishment with ALCAP.
--	{ ID	id-transportlayeraddress				CRITICALITY	ignore	EXTENSION TransportLayerAddress	PRESENCE optional	},
	-- Shall be ignored if bearer establishment with ALCAP.
--	...
--}

--PCH-Parameters-CTCH-SetupRqstTDD ::= ProtocolIE-Single-Container {{ PCH-ParametersIE-CTCH-SetupRqstTDD }}
PCH-Parameters-CTCH-SetupRqstTDD ::= ProtocolIE-Single-Container

--PCH-ParametersIE-CTCH-SetupRqstTDD NBAP-PROTOCOL-IES ::= {
--	{ ID id-PCH-ParametersItem-CTCH-SetupRqstTDD   CRITICALITY reject	TYPE PCH-ParametersItem-CTCH-SetupRqstTDD	PRESENCE mandatory }
--}

PCH-ParametersItem-CTCH-SetupRqstTDD ::= SEQUENCE {
	commonTransportChannelID				CommonTransportChannelID,
	pCH-CCTrCH-ID							CCTrCH-ID,
	dl-TransportFormatSet					TransportFormatSet,	-- For the DL.
	toAWS									ToAWS,
	toAWE									ToAWE,
	pICH-Parameters							PICH-Parameters-CTCH-SetupRqstTDD,
--	iE-Extensions							ProtocolExtensionContainer  { { PCH-ParametersItem-CTCH-SetupRqstTDD-ExtIEs} }		OPTIONAL,
	iE-Extensions							ProtocolExtensionContainer OPTIONAL,
	...
}

--PCH-ParametersItem-CTCH-SetupRqstTDD-ExtIEs NBAP-PROTOCOL-EXTENSION ::= {
--	{ ID	id-PCH-Power-LCR-CTCH-SetupRqstTDD			CRITICALITY	reject	EXTENSION DL-Power		PRESENCE optional	}|
--	{ ID	id-bindingID								CRITICALITY	ignore	EXTENSION BindingID		PRESENCE optional	}|
	-- Shall be ignored if bearer establishment with ALCAP.
--	{ ID	id-transportlayeraddress					CRITICALITY	ignore	EXTENSION TransportLayerAddress	PRESENCE optional	},
	-- Shall be ignored if bearer establishment with ALCAP.
--	...
--}

--PICH-Parameters-CTCH-SetupRqstTDD ::= ProtocolIE-Single-Container {{ PICH-ParametersIE-CTCH-SetupRqstTDD }}
PICH-Parameters-CTCH-SetupRqstTDD ::= ProtocolIE-Single-Container

--PICH-ParametersIE-CTCH-SetupRqstTDD NBAP-PROTOCOL-IES ::= {
--	{ ID id-PICH-ParametersItem-CTCH-SetupRqstTDD	CRITICALITY reject	TYPE PICH-ParametersItem-CTCH-SetupRqstTDD	PRESENCE optional }|
--	{ ID id-PICH-LCR-Parameters-CTCH-SetupRqstTDD	CRITICALITY reject	TYPE PICH-LCR-Parameters-CTCH-SetupRqstTDD	PRESENCE optional }
--}

PICH-ParametersItem-CTCH-SetupRqstTDD ::= SEQUENCE {
	commonPhysicalChannelID					CommonPhysicalChannelID,
 	tdd-ChannelisationCode					TDD-ChannelisationCode,
 	timeSlot  								TimeSlot,
	midambleshiftAndBurstType				MidambleShiftAndBurstType,
 	tdd-PhysicalChannelOffset				TDD-PhysicalChannelOffset,
 	repetitionPeriod						RepetitionPeriod,
 	repetitionLength						RepetitionLength,
 	pagingIndicatorLength					PagingIndicatorLength,
	pICH-Power								PICH-Power,
--	iE-Extensions							ProtocolExtensionContainer  { { PICH-ParametersItem-CTCH-SetupRqstTDD-ExtIEs} }		OPTIONAL,
	iE-Extensions							ProtocolExtensionContainer OPTIONAL,
	...
}

--PICH-ParametersItem-CTCH-SetupRqstTDD-ExtIEs NBAP-PROTOCOL-EXTENSION ::= {
--	...
--}

PICH-LCR-Parameters-CTCH-SetupRqstTDD ::= SEQUENCE {
	commonPhysicalChannelID					CommonPhysicalChannelID,
 	tdd-ChannelisationCodeLCR				TDD-ChannelisationCodeLCR,
 	timeSlotLCR  							TimeSlotLCR,
	midambleShiftLCR						MidambleShiftLCR,
	tdd-PhysicalChannelOffset				TDD-PhysicalChannelOffset,
 	repetitionPeriod						RepetitionPeriod,
 	repetitionLength						RepetitionLength,
 	pagingIndicatorLength					PagingIndicatorLength,
	pICH-Power								PICH-Power,
	second-TDD-ChannelisationCodeLCR		TDD-ChannelisationCodeLCR,
--	iE-Extensions							ProtocolExtensionContainer  { { PICH-LCR-ParametersItem-CTCH-SetupRqstTDD-ExtIEs} }		OPTIONAL,
	iE-Extensions							ProtocolExtensionContainer OPTIONAL,
	...
}

--PICH-LCR-ParametersItem-CTCH-SetupRqstTDD-ExtIEs NBAP-PROTOCOL-EXTENSION ::= {
--{ ID	id-Tstd-indicator			CRITICALITY	reject		EXTENSION 	TSTD-Indicator		PRESENCE 	optional	},
	-- Applicable to 1.28 Mcps TDD only
--	...
--}

--Secondary-CCPCH-LCR-parameterList-CTCH-SetupRqstTDD ::= SEQUENCE (SIZE (1..maxNrOfSCCPCHLCRs)) OF Secondary-CCPCH-LCR-parameterItem-CTCH-SetupRqstTDD
Secondary-CCPCH-LCR-parameterList-CTCH-SetupRqstTDD ::= SEQUENCE (SIZE (1..8)) OF Secondary-CCPCH-LCR-parameterItem-CTCH-SetupRqstTDD

Secondary-CCPCH-LCR-parameterItem-CTCH-SetupRqstTDD ::= SEQUENCE {
	commonPhysicalChannelID						CommonPhysicalChannelID,
	tdd-ChannelisationCodeLCR					TDD-ChannelisationCodeLCR,
	timeslotLCR									TimeSlotLCR,
	midambleShiftLCR							MidambleShiftLCR,
	tdd-PhysicalChannelOffset					TDD-PhysicalChannelOffset,
	repetitionPeriod							RepetitionPeriod,
	repetitionLength							RepetitionLength,
	s-CCPCH-Power								DL-Power,
	s-CCPCH-TimeSlotFormat-LCR					TDD-DL-DPCH-TimeSlotFormat-LCR,
--	iE-Extensions								ProtocolExtensionContainer { { Secondary-CCPCH-LCR-parameterItem-CTCH-SetupRqstTDD-ExtIEs} }		OPTIONAL,
	iE-Extensions								ProtocolExtensionContainer OPTIONAL,
	...
}

--Secondary-CCPCH-LCR-parameterItem-CTCH-SetupRqstTDD-ExtIEs NBAP-PROTOCOL-EXTENSION ::= {
--	...
--}

MICH-Parameters-CTCH-SetupRqstTDD ::= SEQUENCE {
	commonPhysicalChannelID					CommonPhysicalChannelID,
	tdd-PhysicalChannelOffset				TDD-PhysicalChannelOffset,
	repetitionPeriod						RepetitionPeriod,
	repetitionLength						RepetitionLength,
	notificationIndicatorLength				NotificationIndicatorLength,
	mICH-Power								PICH-Power,
	mICH-TDDOption-Specific-Parameters		MICH-TDDOption-Specific-Parameters-CTCH-SetupRqstTDD,
--	iE-Extensions							ProtocolExtensionContainer  { { MICH-Parameters-CTCH-SetupRqstTDD-ExtIEs} }		OPTIONAL,
	iE-Extensions							ProtocolExtensionContainer 
	OPTIONAL,
	...
}

--MICH-Parameters-CTCH-SetupRqstTDD-ExtIEs NBAP-PROTOCOL-EXTENSION ::= {
--	...
--}

MICH-TDDOption-Specific-Parameters-CTCH-SetupRqstTDD ::= CHOICE {
	hCR-TDD									MICH-HCR-Parameters-CTCH-SetupRqstTDD,
	lCR-TDD									MICH-LCR-Parameters-CTCH-SetupRqstTDD,
	...
}

MICH-HCR-Parameters-CTCH-SetupRqstTDD ::= SEQUENCE {
	tdd-ChannelisationCode					TDD-ChannelisationCode,
	timeSlot								TimeSlot,
	midambleshiftAndBurstType				MidambleShiftAndBurstType,
--	iE-Extensions							ProtocolExtensionContainer { { MICH-HCR-Parameters-CTCH-SetupRqstTDD-ExtIEs } }		OPTIONAL,
	iE-Extensions							ProtocolExtensionContainer OPTIONAL,
	...
}

--MICH-HCR-Parameters-CTCH-SetupRqstTDD-ExtIEs NBAP-PROTOCOL-EXTENSION ::= {
--	...
--}

MICH-LCR-Parameters-CTCH-SetupRqstTDD ::= SEQUENCE {
	tdd-ChannelisationCodeLCR				TDD-ChannelisationCodeLCR,
	timeSlotLCR								TimeSlotLCR,
	midambleShiftLCR						MidambleShiftLCR,
	second-TDD-ChannelisationCodeLCR		TDD-ChannelisationCodeLCR,
	tSTD-Indicator							TSTD-Indicator,
--	iE-Extensions							ProtocolExtensionContainer { { MICH-LCR-Parameters-CTCH-SetupRqstTDD-ExtIEs } }		OPTIONAL,
	iE-Extensions							ProtocolExtensionContainer OPTIONAL,
	...
}

--MICH-LCR-Parameters-CTCH-SetupRqstTDD-ExtIEs NBAP-PROTOCOL-EXTENSION ::= {
--	...
--}

--Secondary-CCPCH-parameterExtendedList-CTCH-SetupRqstTDD ::= SEQUENCE (SIZE (1..maxNrOfSCCPCHsinExt)) OF Secondary-CCPCH-parameterItem-CTCH-SetupRqstTDD
Secondary-CCPCH-parameterExtendedList-CTCH-SetupRqstTDD ::= SEQUENCE (SIZE (1..232)) OF Secondary-CCPCH-parameterItem-CTCH-SetupRqstTDD
	-- Applicable to 3.84Mcps TDD only, used when more than maxNrOfSCCPCHs SCCPCHs are to be established.

--Secondary-CCPCH-LCR-parameterExtendedList-CTCH-SetupRqstTDD ::= SEQUENCE (SIZE (1..maxNrOfSCCPCHsLCRinExt)) OF Secondary-CCPCH-LCR-parameterItem-CTCH-SetupRqstTDD
Secondary-CCPCH-LCR-parameterExtendedList-CTCH-SetupRqstTDD ::= SEQUENCE (SIZE (1..88)) OF Secondary-CCPCH-LCR-parameterItem-CTCH-SetupRqstTDD
	-- Applicable to 1.28Mcps TDD only, used when more than maxNrOfSCCPCHLCRs SCCPCHs are to be established.

PRACH-CTCH-SetupRqstTDD ::= SEQUENCE {
	pRACH-Parameters-CTCH-SetupRqstTDD			PRACH-Parameters-CTCH-SetupRqstTDD,
--	iE-Extensions								ProtocolExtensionContainer  { { PRACH-CTCH-SetupRqstTDD-ExtIEs } }		OPTIONAL,
	iE-Extensions								ProtocolExtensionContainer OPTIONAL,
	...
}

--PRACH-CTCH-SetupRqstTDD-ExtIEs NBAP-PROTOCOL-EXTENSION ::= {
--	{ ID id-FPACH-LCR-Parameters-CTCH-SetupRqstTDD	CRITICALITY reject	EXTENSION FPACH-LCR-Parameters-CTCH-SetupRqstTDD	PRESENCE optional	},
	-- Mandatory for 1.28Mcps TDD, Not Applicable to 3.84Mcps TDD
--	...
--}

--PRACH-Parameters-CTCH-SetupRqstTDD ::= ProtocolIE-Single-Container {{ PRACH-ParametersIE-CTCH-SetupRqstTDD }}
PRACH-Parameters-CTCH-SetupRqstTDD ::= ProtocolIE-Single-Container

--PRACH-ParametersIE-CTCH-SetupRqstTDD NBAP-PROTOCOL-IES ::= {
--	{ ID id-PRACH-ParametersItem-CTCH-SetupRqstTDD		CRITICALITY reject	TYPE PRACH-ParametersItem-CTCH-SetupRqstTDD		PRESENCE optional }|
--	{ ID id-PRACH-LCR-ParametersList-CTCH-SetupRqstTDD	CRITICALITY reject	TYPE PRACH-LCR-ParametersList-CTCH-SetupRqstTDD	PRESENCE optional }
--}


PRACH-ParametersItem-CTCH-SetupRqstTDD ::= SEQUENCE {
	commonPhysicalChannelID						CommonPhysicalChannelID,
	tFCS										TFCS,
	timeslot									TimeSlot,
	tdd-ChannelisationCode						TDD-ChannelisationCode,
	maxPRACH-MidambleShifts						MaxPRACH-MidambleShifts,
	pRACH-Midamble 								PRACH-Midamble,
	rACH										RACH-Parameter-CTCH-SetupRqstTDD,
--	iE-Extensions								ProtocolExtensionContainer  { { PRACH-ParametersItem-CTCH-SetupRqstTDD-ExtIEs} }		OPTIONAL,
	iE-Extensions								ProtocolExtensionContainer OPTIONAL,
	...
}

--PRACH-ParametersItem-CTCH-SetupRqstTDD-ExtIEs NBAP-PROTOCOL-EXTENSION ::= {
--	...
--}

--RACH-Parameter-CTCH-SetupRqstTDD ::= ProtocolIE-Single-Container {{ RACH-ParameterIE-CTCH-SetupRqstTDD }}
RACH-Parameter-CTCH-SetupRqstTDD ::= ProtocolIE-Single-Container

--RACH-ParameterIE-CTCH-SetupRqstTDD NBAP-PROTOCOL-IES ::= {
--	{ ID id-RACH-ParameterItem-CTCH-SetupRqstTDD   CRITICALITY reject	TYPE RACH-ParameterItem-CTCH-SetupRqstTDD	PRESENCE mandatory }
--}

RACH-ParameterItem-CTCH-SetupRqstTDD ::= SEQUENCE {
	commonTransportChannelID					CommonTransportChannelID,
	uL-TransportFormatSet						TransportFormatSet,	-- For the UL
--	iE-Extensions								ProtocolExtensionContainer  { { RACH-ParameterItem-CTCH-SetupRqstTDD-ExtIEs} }		OPTIONAL,
	iE-Extensions								ProtocolExtensionContainer OPTIONAL,
	...
}

--RACH-ParameterItem-CTCH-SetupRqstTDD-ExtIEs NBAP-PROTOCOL-EXTENSION ::= {
--	{ ID id-bindingID					CRITICALITY ignore	EXTENSION BindingID					PRESENCE optional }|
		-- Shall be ignored if bearer establishment with ALCAP.
--	{ ID id-transportlayeraddress		CRITICALITY ignore	EXTENSION TransportLayerAddress		PRESENCE optional },
		-- Shall be ignored if bearer establishment with ALCAP.
--	...
--}

--PRACH-LCR-ParametersList-CTCH-SetupRqstTDD ::= SEQUENCE (SIZE (1..maxNrOfPRACHLCRs)) OF PRACH-LCR-ParametersItem-CTCH-SetupRqstTDD 
PRACH-LCR-ParametersList-CTCH-SetupRqstTDD ::= SEQUENCE (SIZE (1..8)) OF PRACH-LCR-ParametersItem-CTCH-SetupRqstTDD 

PRACH-LCR-ParametersItem-CTCH-SetupRqstTDD ::= SEQUENCE {
	commonPhysicalChannelID						CommonPhysicalChannelID,
	tFCS										TFCS,
	timeslotLCR									TimeSlotLCR,
	tdd-ChannelisationCodeLCR					TDD-ChannelisationCodeLCR,
	midambleShiftLCR							MidambleShiftLCR,
	rACH										RACH-Parameter-CTCH-SetupRqstTDD,
--	iE-Extensions								ProtocolExtensionContainer  { { PRACH-LCR-ParametersItem-CTCH-SetupRqstTDD-ExtIEs} }		OPTIONAL,
	iE-Extensions								ProtocolExtensionContainer OPTIONAL,
	...
}

--PRACH-LCR-ParametersItem-CTCH-SetupRqstTDD-ExtIEs NBAP-PROTOCOL-EXTENSION ::= {
--	...
--}

FPACH-LCR-Parameters-CTCH-SetupRqstTDD ::= SEQUENCE {
	commonPhysicalChannelID						CommonPhysicalChannelID,
 	tdd-ChannelisationCodeLCR					TDD-ChannelisationCodeLCR,
	timeslotLCR									TimeSlotLCR,
	midambleShiftLCR							MidambleShiftLCR,
	fPACH-Power									FPACH-Power,
--	iE-Extensions								ProtocolExtensionContainer  { { FPACH-LCR-ParametersItem-CTCH-SetupRqstTDD-ExtIEs} }		OPTIONAL,
	iE-Extensions								ProtocolExtensionContainer OPTIONAL,
	...
}

--FPACH-LCR-ParametersItem-CTCH-SetupRqstTDD-ExtIEs NBAP-PROTOCOL-EXTENSION ::= {
--	...
--}

-- **************************************************************
--
-- COMMON TRANSPORT CHANNEL SETUP RESPONSE
--
-- **************************************************************

--CommonTransportChannelSetupResponse ::= SEQUENCE {
--	protocolIEs				ProtocolIE-Container	{{CommonTransportChannelSetupResponse-IEs}},
--	protocolExtensions		ProtocolExtensionContainer	{{CommonTransportChannelSetupResponse-Extensions}}    OPTIONAL,
--	...
--}

CommonTransportChannelSetupResponse ::= SEQUENCE {
	protocolIEs				ProtocolIE-Container,
	protocolExtensions		ProtocolExtensionContainer	 OPTIONAL,
	...
}
--CommonTransportChannelSetupResponse-IEs NBAP-PROTOCOL-IES ::= {
--	{ ID id-FACH-ParametersList-CTCH-SetupRsp	CRITICALITY ignore	TYPE FACH-CommonTransportChannel-InformationResponse		PRESENCE	optional	}|
--	{ ID id-PCH-Parameters-CTCH-SetupRsp		CRITICALITY ignore	TYPE CommonTransportChannel-InformationResponse				PRESENCE	optional	}|
--	{ ID id-RACH-Parameters-CTCH-SetupRsp		CRITICALITY ignore	TYPE CommonTransportChannel-InformationResponse				PRESENCE	optional	}|
--	{ ID id-CriticalityDiagnostics				CRITICALITY ignore	TYPE CriticalityDiagnostics					PRESENCE	optional	},
--	...
--}

--CommonTransportChannelSetupResponse-Extensions NBAP-PROTOCOL-EXTENSION ::= {
--	...
--}

--FACH-CommonTransportChannel-InformationResponse ::= SEQUENCE (SIZE (1..maxNrOfFACHs)) OF CommonTransportChannel-InformationResponse
FACH-CommonTransportChannel-InformationResponse ::= SEQUENCE (SIZE (1..8)) OF CommonTransportChannel-InformationResponse

-- **************************************************************
--
-- COMMON TRANSPORT CHANNEL SETUP FAILURE
--
-- **************************************************************

--CommonTransportChannelSetupFailure ::= SEQUENCE {
--	protocolIEs				ProtocolIE-Container	{{CommonTransportChannelSetupFailure-IEs}},
--	protocolExtensions		ProtocolExtensionContainer	{{CommonTransportChannelSetupFailure-Extensions}}     OPTIONAL,
--	...
--}
CommonTransportChannelSetupFailure ::= SEQUENCE {
	protocolIEs				ProtocolIE-Container,
	protocolExtensions		ProtocolExtensionContainer	OPTIONAL,
	...
}
--CommonTransportChannelSetupFailure-IEs NBAP-PROTOCOL-IES ::= {
--	{ ID	id-Cause					CRITICALITY	ignore		TYPE	Cause						PRESENCE	mandatory	}|
--	{ ID	id-CriticalityDiagnostics	CRITICALITY	ignore		TYPE	CriticalityDiagnostics		PRESENCE	optional		},
--	...
--}

--CommonTransportChannelSetupFailure-Extensions NBAP-PROTOCOL-EXTENSION ::= {
--	...
--}

-- **************************************************************
--
-- COMMON TRANSPORT CHANNEL RECONFIGURATION REQUEST FDD
--
-- **************************************************************

--CommonTransportChannelReconfigurationRequestFDD ::= SEQUENCE {
--	protocolIEs				ProtocolIE-Container	{{CommonTransportChannelReconfigurationRequestFDD-IEs}},
--	protocolExtensions		ProtocolExtensionContainer	{{CommonTransportChannelReconfigurationRequestFDD-Extensions}}		OPTIONAL,
--	...
--}
CommonTransportChannelReconfigurationRequestFDD ::= SEQUENCE {
	protocolIEs				ProtocolIE-Container,
	protocolExtensions		ProtocolExtensionContainer	OPTIONAL,
	...
}
--CommonTransportChannelReconfigurationRequestFDD-IEs NBAP-PROTOCOL-IES ::= {
--	{ ID id-C-ID											CRITICALITY reject	TYPE C-ID							PRESENCE mandatory }|
--	{ ID id-ConfigurationGenerationID						CRITICALITY reject	TYPE ConfigurationGenerationID					PRESENCE mandatory }|
--	{ ID id-CommonPhysicalChannelType-CTCH-ReconfRqstFDD	CRITICALITY reject	TYPE CommonPhysicalChannelType-CTCH-ReconfRqstFDD	PRESENCE mandatory },
--	...
--}

--CommonTransportChannelReconfigurationRequestFDD-Extensions NBAP-PROTOCOL-EXTENSION ::= {
--	...
--}

CommonPhysicalChannelType-CTCH-ReconfRqstFDD ::= CHOICE {
	secondary-CCPCH-parameters		Secondary-CCPCHList-CTCH-ReconfRqstFDD,
	pRACH-parameters				PRACHList-CTCH-ReconfRqstFDD,
	notUsed-cPCH-parameters			NULL,
	...
}

Secondary-CCPCHList-CTCH-ReconfRqstFDD ::= SEQUENCE {
	fACH-ParametersList-CTCH-ReconfRqstFDD		FACH-ParametersList-CTCH-ReconfRqstFDD	OPTIONAL,
	pCH-Parameters-CTCH-ReconfRqstFDD			PCH-Parameters-CTCH-ReconfRqstFDD		OPTIONAL,
	pICH-Parameters-CTCH-ReconfRqstFDD			PICH-Parameters-CTCH-ReconfRqstFDD		OPTIONAL,
--	iE-Extensions								ProtocolExtensionContainer { { Secondary-CCPCH-CTCH-ReconfRqstFDD-ExtIEs} } OPTIONAL,
	iE-Extensions								ProtocolExtensionContainer OPTIONAL,
	...
}

--Secondary-CCPCH-CTCH-ReconfRqstFDD-ExtIEs NBAP-PROTOCOL-EXTENSION ::= {
--	{ ID id-MICH-Parameters-CTCH-ReconfRqstFDD		CRITICALITY reject	EXTENSION MICH-Parameters-CTCH-ReconfRqstFDD			PRESENCE optional	},
--	...
--}

--FACH-ParametersList-CTCH-ReconfRqstFDD ::= ProtocolIE-Single-Container {{ FACH-ParametersListIEs-CTCH-ReconfRqstFDD }}
FACH-ParametersList-CTCH-ReconfRqstFDD ::= ProtocolIE-Single-Container

--FACH-ParametersListIEs-CTCH-ReconfRqstFDD NBAP-PROTOCOL-IES ::= {
--	{ ID id-FACH-ParametersListIE-CTCH-ReconfRqstFDD	CRITICALITY reject	TYPE FACH-ParametersListIE-CTCH-ReconfRqstFDD 	PRESENCE	mandatory }
--}

--FACH-ParametersListIE-CTCH-ReconfRqstFDD ::= SEQUENCE (SIZE (1..maxFACHCell)) OF FACH-ParametersItem-CTCH-ReconfRqstFDD
FACH-ParametersListIE-CTCH-ReconfRqstFDD ::= SEQUENCE (SIZE (1..256)) OF FACH-ParametersItem-CTCH-ReconfRqstFDD

FACH-ParametersItem-CTCH-ReconfRqstFDD ::= SEQUENCE {
	commonTransportChannelID				CommonTransportChannelID,
	maxFACH-Power							DL-Power		OPTIONAL,
	toAWS									ToAWS			OPTIONAL,
	toAWE									ToAWE			OPTIONAL,
--	iE-Extensions							ProtocolExtensionContainer  { { FACH-ParametersItem-CTCH-ReconfRqstFDD-ExtIEs} }		OPTIONAL,
	iE-Extensions							ProtocolExtensionContainer  OPTIONAL,
	...
}

--FACH-ParametersItem-CTCH-ReconfRqstFDD-ExtIEs NBAP-PROTOCOL-EXTENSION ::= {
--	...
--}

--PCH-Parameters-CTCH-ReconfRqstFDD ::= ProtocolIE-Single-Container {{ PCH-ParametersIE-CTCH-ReconfRqstFDD }}
PCH-Parameters-CTCH-ReconfRqstFDD ::= ProtocolIE-Single-Container

--PCH-ParametersIE-CTCH-ReconfRqstFDD NBAP-PROTOCOL-IES ::= {
--	{ ID id-PCH-ParametersItem-CTCH-ReconfRqstFDD	CRITICALITY reject	TYPE PCH-ParametersItem-CTCH-ReconfRqstFDD 	PRESENCE	mandatory }
--}

PCH-ParametersItem-CTCH-ReconfRqstFDD ::= SEQUENCE {
	commonTransportChannelID				CommonTransportChannelID,
	pCH-Power								DL-Power		OPTIONAL,
	toAWS									ToAWS			OPTIONAL,
	toAWE									ToAWE			OPTIONAL,
--	iE-Extensions							ProtocolExtensionContainer  { { PCH-ParametersItem-CTCH-ReconfRqstFDD-ExtIEs} }			OPTIONAL,
	iE-Extensions							ProtocolExtensionContainer  OPTIONAL,
	...
}

--PCH-ParametersItem-CTCH-ReconfRqstFDD-ExtIEs NBAP-PROTOCOL-EXTENSION ::= {
--	...
--}

--PICH-Parameters-CTCH-ReconfRqstFDD ::= ProtocolIE-Single-Container {{ PICH-ParametersIE-CTCH-ReconfRqstFDD }}
PICH-Parameters-CTCH-ReconfRqstFDD ::= ProtocolIE-Single-Container

--PICH-ParametersIE-CTCH-ReconfRqstFDD NBAP-PROTOCOL-IES ::= {
--	{ ID id-PICH-ParametersItem-CTCH-ReconfRqstFDD	CRITICALITY reject	TYPE PICH-ParametersItem-CTCH-ReconfRqstFDD 	PRESENCE	mandatory }
--}

PICH-ParametersItem-CTCH-ReconfRqstFDD ::= SEQUENCE {
	commonPhysicalChannelID				CommonPhysicalChannelID,
	pICH-Power							PICH-Power		OPTIONAL,
--	iE-Extensions						ProtocolExtensionContainer  { { PICH-ParametersItem-CTCH-ReconfRqstFDD-ExtIEs} }		OPTIONAL,
	iE-Extensions						ProtocolExtensionContainer  OPTIONAL,
	...
}

--PICH-ParametersItem-CTCH-ReconfRqstFDD-ExtIEs NBAP-PROTOCOL-EXTENSION ::= {
--	...
--}

MICH-Parameters-CTCH-ReconfRqstFDD ::= SEQUENCE {
	commonPhysicalChannelID				CommonPhysicalChannelID,
	mICH-Power							PICH-Power															OPTIONAL,
--	iE-Extensions						ProtocolExtensionContainer  { { MICH-Parameters-CTCH-ReconfRqstFDD-ExtIEs} }		OPTIONAL,
	iE-Extensions						ProtocolExtensionContainer  OPTIONAL,
	...
}

--MICH-Parameters-CTCH-ReconfRqstFDD-ExtIEs NBAP-PROTOCOL-EXTENSION ::= {
--	...
--}

PRACHList-CTCH-ReconfRqstFDD ::= SEQUENCE {
	pRACH-ParametersList-CTCH-ReconfRqstFDD		PRACH-ParametersList-CTCH-ReconfRqstFDD	OPTIONAL,
	aICH-ParametersList-CTCH-ReconfRqstFDD		AICH-ParametersList-CTCH-ReconfRqstFDD	OPTIONAL,
--	iE-Extensions								ProtocolExtensionContainer { { PRACH-CTCH-ReconfRqstFDD-ExtIEs} } OPTIONAL,
	iE-Extensions								ProtocolExtensionContainer OPTIONAL,
	...
}

--PRACH-CTCH-ReconfRqstFDD-ExtIEs NBAP-PROTOCOL-EXTENSION ::= {
--	...
--}

--PRACH-ParametersList-CTCH-ReconfRqstFDD ::= ProtocolIE-Single-Container {{ PRACH-ParametersListIEs-CTCH-ReconfRqstFDD }}
PRACH-ParametersList-CTCH-ReconfRqstFDD ::= ProtocolIE-Single-Container

--PRACH-ParametersListIEs-CTCH-ReconfRqstFDD NBAP-PROTOCOL-IES ::= {
--	{ ID id-PRACH-ParametersListIE-CTCH-ReconfRqstFDD	CRITICALITY reject	TYPE PRACH-ParametersListIE-CTCH-ReconfRqstFDD 	PRESENCE	mandatory }
--}

--PRACH-ParametersListIE-CTCH-ReconfRqstFDD ::= SEQUENCE (SIZE (1..maxPRACHCell)) OF PRACH-ParametersItem-CTCH-ReconfRqstFDD
PRACH-ParametersListIE-CTCH-ReconfRqstFDD ::= SEQUENCE (SIZE (1..16)) OF PRACH-ParametersItem-CTCH-ReconfRqstFDD

PRACH-ParametersItem-CTCH-ReconfRqstFDD ::= SEQUENCE {
	commonPhysicalChannelID					CommonPhysicalChannelID,
	preambleSignatures						PreambleSignatures														OPTIONAL,
	allowedSlotFormatInformation			AllowedSlotFormatInformationList-CTCH-ReconfRqstFDD						OPTIONAL,
	rACH-SubChannelNumbers					RACH-SubChannelNumbers													OPTIONAL,
--	iE-Extensions							ProtocolExtensionContainer  { { PRACH-ParametersItem-CTCH-ReconfRqstFDD-ExtIEs} }	OPTIONAL,
	iE-Extensions							ProtocolExtensionContainer  OPTIONAL,
	...
}

--PRACH-ParametersItem-CTCH-ReconfRqstFDD-ExtIEs NBAP-PROTOCOL-EXTENSION ::= {
--	...
--}

--AllowedSlotFormatInformationList-CTCH-ReconfRqstFDD ::= SEQUENCE (SIZE (1.. maxNrOfSlotFormatsPRACH)) OF AllowedSlotFormatInformationItem-CTCH-ReconfRqstFDD
AllowedSlotFormatInformationList-CTCH-ReconfRqstFDD ::= SEQUENCE (SIZE (1.. 8)) OF AllowedSlotFormatInformationItem-CTCH-ReconfRqstFDD

AllowedSlotFormatInformationItem-CTCH-ReconfRqstFDD ::= SEQUENCE {
	rACH-SlotFormat							RACH-SlotFormat,
--	iE-Extensions							ProtocolExtensionContainer  { { AllowedSlotFormatInformationItem-CTCH-ReconfRqstFDD-ExtIEs} }		OPTIONAL,
	iE-Extensions							ProtocolExtensionContainer  OPTIONAL,
	...
}

--AllowedSlotFormatInformationItem-CTCH-ReconfRqstFDD-ExtIEs NBAP-PROTOCOL-EXTENSION ::= {
--	...
--}

--AICH-ParametersList-CTCH-ReconfRqstFDD ::= ProtocolIE-Single-Container {{ AICH-ParametersListIEs-CTCH-ReconfRqstFDD }}
AICH-ParametersList-CTCH-ReconfRqstFDD ::= ProtocolIE-Single-Container

--AICH-ParametersListIEs-CTCH-ReconfRqstFDD NBAP-PROTOCOL-IES ::= {
--	{ ID id-AICH-ParametersListIE-CTCH-ReconfRqstFDD	CRITICALITY reject	TYPE AICH-ParametersListIE-CTCH-ReconfRqstFDD 	PRESENCE	mandatory }
--}

--AICH-ParametersListIE-CTCH-ReconfRqstFDD ::= SEQUENCE (SIZE (1..maxPRACHCell)) OF AICH-ParametersItem-CTCH-ReconfRqstFDD
AICH-ParametersListIE-CTCH-ReconfRqstFDD ::= SEQUENCE (SIZE (1..16)) OF AICH-ParametersItem-CTCH-ReconfRqstFDD

AICH-ParametersItem-CTCH-ReconfRqstFDD ::= SEQUENCE {
	commonPhysicalChannelID				CommonPhysicalChannelID,
	aICH-Power							AICH-Power		OPTIONAL,
--	iE-Extensions						ProtocolExtensionContainer  { { AICH-ParametersItemIE-CTCH-ReconfRqstFDD-ExtIEs} }		OPTIONAL,
	iE-Extensions						ProtocolExtensionContainer  OPTIONAL,
	...
}

--AICH-ParametersItemIE-CTCH-ReconfRqstFDD-ExtIEs NBAP-PROTOCOL-EXTENSION ::= {
--	...
--}

-- **************************************************************
--
-- COMMON TRANSPORT CHANNEL RECONFIGURATION REQUEST TDD
--
-- **************************************************************

--CommonTransportChannelReconfigurationRequestTDD ::= SEQUENCE {
--	protocolIEs				ProtocolIE-Container	{{CommonTransportChannelReconfigurationRequestTDD-IEs}},
--	protocolExtensions		ProtocolExtensionContainer	{{CommonTransportChannelReconfigurationRequestTDD-Extensions}}		OPTIONAL,
--	...
--}
CommonTransportChannelReconfigurationRequestTDD ::= SEQUENCE {
	protocolIEs				ProtocolIE-Container,
	protocolExtensions		ProtocolExtensionContainer	OPTIONAL,
	...
}
--CommonTransportChannelReconfigurationRequestTDD-IEs NBAP-PROTOCOL-IES ::= {
--	{ ID id-C-ID									CRITICALITY reject	TYPE C-ID						PRESENCE mandatory }|
--	{ ID id-ConfigurationGenerationID				CRITICALITY reject	TYPE ConfigurationGenerationID		PRESENCE mandatory }|
--	{ ID id-Secondary-CCPCH-Parameters-CTCH-ReconfRqstTDD	CRITICALITY reject	TYPE Secondary-CCPCH-Parameters-CTCH-ReconfRqstTDD		PRESENCE optional	}|
--	{ ID id-PICH-Parameters-CTCH-ReconfRqstTDD		CRITICALITY reject	TYPE PICH-Parameters-CTCH-ReconfRqstTDD		PRESENCE optional }|
--	{ ID id-FACH-ParametersList-CTCH-ReconfRqstTDD	CRITICALITY reject	TYPE FACH-ParametersList-CTCH-ReconfRqstTDD		PRESENCE optional }|
--	{ ID id-PCH-Parameters-CTCH-ReconfRqstTDD		CRITICALITY reject	TYPE PCH-Parameters-CTCH-ReconfRqstTDD		PRESENCE optional },
--	...
--}

--CommonTransportChannelReconfigurationRequestTDD-Extensions NBAP-PROTOCOL-EXTENSION ::= {
--	{ ID id-FPACH-LCR-Parameters-CTCH-ReconfRqstTDD		CRITICALITY reject	EXTENSION FPACH-LCR-Parameters-CTCH-ReconfRqstTDD	PRESENCE optional	}|
	-- Mandatory For 1.28Mcps TDD, Not Applicable to 3.84Mcps TDD
--	{ ID id-MICH-Parameters-CTCH-ReconfRqstTDD			CRITICALITY reject	EXTENSION MICH-Parameters-CTCH-ReconfRqstTDD			PRESENCE optional	},
--	...
--}

Secondary-CCPCH-Parameters-CTCH-ReconfRqstTDD::= SEQUENCE {
	cCTrCH-ID						CCTrCH-ID,
	secondaryCCPCHList				Secondary-CCPCHList-CTCH-ReconfRqstTDD			OPTIONAL,
--	iE-Extensions					ProtocolExtensionContainer  { { Secondary-CCPCH-CTCH-ReconfRqstTDD-ExtIEs} }		OPTIONAL,
	iE-Extensions					ProtocolExtensionContainer  OPTIONAL,
	...
}

--Secondary-CCPCH-CTCH-ReconfRqstTDD-ExtIEs NBAP-PROTOCOL-EXTENSION ::= {
--	{ ID id-Additional-S-CCPCH-Parameters-CTCH-ReconfRqstTDD			CRITICALITY reject	EXTENSION Secondary-CCPCH-parameterExtendedList-CTCH-ReconfRqstTDD		PRESENCE optional	}|
	-- Applicable to 3.84Mcps TDD only, used when more than maxNrOfSCCPCHs SCCPCHs are to be reconfigured.
--	{ ID id-Additional-S-CCPCH-LCR-Parameters-CTCH-ReconfRqstTDD		CRITICALITY reject	EXTENSION Secondary-CCPCH-LCR-parameterExtendedList-CTCH-ReconfRqstTDD	PRESENCE optional	},
	-- Applicable to 1.28Mcps TDD only, used when more than maxNrOfSCCPCHs SCCPCHs are to be reconfigured.
--	...
--}

--Secondary-CCPCHList-CTCH-ReconfRqstTDD ::= ProtocolIE-Single-Container {{ Secondary-CCPCHListIEs-CTCH-ReconfRqstTDD }}
Secondary-CCPCHList-CTCH-ReconfRqstTDD ::= ProtocolIE-Single-Container

--Secondary-CCPCHListIEs-CTCH-ReconfRqstTDD NBAP-PROTOCOL-IES ::= {
--	{ ID id-Secondary-CCPCHListIE-CTCH-ReconfRqstTDD	CRITICALITY reject	TYPE Secondary-CCPCHListIE-CTCH-ReconfRqstTDD 	PRESENCE	mandatory }
--}

--Secondary-CCPCHListIE-CTCH-ReconfRqstTDD ::= SEQUENCE (SIZE (1..maxNrOfSCCPCHs)) OF Secondary-CCPCHItem-CTCH-ReconfRqstTDD
Secondary-CCPCHListIE-CTCH-ReconfRqstTDD ::= SEQUENCE (SIZE (1..8)) OF Secondary-CCPCHItem-CTCH-ReconfRqstTDD

Secondary-CCPCHItem-CTCH-ReconfRqstTDD ::= SEQUENCE {
	commonPhysicalChannelID				CommonPhysicalChannelID,
	sCCPCH-Power						DL-Power		OPTIONAL,
--	iE-Extensions						ProtocolExtensionContainer  { { Secondary-CCPCHItem-CTCH-ReconfRqstTDD-ExtIEs} }		OPTIONAL,
	iE-Extensions						ProtocolExtensionContainer  OPTIONAL,
	...
}

--Secondary-CCPCHItem-CTCH-ReconfRqstTDD-ExtIEs NBAP-PROTOCOL-EXTENSION ::= {
--	...
--}

PICH-Parameters-CTCH-ReconfRqstTDD	 ::= SEQUENCE {
	commonPhysicalChannelID				CommonPhysicalChannelID,
	pICH-Power							PICH-Power		OPTIONAL,
--	iE-Extensions						ProtocolExtensionContainer  { { PICH-Parameters-CTCH-ReconfRqstTDD-ExtIEs} }		OPTIONAL,
	iE-Extensions						ProtocolExtensionContainer  OPTIONAL,
	...
}

--PICH-Parameters-CTCH-ReconfRqstTDD-ExtIEs NBAP-PROTOCOL-EXTENSION ::= {
--	...
--}

--FACH-ParametersList-CTCH-ReconfRqstTDD ::= SEQUENCE (SIZE (0..maxNrOfFACHs)) OF FACH-ParametersItem-CTCH-ReconfRqstTDD
FACH-ParametersList-CTCH-ReconfRqstTDD ::= SEQUENCE (SIZE (0..8)) OF FACH-ParametersItem-CTCH-ReconfRqstTDD

FACH-ParametersItem-CTCH-ReconfRqstTDD ::= SEQUENCE {
 	commonTransportChannelID		CommonTransportChannelID,
	toAWS							ToAWS			OPTIONAL,
 	toAWE							ToAWE			OPTIONAL,
--	iE-Extensions					ProtocolExtensionContainer  { { FACH-ParametersItem-CTCH-ReconfRqstTDD-ExtIEs} }		OPTIONAL,
	iE-Extensions					ProtocolExtensionContainer  OPTIONAL,
	...
}

--FACH-ParametersItem-CTCH-ReconfRqstTDD-ExtIEs NBAP-PROTOCOL-EXTENSION ::= {
--	{ ID	id-maxFACH-Power-LCR-CTCH-ReconfRqstTDD			CRITICALITY	reject		EXTENSION 	DL-Power		PRESENCE 	optional	},
	--  Applicable to 1.28Mcps TDD only
--	...
--}

PCH-Parameters-CTCH-ReconfRqstTDD ::= SEQUENCE {
	commonTransportChannelID		CommonTransportChannelID,
	toAWS							ToAWS			OPTIONAL,
	toAWE							ToAWE			OPTIONAL,
--	iE-Extensions					ProtocolExtensionContainer  { { PCH-Parameters-CTCH-ReconfRqstTDD-ExtIEs} }		OPTIONAL,
	iE-Extensions					ProtocolExtensionContainer  OPTIONAL,
	...
}

--PCH-Parameters-CTCH-ReconfRqstTDD-ExtIEs NBAP-PROTOCOL-EXTENSION ::= {
--	{ ID id-PCH-Power-LCR-CTCH-ReconfRqstTDD		CRITICALITY reject		EXTENSION DL-Power		PRESENCE optional },
--	...
	-- Applicable to 1.28Mcps TDD only
--}

FPACH-LCR-Parameters-CTCH-ReconfRqstTDD ::= SEQUENCE {
	commonPhysicalChannelId			CommonPhysicalChannelID,
	fPACHPower						FPACH-Power		OPTIONAL,
--	iE-Extensions					ProtocolExtensionContainer  { { FPACH-LCR-Parameters-CTCH-ReconfRqstTDD-ExtIEs} }		OPTIONAL,
	iE-Extensions					ProtocolExtensionContainer  OPTIONAL,
	...
}

--FPACH-LCR-Parameters-CTCH-ReconfRqstTDD-ExtIEs NBAP-PROTOCOL-EXTENSION ::= {
--	...
--}
MICH-Parameters-CTCH-ReconfRqstTDD ::= SEQUENCE {
	commonPhysicalChannelID				CommonPhysicalChannelID,
	mICH-Power							PICH-Power															OPTIONAL,
--	iE-Extensions						ProtocolExtensionContainer  { { MICH-Parameters-CTCH-ReconfRqstTDD-ExtIEs} }		OPTIONAL,
	iE-Extensions						ProtocolExtensionContainer  OPTIONAL,
	...
}

--MICH-Parameters-CTCH-ReconfRqstTDD-ExtIEs NBAP-PROTOCOL-EXTENSION ::= {
--	...
--}

--Secondary-CCPCH-parameterExtendedList-CTCH-ReconfRqstTDD ::= SEQUENCE (SIZE (1..maxNrOfSCCPCHsinExt)) OF Secondary-CCPCHItem-CTCH-ReconfRqstTDD
Secondary-CCPCH-parameterExtendedList-CTCH-ReconfRqstTDD ::= SEQUENCE (SIZE (1..232)) OF Secondary-CCPCHItem-CTCH-ReconfRqstTDD
	-- Applicable to 3.84Mcps TDD only, used when more than maxNrOfSCCPCHs SCCPCHs are to be reconfigured.

--Secondary-CCPCH-LCR-parameterExtendedList-CTCH-ReconfRqstTDD ::= SEQUENCE (SIZE (1..maxNrOfSCCPCHsLCRinExt)) OF Secondary-CCPCHItem-CTCH-ReconfRqstTDD
Secondary-CCPCH-LCR-parameterExtendedList-CTCH-ReconfRqstTDD ::= SEQUENCE (SIZE (1..88)) OF Secondary-CCPCHItem-CTCH-ReconfRqstTDD
	-- Applicable to 1.28Mcps TDD only, used when more than maxNrOfSCCPCHs SCCPCHs are to be reconfigured.

-- **************************************************************
--
-- COMMON TRANSPORT CHANNEL RECONFIGURATION RESPONSE
--
-- **************************************************************

--CommonTransportChannelReconfigurationResponse ::= SEQUENCE {
--	protocolIEs				ProtocolIE-Container	{{CommonTransportChannelReconfigurationResponse-IEs}},
--	protocolExtensions		ProtocolExtensionContainer	{{CommonTransportChannelReconfigurationResponse-Extensions}}		OPTIONAL,
--	...
--}
CommonTransportChannelReconfigurationResponse ::= SEQUENCE {
	protocolIEs				ProtocolIE-Container,
	protocolExtensions		ProtocolExtensionContainer	OPTIONAL,
	...
}

--CommonTransportChannelReconfigurationResponse-IEs NBAP-PROTOCOL-IES ::= {	
--	{ ID	id-CriticalityDiagnostics		CRITICALITY		ignore			TYPE	CriticalityDiagnostics		PRESENCE	optional},
--	...
--}

--CommonTransportChannelReconfigurationResponse-Extensions NBAP-PROTOCOL-EXTENSION ::= {
--	...
--}

-- **************************************************************
--
-- COMMON TRANSPORT CHANNEL RECONFIGURATION FAILURE
--
-- **************************************************************

--CommonTransportChannelReconfigurationFailure ::= SEQUENCE {
--	protocolIEs				ProtocolIE-Container	{{CommonTransportChannelReconfigurationFailure-IEs}},
--	protocolExtensions		ProtocolExtensionContainer	{{CommonTransportChannelReconfigurationFailure-Extensions}}          OPTIONAL,
--	...
--}
CommonTransportChannelReconfigurationFailure ::= SEQUENCE {
	protocolIEs				ProtocolIE-Container,
	protocolExtensions		ProtocolExtensionContainer	OPTIONAL,
	...
}
--CommonTransportChannelReconfigurationFailure-IEs NBAP-PROTOCOL-IES ::= {
--	{ ID	id-Cause						CRITICALITY	ignore			TYPE	Cause					PRESENCE	mandatory	}|
--	{ ID	id-CriticalityDiagnostics		CRITICALITY	ignore			TYPE	CriticalityDiagnostics		PRESENCE	optional	},
--	...
--}

--CommonTransportChannelReconfigurationFailure-Extensions NBAP-PROTOCOL-EXTENSION ::= {
--	...
--}

-- **************************************************************
--
-- COMMON TRANSPORT CHANNEL DELETION REQUEST
--
-- **************************************************************

--CommonTransportChannelDeletionRequest ::= SEQUENCE {
--	protocolIEs					ProtocolIE-Container	{{CommonTransportChannelDeletionRequest-IEs}},
--	protocolExtensions			ProtocolExtensionContainer	{{CommonTransportChannelDeletionRequest-Extensions}}        	OPTIONAL,
--	...
--}
CommonTransportChannelDeletionRequest ::= SEQUENCE {
	protocolIEs					ProtocolIE-Container,
	protocolExtensions			ProtocolExtensionContainer	OPTIONAL,
	...
}

--CommonTransportChannelDeletionRequest-IEs NBAP-PROTOCOL-IES ::= {
--	{ ID	id-C-ID								CRITICALITY	reject		TYPE	C-ID				PRESENCE mandatory}|
--	{ ID	id-CommonPhysicalChannelID			CRITICALITY	reject		TYPE	CommonPhysicalChannelID	PRESENCE mandatory}|
--	{ ID	id-ConfigurationGenerationID		CRITICALITY	reject		TYPE	ConfigurationGenerationID	PRESENCE mandatory},
--	...
--}

--CommonTransportChannelDeletionRequest-Extensions NBAP-PROTOCOL-EXTENSION ::= {
--	...
--}

-- **************************************************************
--
-- COMMON TRANSPORT CHANNEL DELETION RESPONSE
--
-- **************************************************************

--CommonTransportChannelDeletionResponse ::= SEQUENCE {
--	protocolIEs				ProtocolIE-Container	{{CommonTransportChannelDeletionResponse-IEs}},
--	protocolExtensions		ProtocolExtensionContainer	{{CommonTransportChannelDeletionResponse-Extensions}}     		OPTIONAL,
--	...
--}

CommonTransportChannelDeletionResponse ::= SEQUENCE {
	protocolIEs				ProtocolIE-Container,
	protocolExtensions		ProtocolExtensionContainer OPTIONAL,
	...
}

--CommonTransportChannelDeletionResponse-IEs NBAP-PROTOCOL-IES ::= {
--	{ ID	id-CriticalityDiagnostics		CRITICALITY		ignore		TYPE	CriticalityDiagnostics		PRESENCE	optional},
--	...
--}

--CommonTransportChannelDeletionResponse-Extensions NBAP-PROTOCOL-EXTENSION ::= {
--	...
--}

-- **************************************************************
--
-- BLOCK RESOURCE REQUEST
--
-- **************************************************************

--BlockResourceRequest ::= SEQUENCE {
--	protocolIEs				ProtocolIE-Container       {{BlockResourceRequest-IEs}},
--	protocolExtensions		ProtocolExtensionContainer	{{BlockResourceRequest-Extensions}}                   OPTIONAL,
--	...
--}
BlockResourceRequest ::= SEQUENCE {
	protocolIEs				ProtocolIE-Container,
	protocolExtensions		ProtocolExtensionContainer OPTIONAL,
	...
}

--BlockResourceRequest-IEs NBAP-PROTOCOL-IES ::= {
--	{ ID	id-C-ID								CRITICALITY	reject		TYPE	C-ID						PRESENCE	mandatory	}|
--	{ ID	id-BlockingPriorityIndicator		CRITICALITY	reject		TYPE	BlockingPriorityIndicator			PRESENCE	mandatory	}|
--	{ ID	id-ShutdownTimer					CRITICALITY	reject		TYPE	ShutdownTimer				PRESENCE	conditional	},
	-- The IE shall be present if the Blocking Priority Indicator IE indicates "Normal Priority"--
--	...
--}

--BlockResourceRequest-Extensions NBAP-PROTOCOL-EXTENSION ::= {
--	...
--}

-- **************************************************************
--
-- BLOCK RESOURCE RESPONSE
--
-- **************************************************************

--BlockResourceResponse ::= SEQUENCE {
--	protocolIEs					ProtocolIE-Container       {{BlockResourceResponse-IEs}},
--	protocolExtensions			ProtocolExtensionContainer	{{BlockResourceResponse-Extensions}}		OPTIONAL,
--	...
--}
BlockResourceResponse ::= SEQUENCE {
	protocolIEs					ProtocolIE-Container,
	protocolExtensions			ProtocolExtensionContainer	OPTIONAL,
	...
}
--BlockResourceResponse-IEs NBAP-PROTOCOL-IES ::= {
--	{ ID	id-CriticalityDiagnostics		CRITICALITY		ignore		TYPE	CriticalityDiagnostics		PRESENCE	optional},
--	...
--}

--BlockResourceResponse-Extensions NBAP-PROTOCOL-EXTENSION ::= {
--	...
--}

-- **************************************************************
--
-- BLOCK RESOURCE FAILURE
--
-- **************************************************************

--BlockResourceFailure ::= SEQUENCE {
--	protocolIEs				ProtocolIE-Container       {{BlockResourceFailure-IEs}},
--	protocolExtensions		ProtocolExtensionContainer	{{BlockResourceFailure-Extensions}}		OPTIONAL,
--	...
--}
BlockResourceFailure ::= SEQUENCE {
	protocolIEs				ProtocolIE-Container,
	protocolExtensions		ProtocolExtensionContainer	OPTIONAL,
	...
}
--BlockResourceFailure-IEs NBAP-PROTOCOL-IES ::= {
--	{ ID	id-Cause						CRITICALITY		ignore		TYPE	Cause						PRESENCE	mandatory	}|
--	{ ID	id-CriticalityDiagnostics		CRITICALITY		ignore		TYPE	CriticalityDiagnostics 		PRESENCE	optional	},
--	...
--}

--BlockResourceFailure-Extensions NBAP-PROTOCOL-EXTENSION ::= {
--	...
--}

-- **************************************************************
--
-- UNBLOCK RESOURCE INDICATION
--
-- **************************************************************

--UnblockResourceIndication ::= SEQUENCE {
--	protocolIEs				ProtocolIE-Container	{{UnblockResourceIndication-IEs}},
--	protocolExtensions		ProtocolExtensionContainer	{{UnblockResourceIndication-Extensions}}    OPTIONAL,
--	...
--}
UnblockResourceIndication ::= SEQUENCE {
	protocolIEs				ProtocolIE-Container,
	protocolExtensions		ProtocolExtensionContainer	OPTIONAL,
	...
}
--UnblockResourceIndication-IEs NBAP-PROTOCOL-IES ::= {
--	{ ID	id-C-ID			CRITICALITY		ignore		TYPE	C-ID		PRESENCE	mandatory},
--	...
--}

--UnblockResourceIndication-Extensions NBAP-PROTOCOL-EXTENSION ::= {
--	...
--}
-- **************************************************************
--
-- AUDIT REQUIRED INDICATION
--
-- **************************************************************

--AuditRequiredIndication ::= SEQUENCE {
--	protocolIEs				ProtocolIE-Container	{{AuditRequiredIndication-IEs}},
--	protocolExtensions 		ProtocolExtensionContainer	{{AuditRequiredIndication-Extensions}}    	OPTIONAL,
--	...
--}
AuditRequiredIndication ::= SEQUENCE {
	protocolIEs				ProtocolIE-Container,
	protocolExtensions 		ProtocolExtensionContainer OPTIONAL,
	...
}

--AuditRequiredIndication-IEs NBAP-PROTOCOL-IES ::= {
--	...
--}

--AuditRequiredIndication-Extensions NBAP-PROTOCOL-EXTENSION ::= {
--	...
--}

-- **************************************************************
--
-- AUDIT REQUEST
--
-- **************************************************************

--AuditRequest ::= SEQUENCE {
--	protocolIEs					ProtocolIE-Container	{{AuditRequest-IEs}},
--	protocolExtensions			ProtocolExtensionContainer	{{AuditRequest-Extensions}}		OPTIONAL,
--	...
--}
AuditRequest ::= SEQUENCE {
	protocolIEs					ProtocolIE-Container,
	protocolExtensions			ProtocolExtensionContainer	OPTIONAL,
	...
}
--AuditRequest-IEs NBAP-PROTOCOL-IES ::= {
--	{ ID	id-Start-Of-Audit-Sequence-Indicator		CRITICALITY		reject	TYPE Start-Of-Audit-Sequence-Indicator	 	PRESENCE  mandatory },
--	...
--}

--AuditRequest-Extensions NBAP-PROTOCOL-EXTENSION ::= {
--	...
--}

-- **************************************************************
--
-- AUDIT RESPONSE
--
-- **************************************************************

--AuditResponse ::= SEQUENCE {
--	protocolIEs					ProtocolIE-Container	{{AuditResponse-IEs}},
--	protocolExtensions			ProtocolExtensionContainer	{{AuditResponse-Extensions}}		OPTIONAL,
--	...
--}
AuditResponse ::= SEQUENCE {
	protocolIEs					ProtocolIE-Container,
	protocolExtensions			ProtocolExtensionContainer	OPTIONAL,
	...
}

--AuditResponse-IEs NBAP-PROTOCOL-IES ::= {
--	{ ID id-End-Of-Audit-Sequence-Indicator				CRITICALITY ignore	TYPE End-Of-Audit-Sequence-Indicator				PRESENCE mandatory }|
--	{ ID id-Cell-InformationList-AuditRsp				CRITICALITY ignore	TYPE Cell-InformationList-AuditRsp				PRESENCE optional }|
--	{ ID id-CCP-InformationList-AuditRsp				CRITICALITY ignore	TYPE CCP-InformationList-AuditRsp				PRESENCE optional }|
	-- CCP (Communication Control Port) --
--	{ ID id-Local-Cell-InformationList-AuditRsp			CRITICALITY ignore	TYPE Local-Cell-InformationList-AuditRsp			PRESENCE optional }|
--	{ ID id-Local-Cell-Group-InformationList-AuditRsp	CRITICALITY ignore	TYPE Local-Cell-Group-InformationList-AuditRsp	PRESENCE optional }|
--	{ ID id-CriticalityDiagnostics						CRITICALITY ignore	TYPE CriticalityDiagnostics				PRESENCE optional },
--	...
--}

--AuditResponse-Extensions NBAP-PROTOCOL-EXTENSION ::= {
--	{ ID id-Power-Local-Cell-Group-InformationList-AuditRsp	CRITICALITY ignore	EXTENSION Power-Local-Cell-Group-InformationList-AuditRsp		PRESENCE optional },
--	...
--}

--Cell-InformationList-AuditRsp ::= SEQUENCE (SIZE (1..maxCellinNodeB)) OF ProtocolIE-Single-Container {{ Cell-InformationItemIE-AuditRsp}}
Cell-InformationList-AuditRsp ::= SEQUENCE (SIZE (1..256)) OF ProtocolIE-Single-Container

--Cell-InformationItemIE-AuditRsp NBAP-PROTOCOL-IES ::= {
--	{ ID	id-Cell-InformationItem-AuditRsp		CRITICALITY ignore		TYPE Cell-InformationItem-AuditRsp			PRESENCE optional	}
--}

Cell-InformationItem-AuditRsp ::= SEQUENCE {
	c-ID									C-ID,
	configurationGenerationID				ConfigurationGenerationID,
	resourceOperationalState				ResourceOperationalState,
	availabilityStatus						AvailabilityStatus,
	local-Cell-ID							Local-Cell-ID,
	primary-SCH-Information					P-SCH-Information-AuditRsp					OPTIONAL,
	secondary-SCH-Information				S-SCH-Information-AuditRsp					OPTIONAL,
	primary-CPICH-Information				P-CPICH-Information-AuditRsp				OPTIONAL,
	secondary-CPICH-InformationList			S-CPICH-InformationList-AuditRsp			OPTIONAL,
	primary-CCPCH-Information				P-CCPCH-Information-AuditRsp				OPTIONAL,
	bCH-Information							BCH-Information-AuditRsp					OPTIONAL,
	secondary-CCPCH-InformationList			S-CCPCH-InformationList-AuditRsp			OPTIONAL,
	pCH-Information							PCH-Information-AuditRsp					OPTIONAL,
	pICH-Information						PICH-Information-AuditRsp					OPTIONAL,
	fACH-InformationList					FACH-InformationList-AuditRsp				OPTIONAL,
	pRACH-InformationList					PRACH-InformationList-AuditRsp				OPTIONAL,
	rACH-InformationList					RACH-InformationList-AuditRsp				OPTIONAL,
	aICH-InformationList					AICH-InformationList-AuditRsp				OPTIONAL,
	notUsed-1-pCPCH-InformationList			NULL										OPTIONAL,
	notUsed-2-cPCH-InformationList			NULL										OPTIONAL,
	notUsed-3-aP-AICH-InformationList		NULL										OPTIONAL,
	notUsed-4-cDCA-ICH-InformationList		NULL										OPTIONAL,
	sCH-Information							SCH-Information-AuditRsp					OPTIONAL,
--	iE-Extensions							ProtocolExtensionContainer  { { Cell-InformationItem-AuditRsp-ExtIEs} }		OPTIONAL,
	iE-Extensions							ProtocolExtensionContainer  OPTIONAL,
	...
}

--Cell-InformationItem-AuditRsp-ExtIEs NBAP-PROTOCOL-EXTENSION ::= {
--	{ ID id-FPACH-LCR-InformationList-AuditRsp		CRITICALITY ignore	EXTENSION FPACH-LCR-InformationList-AuditRsp			PRESENCE optional }|
	-- Applicable to 1.28Mcps TDD only
--	{ ID id-DwPCH-LCR-InformationList-AuditRsp		CRITICALITY ignore	EXTENSION Common-PhysicalChannel-Status-Information	PRESENCE optional }|
	-- Applicable to 1.28Mcps TDD only
--	{ ID id-HSDSCH-Resources-Information-AuditRsp	CRITICALITY ignore	EXTENSION HS-DSCH-Resources-Information-AuditRsp		PRESENCE optional }|
--	{ ID id-MICH-Information-AuditRsp				CRITICALITY ignore	EXTENSION Common-PhysicalChannel-Status-Information	PRESENCE optional }|
--	{ ID id-S-CCPCH-InformationListExt-AuditRsp		CRITICALITY ignore	EXTENSION S-CCPCH-InformationListExt-AuditRsp			PRESENCE optional }|
	-- Applicable to 3.84Mcps TDD only, used when there are more than maxSCCPCHCell SCCPCHs in the cell.
--	{ ID id-S-CCPCH-LCR-InformationListExt-AuditRsp	CRITICALITY ignore	EXTENSION S-CCPCH-LCR-InformationListExt-AuditRsp		PRESENCE optional }|
	-- Applicable to 1.28Mcps TDD only, used when there are more than maxSCCPCHCell SCCPCHs in the cell.
--	{ ID id-E-DCH-Resources-Information-AuditRsp	CRITICALITY ignore	EXTENSION E-DCH-Resources-Information-AuditRsp			PRESENCE optional },
--	...
--}

--P-SCH-Information-AuditRsp ::= ProtocolIE-Single-Container {{ P-SCH-InformationIE-AuditRsp }}
P-SCH-Information-AuditRsp ::= ProtocolIE-Single-Container

--P-SCH-InformationIE-AuditRsp NBAP-PROTOCOL-IES ::= {
--	{ ID id-P-SCH-Information	CRITICALITY ignore	TYPE Common-PhysicalChannel-Status-Information 	PRESENCE	mandatory }
--}

--S-SCH-Information-AuditRsp ::= ProtocolIE-Single-Container {{ S-SCH-InformationIE-AuditRsp }}
S-SCH-Information-AuditRsp ::= ProtocolIE-Single-Container

--S-SCH-InformationIE-AuditRsp NBAP-PROTOCOL-IES ::= {
--	{ ID id-S-SCH-Information	CRITICALITY ignore	TYPE Common-PhysicalChannel-Status-Information 	PRESENCE	mandatory }
--}

--P-CPICH-Information-AuditRsp ::= ProtocolIE-Single-Container {{ P-CPICH-InformationIE-AuditRsp }}
P-CPICH-Information-AuditRsp ::= ProtocolIE-Single-Container

--P-CPICH-InformationIE-AuditRsp NBAP-PROTOCOL-IES ::= {
--	{ ID id-P-CPICH-Information	CRITICALITY ignore	TYPE Common-PhysicalChannel-Status-Information 	PRESENCE	mandatory }
--}

--S-CPICH-InformationList-AuditRsp ::= SEQUENCE (SIZE (1..maxSCPICHCell)) OF ProtocolIE-Single-Container {{ S-CPICH-InformationItemIE-AuditRsp }}
S-CPICH-InformationList-AuditRsp ::= SEQUENCE (SIZE (1..32)) OF ProtocolIE-Single-Container

--S-CPICH-InformationItemIE-AuditRsp NBAP-PROTOCOL-IES ::= {
--	{ ID id-S-CPICH-Information   CRITICALITY ignore	TYPE Common-PhysicalChannel-Status-Information		PRESENCE mandatory }
--}

--P-CCPCH-Information-AuditRsp ::= ProtocolIE-Single-Container {{ P-CCPCH-InformationIE-AuditRsp }}
P-CCPCH-Information-AuditRsp ::= ProtocolIE-Single-Container

--P-CCPCH-InformationIE-AuditRsp NBAP-PROTOCOL-IES ::= {
--	{ ID id-P-CCPCH-Information   CRITICALITY ignore	TYPE Common-PhysicalChannel-Status-Information		PRESENCE mandatory }
--}

--BCH-Information-AuditRsp ::= ProtocolIE-Single-Container {{ BCH-InformationIE-AuditRsp }}
BCH-Information-AuditRsp ::= ProtocolIE-Single-Container

--BCH-InformationIE-AuditRsp NBAP-PROTOCOL-IES ::= {
--	{ ID id-BCH-Information   CRITICALITY ignore	TYPE Common-TransportChannel-Status-Information		PRESENCE mandatory }
--}

--S-CCPCH-InformationList-AuditRsp ::= SEQUENCE (SIZE (1..maxSCCPCHCell)) OF ProtocolIE-Single-Container {{ S-CCPCH-InformationItemIE-AuditRsp }}
S-CCPCH-InformationList-AuditRsp ::= SEQUENCE (SIZE (1..32)) OF ProtocolIE-Single-Container

--S-CCPCH-InformationItemIE-AuditRsp NBAP-PROTOCOL-IES ::= {
--	{ ID id-S-CCPCH-Information   CRITICALITY ignore	TYPE Common-PhysicalChannel-Status-Information		PRESENCE mandatory }
--}
--PCH-Information-AuditRsp ::= ProtocolIE-Single-Container {{ PCH-InformationIE-AuditRsp }}
PCH-Information-AuditRsp ::= ProtocolIE-Single-Container

--PCH-InformationIE-AuditRsp NBAP-PROTOCOL-IES ::= {
--	{ ID id-PCH-Information   CRITICALITY ignore	TYPE Common-TransportChannel-Status-Information		PRESENCE mandatory }
--}

--PICH-Information-AuditRsp ::= ProtocolIE-Single-Container {{ PICH-InformationIE-AuditRsp }}
PICH-Information-AuditRsp ::= ProtocolIE-Single-Container

--PICH-InformationIE-AuditRsp NBAP-PROTOCOL-IES ::= {
--	{ ID id-PICH-Information   CRITICALITY ignore	TYPE Common-PhysicalChannel-Status-Information		PRESENCE mandatory }
--}

--FACH-InformationList-AuditRsp ::= SEQUENCE (SIZE (1..maxFACHCell)) OF ProtocolIE-Single-Container {{ FACH-InformationItemIE-AuditRsp }}
FACH-InformationList-AuditRsp ::= SEQUENCE (SIZE (1..256)) OF ProtocolIE-Single-Container 

--FACH-InformationItemIE-AuditRsp NBAP-PROTOCOL-IES ::= {
--	{ ID id-FACH-Information   CRITICALITY ignore	TYPE Common-TransportChannel-Status-Information		PRESENCE mandatory }
--}

--PRACH-InformationList-AuditRsp ::= SEQUENCE (SIZE (1..maxPRACHCell)) OF ProtocolIE-Single-Container {{ PRACH-InformationItemIE-AuditRsp }}
PRACH-InformationList-AuditRsp ::= SEQUENCE (SIZE (1..16)) OF ProtocolIE-Single-Container

--PRACH-InformationItemIE-AuditRsp NBAP-PROTOCOL-IES ::= {
--	{ ID id-PRACH-Information   CRITICALITY ignore	TYPE Common-PhysicalChannel-Status-Information		PRESENCE mandatory }
--}

--RACH-InformationList-AuditRsp ::= SEQUENCE (SIZE (1..maxRACHCell)) OF ProtocolIE-Single-Container {{ RACH-InformationItemIE-AuditRsp }}
RACH-InformationList-AuditRsp ::= SEQUENCE (SIZE (1..16)) OF ProtocolIE-Single-Container

--RACH-InformationItemIE-AuditRsp NBAP-PROTOCOL-IES ::= {
--	{ ID id-RACH-Information   CRITICALITY ignore	TYPE Common-TransportChannel-Status-Information		PRESENCE mandatory }
--}

--AICH-InformationList-AuditRsp ::= SEQUENCE (SIZE (1..maxPRACHCell)) OF ProtocolIE-Single-Container {{ AICH-InformationItemIE-AuditRsp }}
AICH-InformationList-AuditRsp ::= SEQUENCE (SIZE (1..16)) OF ProtocolIE-Single-Container

--AICH-InformationItemIE-AuditRsp NBAP-PROTOCOL-IES ::= {
--	{ ID id-AICH-Information   CRITICALITY ignore	TYPE Common-PhysicalChannel-Status-Information		PRESENCE mandatory }
--}

--SCH-Information-AuditRsp ::= ProtocolIE-Single-Container {{ SCH-InformationIE-AuditRsp }}
SCH-Information-AuditRsp ::= ProtocolIE-Single-Container

--SCH-InformationIE-AuditRsp NBAP-PROTOCOL-IES ::= {
--	{ ID id-SCH-Information   CRITICALITY ignore	TYPE Common-PhysicalChannel-Status-Information		PRESENCE mandatory }
--}

--CCP-InformationList-AuditRsp ::=SEQUENCE (SIZE (1..maxCCPinNodeB)) OF ProtocolIE-Single-Container {{ CCP-InformationItemIE-AuditRsp }}
CCP-InformationList-AuditRsp ::=SEQUENCE (SIZE (1..256)) OF ProtocolIE-Single-Container

--CCP-InformationItemIE-AuditRsp NBAP-PROTOCOL-IES ::= {
--	{ID	id-CCP-InformationItem-AuditRsp			CRITICALITY		ignore			TYPE	CCP-InformationItem-AuditRsp			PRESENCE	mandatory}
--}	

CCP-InformationItem-AuditRsp ::= SEQUENCE {
	communicationControlPortID			CommunicationControlPortID,
	resourceOperationalState			ResourceOperationalState,
	availabilityStatus					AvailabilityStatus,
--	iE-Extensions						ProtocolExtensionContainer  {{ CCP-InformationItem-AuditRsp-ExtIEs }}		OPTIONAL,
	iE-Extensions						ProtocolExtensionContainer  OPTIONAL,
	...
}

--CCP-InformationItem-AuditRsp-ExtIEs NBAP-PROTOCOL-EXTENSION ::= {
--	...
--}

--FPACH-LCR-InformationList-AuditRsp ::= SEQUENCE (SIZE (1..maxFPACHCell)) OF ProtocolIE-Single-Container {{ FPACH-LCR-InformationItemIE-AuditRsp }}
FPACH-LCR-InformationList-AuditRsp ::= SEQUENCE (SIZE (1..8)) OF ProtocolIE-Single-Container

--FPACH-LCR-InformationItemIE-AuditRsp NBAP-PROTOCOL-IES ::= {
--	{ ID id-FPACH-LCR-Information-AuditRsp   CRITICALITY ignore	TYPE Common-PhysicalChannel-Status-Information		PRESENCE mandatory }
--}

HS-DSCH-Resources-Information-AuditRsp ::= SEQUENCE {
	resourceOperationalState			ResourceOperationalState,
	availabilityStatus					AvailabilityStatus,
--	iE-Extensions						ProtocolExtensionContainer  {{ HS-DSCH-Resources-Information-AuditRsp-ExtIEs }}		OPTIONAL,
	iE-Extensions						ProtocolExtensionContainer OPTIONAL,
	...
}

--HS-DSCH-Resources-Information-AuditRsp-ExtIEs NBAP-PROTOCOL-EXTENSION ::= {
--	...
--}

--S-CCPCH-InformationListExt-AuditRsp ::= SEQUENCE (SIZE (1..maxSCCPCHCellinExt)) OF ProtocolIE-Single-Container {{ S-CCPCH-InformationItemIE-AuditRsp }}
S-CCPCH-InformationListExt-AuditRsp ::= SEQUENCE (SIZE (1..208)) OF ProtocolIE-Single-Container

--S-CCPCH-LCR-InformationListExt-AuditRsp ::= SEQUENCE (SIZE (1..maxSCCPCHCellinExtLCR)) OF ProtocolIE-Single-Container {{ S-CCPCH-InformationItemIE-AuditRsp }}
S-CCPCH-LCR-InformationListExt-AuditRsp ::= SEQUENCE (SIZE (1..64)) OF ProtocolIE-Single-Container

E-DCH-Resources-Information-AuditRsp ::= SEQUENCE {
	resourceOperationalState			ResourceOperationalState,
	availabilityStatus					AvailabilityStatus,
--	iE-Extensions						ProtocolExtensionContainer  {{ E-DCH-Resources-Information-AuditRsp-ExtIEs }}		OPTIONAL,
	iE-Extensions						ProtocolExtensionContainer OPTIONAL,
	...
}

--E-DCH-Resources-Information-AuditRsp-ExtIEs NBAP-PROTOCOL-EXTENSION ::= {
--	...
--}

--Local-Cell-InformationList-AuditRsp	 ::=SEQUENCE (SIZE (1..maxLocalCellinNodeB)) OF ProtocolIE-Single-Container {{ Local-Cell-InformationItemIE-AuditRsp }}
Local-Cell-InformationList-AuditRsp	 ::=SEQUENCE (SIZE (1..256)) OF ProtocolIE-Single-Container

--Local-Cell-InformationItemIE-AuditRsp NBAP-PROTOCOL-IES ::= {
--	{ ID id-Local-Cell-InformationItem-AuditRsp		CRITICALITY ignore	TYPE Local-Cell-InformationItem-AuditRsp	PRESENCE	mandatory}
--}

Local-Cell-InformationItem-AuditRsp ::= SEQUENCE {
	local-Cell-ID								Local-Cell-ID,
	dl-or-global-capacityCredit					DL-or-Global-CapacityCredit,
	ul-capacityCredit							UL-CapacityCredit													OPTIONAL,
	commonChannelsCapacityConsumptionLaw 		CommonChannelsCapacityConsumptionLaw,
	dedicatedChannelsCapacityConsumptionLaw 	DedicatedChannelsCapacityConsumptionLaw,
	maximumDL-PowerCapability					MaximumDL-PowerCapability											OPTIONAL,
	minSpreadingFactor							MinSpreadingFactor													OPTIONAL,
	minimumDL-PowerCapability					MinimumDL-PowerCapability											OPTIONAL,
	local-Cell-Group-ID							Local-Cell-ID														OPTIONAL,
--	iE-Extensions								ProtocolExtensionContainer  {{ Local-Cell-InformationItem-AuditRsp-ExtIEs}}		OPTIONAL,
	iE-Extensions								ProtocolExtensionContainer  OPTIONAL,
	...
}

--Local-Cell-InformationItem-AuditRsp-ExtIEs NBAP-PROTOCOL-EXTENSION ::= {
--	{ ID	id-ReferenceClockAvailability		CRITICALITY ignore			EXTENSION ReferenceClockAvailability			PRESENCE	optional }|
--	{ ID	id-Power-Local-Cell-Group-ID		CRITICALITY ignore			EXTENSION Local-Cell-ID			PRESENCE	optional }|
--	{ ID	id-HSDPA-Capability					CRITICALITY ignore			EXTENSION HSDPA-Capability			PRESENCE	optional }|
--	{ ID	id-E-DCH-Capability					CRITICALITY ignore			EXTENSION E-DCH-Capability			PRESENCE	optional }|
--	{ ID	id-E-DCH-CapacityConsumptionLaw		CRITICALITY ignore			EXTENSION DedicatedChannelsCapacityConsumptionLaw	PRESENCE	optional },
--	...
--}

--Local-Cell-Group-InformationList-AuditRsp	 ::= SEQUENCE (SIZE (1..maxLocalCellinNodeB)) OF ProtocolIE-Single-Container {{ Local-Cell-Group-InformationItemIE-AuditRsp }}
Local-Cell-Group-InformationList-AuditRsp	 ::= SEQUENCE (SIZE (1..256)) OF ProtocolIE-Single-Container

--Local-Cell-Group-InformationItemIE-AuditRsp NBAP-PROTOCOL-IES ::= {
--	{ ID id-Local-Cell-Group-InformationItem-AuditRsp	CRITICALITY ignore	TYPE Local-Cell-Group-InformationItem-AuditRsp	PRESENCE mandatory}
--}

Local-Cell-Group-InformationItem-AuditRsp ::= SEQUENCE {
	local-Cell-Group-ID							Local-Cell-ID,
	dl-or-global-capacityCredit					DL-or-Global-CapacityCredit,
	ul-capacityCredit							UL-CapacityCredit						OPTIONAL,
	commonChannelsCapacityConsumptionLaw 		CommonChannelsCapacityConsumptionLaw,
	dedicatedChannelsCapacityConsumptionLaw 	DedicatedChannelsCapacityConsumptionLaw,
--	iE-Extensions								ProtocolExtensionContainer  {{ Local-Cell-Group-InformationItem-AuditRsp-ExtIEs}}		OPTIONAL,
	iE-Extensions								ProtocolExtensionContainer  OPTIONAL,
	...
}

--Local-Cell-Group-InformationItem-AuditRsp-ExtIEs NBAP-PROTOCOL-EXTENSION ::= {
--	{ ID	id-E-DCH-CapacityConsumptionLaw		CRITICALITY ignore			EXTENSION DedicatedChannelsCapacityConsumptionLaw	PRESENCE	optional },
--	...
--}

--Power-Local-Cell-Group-InformationList-AuditRsp	 ::= SEQUENCE (SIZE (1..maxLocalCellinNodeB)) OF ProtocolIE-Single-Container {{ Power-Local-Cell-Group-InformationItemIE-AuditRsp }}
Power-Local-Cell-Group-InformationList-AuditRsp	 ::= SEQUENCE (SIZE (1..256)) OF ProtocolIE-Single-Container

--Power-Local-Cell-Group-InformationItemIE-AuditRsp NBAP-PROTOCOL-IES ::= {
--	{ ID	id-Power-Local-Cell-Group-InformationItem-AuditRsp			CRITICALITY		ignore			TYPE	Power-Local-Cell-Group-InformationItem-AuditRsp		PRESENCE	mandatory}
--}

Power-Local-Cell-Group-InformationItem-AuditRsp ::= SEQUENCE {
	power-Local-Cell-Group-ID					Local-Cell-ID,
	maximumDL-PowerCapability					MaximumDL-PowerCapability,
--	iE-Extensions								ProtocolExtensionContainer  {{ Power-Local-Cell-Group-InformationItem-AuditRsp-ExtIEs}}		OPTIONAL,
	iE-Extensions								ProtocolExtensionContainer  OPTIONAL,
	...
}

--Power-Local-Cell-Group-InformationItem-AuditRsp-ExtIEs NBAP-PROTOCOL-EXTENSION ::= {
--	...
--}

-- **************************************************************
--
-- AUDIT FAILURE
--
-- **************************************************************

--AuditFailure ::= SEQUENCE {
--	protocolIEs				ProtocolIE-Container	{{AuditFailure-IEs}},
--	protocolExtensions		ProtocolExtensionContainer	{{AuditFailure-Extensions}}			OPTIONAL,
--	...
--}
AuditFailure ::= SEQUENCE {
	protocolIEs				ProtocolIE-Container,
	protocolExtensions		ProtocolExtensionContainer OPTIONAL,
	...
}

--AuditFailure-IEs NBAP-PROTOCOL-IES ::= {
--	{ ID	id-Cause							CRITICALITY		ignore			TYPE	Cause						PRESENCE	mandatory	}|
--	{ ID	id-CriticalityDiagnostics			CRITICALITY		ignore			TYPE	CriticalityDiagnostics		PRESENCE	optional	},
--	...
--}

--AuditFailure-Extensions NBAP-PROTOCOL-EXTENSION ::= {
--	...
--}
-- **************************************************************
--
-- COMMON MEASUREMENT INITIATION REQUEST
--
-- **************************************************************

--CommonMeasurementInitiationRequest ::= SEQUENCE {
--	protocolIEs				ProtocolIE-Container	{{CommonMeasurementInitiationRequest-IEs}},
--	protocolExtensions		ProtocolExtensionContainer	{{CommonMeasurementInitiationRequest-Extensions}}		OPTIONAL,
--	...
--}
CommonMeasurementInitiationRequest ::= SEQUENCE {
	protocolIEs				ProtocolIE-Container,
	protocolExtensions		ProtocolExtensionContainer	OPTIONAL,
	...
}
--CommonMeasurementInitiationRequest-IEs NBAP-PROTOCOL-IES ::= {
--	{ ID id-MeasurementID							CRITICALITY reject	TYPE MeasurementID				PRESENCE mandatory }|
--	{ ID id-CommonMeasurementObjectType-CM-Rqst		CRITICALITY reject	TYPE CommonMeasurementObjectType-CM-Rqst		PRESENCE mandatory }|
--	{ ID id-CommonMeasurementType					CRITICALITY reject	TYPE CommonMeasurementType		PRESENCE mandatory }|
--	{ ID id-MeasurementFilterCoefficient			CRITICALITY reject	TYPE MeasurementFilterCoefficient		PRESENCE optional }|
--	{ ID id-ReportCharacteristics					CRITICALITY reject	TYPE ReportCharacteristics		PRESENCE mandatory }|
--	{ ID id-SFNReportingIndicator					CRITICALITY reject	TYPE FNReportingIndicator		PRESENCE mandatory }|
--	{ ID id-SFN										CRITICALITY reject	TYPE SFN						PRESENCE optional },
--	...
--}

--CommonMeasurementInitiationRequest-Extensions NBAP-PROTOCOL-EXTENSION ::= {
--	{ID id-CommonMeasurementAccuracy						CRITICALITY reject			EXTENSION CommonMeasurementAccuracy			PRESENCE optional}|
--	{ ID	id-MeasurementRecoveryBehavior					CRITICALITY ignore			EXTENSION	MeasurementRecoveryBehavior		PRESENCE optional
--	},
--	...
--}

CommonMeasurementObjectType-CM-Rqst ::= CHOICE {
	cell							Cell-CM-Rqst,
	rACH							RACH-CM-Rqst,
	notUsed-cPCH					NULL,
	...,
	extension-CommonMeasurementObjectType-CM-Rqst		Extension-CommonMeasurementObjectType-CM-Rqst
}

--Extension-CommonMeasurementObjectType-CM-Rqst	::= ProtocolIE-Single-Container {{ Extension-CommonMeasurementObjectType-CM-RqstIE }}
Extension-CommonMeasurementObjectType-CM-Rqst	::= ProtocolIE-Single-Container

--Extension-CommonMeasurementObjectType-CM-RqstIE NBAP-PROTOCOL-IES ::= {
--	{ ID id-Power-Local-Cell-Group-choice-CM-Rqst	CRITICALITY reject	TYPE PowerLocalCellGroup-CM-Rqst	PRESENCE mandatory }
--}

Cell-CM-Rqst ::= SEQUENCE {
	c-ID							C-ID,
	timeSlot						TimeSlot	OPTIONAL, 	-- Applicable to 3.84Mcps TDD only
--	iE-Extensions					ProtocolExtensionContainer  { { CellItem-CM-Rqst-ExtIEs} }		OPTIONAL,
	iE-Extensions					ProtocolExtensionContainer  OPTIONAL,
	...
}

--CellItem-CM-Rqst-ExtIEs NBAP-PROTOCOL-EXTENSION ::= {
--	{ ID id-TimeSlotLCR-CM-Rqst						CRITICALITY reject	EXTENSION TimeSlotLCR				PRESENCE optional }|
	-- Applicable to 1.28Mcps TDD only
--	{ID id-NeighbouringCellMeasurementInformation	CRITICALITY ignore	EXTENSION NeighbouringCellMeasurementInformation	PRESENCE optional },
--	...
--}

RACH-CM-Rqst ::= SEQUENCE {
	c-ID							C-ID,
	commonTransportChannelID		CommonTransportChannelID,
--	iE-Extensions					ProtocolExtensionContainer  { { RACHItem-CM-Rqst-ExtIEs} }		OPTIONAL,
	iE-Extensions					ProtocolExtensionContainer  OPTIONAL,
	...
}

--RACHItem-CM-Rqst-ExtIEs NBAP-PROTOCOL-EXTENSION ::= {
--	...
--}

PowerLocalCellGroup-CM-Rqst ::= SEQUENCE {
	powerLocalCellGroupID			Local-Cell-ID,
--	iE-Extensions					ProtocolExtensionContainer {{ PowerLocalCellGroup-CM-Rqst-ExtIEs }}	OPTIONAL,
	iE-Extensions					ProtocolExtensionContainer OPTIONAL,
	...
}

--PowerLocalCellGroup-CM-Rqst-ExtIEs NBAP-PROTOCOL-EXTENSION ::= {
--	...
--}

-- **************************************************************
--
-- COMMON MEASUREMENT INITIATION RESPONSE
--
-- **************************************************************
--CommonMeasurementInitiationResponse ::= SEQUENCE {
--	protocolIEs				ProtocolIE-Container	{{CommonMeasurementInitiationResponse-IEs}},
--	protocolExtensions		ProtocolExtensionContainer	{{CommonMeasurementInitiationResponse-Extensions}}		OPTIONAL,
--	...
--}
CommonMeasurementInitiationResponse ::= SEQUENCE {
	protocolIEs				ProtocolIE-Container,
	protocolExtensions		ProtocolExtensionContainer	OPTIONAL,
	...
}
--CommonMeasurementInitiationResponse-IEs NBAP-PROTOCOL-IES ::= {
--	{ ID id-MeasurementID							CRITICALITY ignore		TYPE MeasurementID			PRESENCE	mandatory	}|
--	{ ID id-CommonMeasurementObjectType-CM-Rsp		CRITICALITY ignore		TYPE CommonMeasurementObjectType-CM-Rsp		PRESENCE	optional	}|
--	{ ID	id-SFN									CRITICALITY ignore		TYPE SFN					PRESENCE	optional	}|
--	{ ID id-CriticalityDiagnostics					CRITICALITY ignore		TYPE CriticalityDiagnostics		PRESENCE	optional	},
--	...
--}

--CommonMeasurementInitiationResponse-Extensions NBAP-PROTOCOL-EXTENSION ::= {
--	{ID id-CommonMeasurementAccuracy		CRITICALITY ignore		EXTENSION CommonMeasurementAccuracy	 PRESENCE optional}|
--	{ ID	id-MeasurementRecoverySupportIndicator		CRITICALITY ignore		EXTENSION	MeasurementRecoverySupportIndicator		PRESENCE optional
--	},
--	...
--}

CommonMeasurementObjectType-CM-Rsp ::= CHOICE {
	cell						Cell-CM-Rsp,
	rACH						RACH-CM-Rsp,
	notUsed-cPCH				NULL,
	...,
	extension-CommonMeasurementObjectType-CM-Rsp		Extension-CommonMeasurementObjectType-CM-Rsp
}

--Extension-CommonMeasurementObjectType-CM-Rsp	::= ProtocolIE-Single-Container {{ Extension-CommonMeasurementObjectType-CM-RspIE }}
Extension-CommonMeasurementObjectType-CM-Rsp	::= ProtocolIE-Single-Container

--Extension-CommonMeasurementObjectType-CM-RspIE NBAP-PROTOCOL-IES ::= {
--	{ ID id-Power-Local-Cell-Group-choice-CM-Rsp	CRITICALITY ignore		TYPE PowerLocalCellGroup-CM-Rsp	PRESENCE mandatory }
--}

Cell-CM-Rsp ::= SEQUENCE {
	commonMeasurementValue			CommonMeasurementValue,
--	iE-Extensions					ProtocolExtensionContainer  { { CellItem-CM-Rsp-ExtIEs} }		OPTIONAL,
	iE-Extensions					ProtocolExtensionContainer  OPTIONAL,
	...
}

--CellItem-CM-Rsp-ExtIEs NBAP-PROTOCOL-EXTENSION ::= {
--	...
--}

RACH-CM-Rsp ::= SEQUENCE {
	commonMeasurementValue			CommonMeasurementValue,
--	iE-Extensions					ProtocolExtensionContainer  { { RACHItem-CM-Rsp-ExtIEs} }		OPTIONAL,
	iE-Extensions					ProtocolExtensionContainer  OPTIONAL,
	...
}

--RACHItem-CM-Rsp-ExtIEs NBAP-PROTOCOL-EXTENSION ::= {
--	...
--}

PowerLocalCellGroup-CM-Rsp ::= SEQUENCE {
	commonMeasurementValue			CommonMeasurementValue,
--	iE-Extensions					ProtocolExtensionContainer {{ PowerLocalCellGroup-CM-Rsp-ExtIEs}}		OPTIONAL,
	iE-Extensions					ProtocolExtensionContainer OPTIONAL,
	...
}

--PowerLocalCellGroup-CM-Rsp-ExtIEs NBAP-PROTOCOL-EXTENSION ::= {
--	...
--}

-- **************************************************************
--
-- COMMON MEASUREMENT INITIATION FAILURE
--
-- **************************************************************
--CommonMeasurementInitiationFailure ::= SEQUENCE {
--	protocolIEs				ProtocolIE-Container	{{CommonMeasurementInitiationFailure-IEs}},
--	protocolExtensions		ProtocolExtensionContainer	{{CommonMeasurementInitiationFailure-Extensions}}		OPTIONAL,
--	...
--}
CommonMeasurementInitiationFailure ::= SEQUENCE {
	protocolIEs				ProtocolIE-Container,
	protocolExtensions		ProtocolExtensionContainer OPTIONAL,
	...
}
--CommonMeasurementInitiationFailure-IEs NBAP-PROTOCOL-IES ::= {
--	{ ID	id-MeasurementID				CRITICALITY		ignore			TYPE	MeasurementID		PRESENCE	mandatory	}|
--	{ ID	id-Cause						CRITICALITY		ignore			TYPE	Cause				PRESENCE	mandatory	}|
--	{ ID	id-CriticalityDiagnostics		CRITICALITY		ignore			TYPE	CriticalityDiagnostics		PRESENCE	optional	},
--	...
--}

--CommonMeasurementInitiationFailure-Extensions NBAP-PROTOCOL-EXTENSION ::= {
--	...
--}


-- **************************************************************
--
-- CELL SETUP REQUEST FDD
--
-- **************************************************************

--CellSetupRequestFDD ::= SEQUENCE {
--	protocolIEs				ProtocolIE-Container	{{CellSetupRequestFDD-IEs}},
--	protocolExtensions		ProtocolExtensionContainer	{{CellSetupRequestFDD-Extensions}}		OPTIONAL,
--	...
--}

CellSetupRequestFDD ::= SEQUENCE {
	protocolIEs				ProtocolIE-Container,
	protocolExtensions		ProtocolExtensionContainer OPTIONAL,
	...
}

--CellSetupRequestFDD-IEs NBAP-PROTOCOL-IES ::= {
--	{ ID id-Local-Cell-ID										CRITICALITY reject	TYPE Local-Cell-ID					PRESENCE mandatory }|
--	{ ID id-C-ID												CRITICALITY reject	TYPE C-ID						PRESENCE mandatory }|
--	{ ID id-ConfigurationGenerationID							CRITICALITY reject	TYPE ConfigurationGenerationID					PRESENCE mandatory }|
--	{ ID id-T-Cell												CRITICALITY reject	TYPE T-Cell						PRESENCE mandatory }|
--	{ ID id-UARFCNforNu											CRITICALITY reject	TYPE UARFCN						PRESENCE mandatory }|
--	{ ID id-UARFCNforNd											CRITICALITY reject	TYPE UARFCN						PRESENCE mandatory }|
--	{ ID id-MaximumTransmissionPower							CRITICALITY reject	TYPE MaximumTransmissionPower					PRESENCE mandatory }|
--	{ ID id-Closed-Loop-Timing-Adjustment-Mode					CRITICALITY reject	TYPE Closedlooptimingadjustmentmode			PRESENCE optional }|
--	{ ID id-PrimaryScramblingCode								CRITICALITY reject	TYPE PrimaryScramblingCode					PRESENCE mandatory }|
--	{ ID id-Synchronisation-Configuration-Cell-SetupRqst		CRITICALITY reject	TYPE Synchronisation-Configuration-Cell-SetupRqst			PRESENCE	mandatory }|
--	{ ID id-DL-TPC-Pattern01Count								CRITICALITY reject	TYPE DL-TPC-Pattern01Count					PRESENCE mandatory }|
--	{ ID id-PrimarySCH-Information-Cell-SetupRqstFDD			CRITICALITY reject	TYPE PrimarySCH-Information-Cell-SetupRqstFDD				PRESENCE	mandatory }|
--	{ ID id-SecondarySCH-Information-Cell-SetupRqstFDD			CRITICALITY reject	TYPE SecondarySCH-Information-Cell-SetupRqstFDD			PRESENCE mandatory }|
--	{ ID id-PrimaryCPICH-Information-Cell-SetupRqstFDD			CRITICALITY reject	TYPE PrimaryCPICH-Information-Cell-SetupRqstFDD			PRESENCE	mandatory }|
--	{ ID id-SecondaryCPICH-InformationList-Cell-SetupRqstFDD	CRITICALITY reject	TYPE SecondaryCPICH-InformationList-Cell-SetupRqstFDD	PRESENCE	optional }|
--	{ ID id-PrimaryCCPCH-Information-Cell-SetupRqstFDD			CRITICALITY reject	TYPE PrimaryCCPCH-Information-Cell-SetupRqstFDD			PRESENCE	mandatory }|
--	{ ID id-Limited-power-increase-information-Cell-SetupRqstFDD	CRITICALITY reject	TYPE Limited-power-increase-information-Cell-SetupRqstFDD		PRESENCE mandatory },
--	...
--}

--CellSetupRequestFDD-Extensions NBAP-PROTOCOL-EXTENSION ::= {
--	{ ID id-IPDLParameter-Information-Cell-SetupRqstFDD		CRITICALITY reject	EXTENSION IPDLParameter-Information-Cell-SetupRqstFDD				PRESENCE optional }|
--	{ ID id-CellPortion-InformationList-Cell-SetupRqstFDD	CRITICALITY reject	EXTENSION CellPortion-InformationList-Cell-SetupRqstFDD			PRESENCE optional },
--	...
--}

Synchronisation-Configuration-Cell-SetupRqst ::= SEQUENCE {
	n-INSYNC-IND			N-INSYNC-IND,
 	n-OUTSYNC-IND			N-OUTSYNC-IND,
 	t-RLFAILURE				T-RLFAILURE,
--	iE-Extensions			ProtocolExtensionContainer { { Synchronisation-Configuration-Cell-SetupRqst-ExtIEs} }		OPTIONAL,
	iE-Extensions			ProtocolExtensionContainer OPTIONAL,
	...
}

--Synchronisation-Configuration-Cell-SetupRqst-ExtIEs NBAP-PROTOCOL-EXTENSION ::= {
--	...
--}

PrimarySCH-Information-Cell-SetupRqstFDD ::= SEQUENCE {
	commonPhysicalChannelID					CommonPhysicalChannelID,
	primarySCH-Power						DL-Power,
	tSTD-Indicator							TSTD-Indicator,
--	iE-Extensions							ProtocolExtensionContainer { { PrimarySCH-Information-Cell-SetupRqstFDD-ExtIEs} }		OPTIONAL,
	iE-Extensions							ProtocolExtensionContainer OPTIONAL,
	...
}

--PrimarySCH-Information-Cell-SetupRqstFDD-ExtIEs NBAP-PROTOCOL-EXTENSION ::= {
--	...
--}

SecondarySCH-Information-Cell-SetupRqstFDD ::= SEQUENCE {
	commonPhysicalChannelID					CommonPhysicalChannelID,
	secondarySCH-Power						DL-Power,
	tSTD-Indicator							TSTD-Indicator,
--	iE-Extensions							ProtocolExtensionContainer { { SecondarySCH-Information-Cell-SetupRqstFDD-ExtIEs} }		OPTIONAL,
	iE-Extensions							ProtocolExtensionContainer OPTIONAL,
	...
}

--SecondarySCH-Information-Cell-SetupRqstFDD-ExtIEs NBAP-PROTOCOL-EXTENSION ::= {
--	...
--}

PrimaryCPICH-Information-Cell-SetupRqstFDD ::= SEQUENCE {
	commonPhysicalChannelID					CommonPhysicalChannelID,
	primaryCPICH-Power						PrimaryCPICH-Power,
	transmitDiversityIndicator				TransmitDiversityIndicator,
--	iE-Extensions							ProtocolExtensionContainer { { PrimaryCPICH-Information-Cell-SetupRqstFDD-ExtIEs} }		OPTIONAL,
	iE-Extensions							ProtocolExtensionContainer OPTIONAL,
	...
}

--PrimaryCPICH-Information-Cell-SetupRqstFDD-ExtIEs NBAP-PROTOCOL-EXTENSION ::= {
--	...
--}

--SecondaryCPICH-InformationList-Cell-SetupRqstFDD ::= SEQUENCE (SIZE (1..maxSCPICHCell)) OF ProtocolIE-Single-Container{{ SecondaryCPICH-InformationItemIE-Cell-SetupRqstFDD }}
SecondaryCPICH-InformationList-Cell-SetupRqstFDD ::= SEQUENCE (SIZE (1..32)) OF ProtocolIE-Single-Container

--SecondaryCPICH-InformationItemIE-Cell-SetupRqstFDD NBAP-PROTOCOL-IES ::= {
--	{ ID	id-SecondaryCPICH-InformationItem-Cell-SetupRqstFDD		CRITICALITY		reject			TYPE	SecondaryCPICH-InformationItem-Cell-SetupRqstFDD		PRESENCE	mandatory}
--}

SecondaryCPICH-InformationItem-Cell-SetupRqstFDD ::= SEQUENCE {
	commonPhysicalChannelID					CommonPhysicalChannelID,
	dl-ScramblingCode						DL-ScramblingCode,
	fDD-DL-ChannelisationCodeNumber			FDD-DL-ChannelisationCodeNumber,
	secondaryCPICH-Power					DL-Power,
	transmitDiversityIndicator				TransmitDiversityIndicator,
--	iE-Extensions							ProtocolExtensionContainer { { SecondaryCPICH-InformationItem-Cell-SetupRqstFDD-ExtIEs} }		OPTIONAL,
	iE-Extensions							ProtocolExtensionContainer OPTIONAL,
	...
}

--SecondaryCPICH-InformationItem-Cell-SetupRqstFDD-ExtIEs NBAP-PROTOCOL-EXTENSION ::= {
--	...
--}

PrimaryCCPCH-Information-Cell-SetupRqstFDD ::= SEQUENCE {
	commonPhysicalChannelID					CommonPhysicalChannelID,
	bCH-information							BCH-Information-Cell-SetupRqstFDD,
	sTTD-Indicator							STTD-Indicator,
--	iE-Extensions							ProtocolExtensionContainer { { PrimaryCCPCH-Information-Cell-SetupRqstFDD-ExtIEs} }		OPTIONAL,
	iE-Extensions							ProtocolExtensionContainer OPTIONAL,
	...
}

--PrimaryCCPCH-Information-Cell-SetupRqstFDD-ExtIEs NBAP-PROTOCOL-EXTENSION ::= {
--	...
--}

BCH-Information-Cell-SetupRqstFDD ::= SEQUENCE {
 	commonTransportChannelID				CommonTransportChannelID,
 	bCH-Power								DL-Power,
--	iE-Extensions							ProtocolExtensionContainer { { BCH-Information-Cell-SetupRqstFDD-ExtIEs} }		OPTIONAL,
	iE-Extensions							ProtocolExtensionContainer OPTIONAL,
	...
 }

--BCH-Information-Cell-SetupRqstFDD-ExtIEs NBAP-PROTOCOL-EXTENSION ::= {
--	...
--}

Limited-power-increase-information-Cell-SetupRqstFDD ::= SEQUENCE {
	powerRaiseLimit							PowerRaiseLimit,
	dLPowerAveragingWindowSize				DLPowerAveragingWindowSize,
--	iE-Extensions							ProtocolExtensionContainer { { Limited-power-increase-information-Cell-SetupRqstFDD-ExtIEs} }		OPTIONAL,
	iE-Extensions							ProtocolExtensionContainer OPTIONAL,
	...
}

--Limited-power-increase-information-Cell-SetupRqstFDD-ExtIEs NBAP-PROTOCOL-EXTENSION ::= {
--	...
--}

IPDLParameter-Information-Cell-SetupRqstFDD::= SEQUENCE {
	iPDL-FDD-Parameters							IPDL-FDD-Parameters,
	iPDL-Indicator								IPDL-Indicator,	
--	iE-Extensions							ProtocolExtensionContainer { { IPDLParameter-Information-Cell-SetupRqstFDD-ExtIEs} }		OPTIONAL,
	iE-Extensions							ProtocolExtensionContainer OPTIONAL,
	...
}

--IPDLParameter-Information-Cell-SetupRqstFDD-ExtIEs NBAP-PROTOCOL-EXTENSION ::= {
--	...
--}

--CellPortion-InformationList-Cell-SetupRqstFDD ::= SEQUENCE (SIZE (1..maxNrOfCellPortionsPerCell)) OF ProtocolIE-Single-Container{{ CellPortion-InformationItemIE-Cell-SetupRqstFDD }}
CellPortion-InformationList-Cell-SetupRqstFDD ::= SEQUENCE (SIZE (1..64)) OF ProtocolIE-Single-Container

--CellPortion-InformationItemIE-Cell-SetupRqstFDD NBAP-PROTOCOL-IES ::= {
--	{ ID id-CellPortion-InformationItem-Cell-SetupRqstFDD	CRITICALITY reject	TYPE CellPortion-InformationItem-Cell-SetupRqstFDD					PRESENCE	mandatory}
--}

CellPortion-InformationItem-Cell-SetupRqstFDD::= SEQUENCE {
	cellPortionID							CellPortionID,
	associatedSecondaryCPICH				CommonPhysicalChannelID,
	maximumTransmissionPowerforCellPortion				MaximumTransmissionPower,
--	iE-Extensions							ProtocolExtensionContainer { { CellPortion-InformationItem-Cell-SetupRqstFDD-ExtIEs} }		OPTIONAL,
	iE-Extensions							ProtocolExtensionContainer OPTIONAL,
	...
}

--CellPortion-InformationItem-Cell-SetupRqstFDD-ExtIEs NBAP-PROTOCOL-EXTENSION ::= {
--...
--}

-- **************************************************************
--
-- CELL SETUP REQUEST TDD
--
-- **************************************************************

--CellSetupRequestTDD ::= SEQUENCE {
--	protocolIEs				ProtocolIE-Container	{{CellSetupRequestTDD-IEs}},
--	protocolExtensions		ProtocolExtensionContainer	{{CellSetupRequestTDD-Extensions}}		OPTIONAL,
--	...
--}
CellSetupRequestTDD ::= SEQUENCE {
	protocolIEs				ProtocolIE-Container,
	protocolExtensions		ProtocolExtensionContainer	OPTIONAL,
	...
}

--CellSetupRequestTDD-IEs NBAP-PROTOCOL-IES ::= {
--	{ ID id-Local-Cell-ID									CRITICALITY reject	TYPE Local-Cell-ID					PRESENCE mandatory }|
--	{ ID id-C-ID											CRITICALITY reject	TYPE C-ID							PRESENCE mandatory }|
--	{ ID id-ConfigurationGenerationID						CRITICALITY reject	TYPE ConfigurationGenerationID					PRESENCE mandatory }|
--	{ ID id-UARFCNforNt										CRITICALITY reject	TYPE UARFCN							PRESENCE mandatory }|
--	{ ID id-CellParameterID									CRITICALITY reject	TYPE CellParameterID					PRESENCE mandatory }|
--	{ ID id-MaximumTransmissionPower						CRITICALITY reject	TYPE MaximumTransmissionPower					PRESENCE mandatory }|
--	{ ID id-TransmissionDiversityApplied					CRITICALITY reject	TYPE TransmissionDiversityApplied					PRESENCE mandatory }|
--	{ ID id-SyncCase										CRITICALITY reject	TYPE SyncCase						PRESENCE mandatory }|
--	{ ID id-Synchronisation-Configuration-Cell-SetupRqst	CRITICALITY reject	TYPE Synchronisation-Configuration-Cell-SetupRqst	PRESENCE mandatory }|
--	{ ID id-DPCHConstant									CRITICALITY reject	TYPE ConstantValue					PRESENCE mandatory }|	
	-- This IE shall be ignored by the Node B.
--	{ ID id-PUSCHConstant									CRITICALITY reject	TYPE ConstantValue					PRESENCE mandatory }|	
	-- This IE shall be ignored by the Node B.
--	{ ID id-PRACHConstant									CRITICALITY reject	TYPE ConstantValue					PRESENCE mandatory }|	
	-- This IE shall be ignored by the Node B.
--	{ ID id-TimingAdvanceApplied							CRITICALITY reject	TYPE TimingAdvanceApplied					PRESENCE mandatory }|
--	{ ID id-SCH-Information-Cell-SetupRqstTDD				CRITICALITY reject	TYPE SCH-Information-Cell-SetupRqstTDD				PRESENCE optional }|
	-- Mandatory for 3.84Mcps TDD, Not Applicable to 1.28Mcps TDD
--	{ ID id-PCCPCH-Information-Cell-SetupRqstTDD			CRITICALITY reject	TYPE PCCPCH-Information-Cell-SetupRqstTDD			PRESENCE optional }|
	-- Mandatory for 3.84Mcps TDD, Not Applicable to 1.28Mcps TDD
--	{ ID id-TimeSlotConfigurationList-Cell-SetupRqstTDD		CRITICALITY reject	TYPE TimeSlotConfigurationList-Cell-SetupRqstTDD	PRESENCE optional },
	-- Mandatory for 3.84Mcps TDD, Not Applicable to 1.28Mcps TDD
--	...
--}

--CellSetupRequestTDD-Extensions NBAP-PROTOCOL-EXTENSION ::= {
--	{ ID id-TimeSlotConfigurationList-LCR-Cell-SetupRqstTDD		CRITICALITY reject	EXTENSION TimeSlotConfigurationList-LCR-Cell-SetupRqstTDD		PRESENCE optional }|
	-- Mandatory for 1.28Mcps TDD, Not Applicable to 3.84Mcps TDD
--	{ ID id-PCCPCH-LCR-Information-Cell-SetupRqstTDD			CRITICALITY reject	EXTENSION PCCPCH-LCR-Information-Cell-SetupRqstTDD				PRESENCE optional }|
	-- Mandatory for 1.28Mcps TDD, Not Applicable to 3.84Mcps TDD
--	{ ID id-DwPCH-LCR-Information-Cell-SetupRqstTDD				CRITICALITY reject	EXTENSION DwPCH-LCR-Information-Cell-SetupRqstTDD				PRESENCE optional }|
	-- Mandatory for 1.28Mcps TDD, Not Applicable to 3.84Mcps TDD
--	{ ID id-ReferenceSFNoffset									CRITICALITY ignore	EXTENSION ReferenceSFNoffset										PRESENCE optional }|
--	{ ID id-IPDLParameter-Information-Cell-SetupRqstTDD			CRITICALITY reject	EXTENSION IPDLParameter-Information-Cell-SetupRqstTDD			PRESENCE optional }|
	-- Applicable to 3.84Mcps TDD only
--	{ ID id-IPDLParameter-Information-LCR-Cell-SetupRqstTDD		CRITICALITY reject	EXTENSION IPDLParameter-Information-LCR-Cell-SetupRqstTDD	PRESENCE optional },
	-- Applicable to 1.28Mcps TDD only
--	...
--}


SCH-Information-Cell-SetupRqstTDD ::= SEQUENCE {
	commonPhysicalChannelID					CommonPhysicalChannelID,
	syncCaseIndicator						SyncCaseIndicator-Cell-SetupRqstTDD-PSCH,
	sCH-Power								DL-Power,
	tSTD-Indicator							TSTD-Indicator,
--	iE-Extensions							ProtocolExtensionContainer { { SCH-Information-Cell-SetupRqstTDD-ExtIEs} }		OPTIONAL,
	iE-Extensions							ProtocolExtensionContainer OPTIONAL,
	...
}

--SCH-Information-Cell-SetupRqstTDD-ExtIEs NBAP-PROTOCOL-EXTENSION ::= {
--	...
--}

--SyncCaseIndicator-Cell-SetupRqstTDD-PSCH ::= ProtocolIE-Single-Container {{ SyncCaseIndicatorIE-Cell-SetupRqstTDD-PSCH }}
SyncCaseIndicator-Cell-SetupRqstTDD-PSCH ::= ProtocolIE-Single-Container

--SyncCaseIndicatorIE-Cell-SetupRqstTDD-PSCH NBAP-PROTOCOL-IES ::= {
--	{ ID id-SyncCaseIndicatorItem-Cell-SetupRqstTDD-PSCH   CRITICALITY reject	TYPE SyncCaseIndicatorItem-Cell-SetupRqstTDD-PSCH		PRESENCE mandatory }
--}

SyncCaseIndicatorItem-Cell-SetupRqstTDD-PSCH ::= CHOICE {
	case1								Case1-Cell-SetupRqstTDD,
	case2								Case2-Cell-SetupRqstTDD,
	...
}

Case1-Cell-SetupRqstTDD ::= SEQUENCE {
	timeSlot							TimeSlot,
--	iE-Extensions						ProtocolExtensionContainer { { Case1Item-Cell-SetupRqstTDD-ExtIEs} }		OPTIONAL,
	iE-Extensions						ProtocolExtensionContainer OPTIONAL,
	...
}

--Case1Item-Cell-SetupRqstTDD-ExtIEs NBAP-PROTOCOL-EXTENSION ::= {
--	...
--}

Case2-Cell-SetupRqstTDD ::= SEQUENCE {
	sCH-TimeSlot						SCH-TimeSlot,
--	iE-Extensions						ProtocolExtensionContainer { { Case2Item-Cell-SetupRqstTDD-ExtIEs} }		OPTIONAL,
	iE-Extensions						ProtocolExtensionContainer OPTIONAL,
	...
}

--Case2Item-Cell-SetupRqstTDD-ExtIEs NBAP-PROTOCOL-EXTENSION ::= {
--	...
--}


PCCPCH-Information-Cell-SetupRqstTDD ::= SEQUENCE {
	commonPhysicalChannelID					CommonPhysicalChannelID,
	tdd-PhysicalChannelOffset				TDD-PhysicalChannelOffset,
	repetitionPeriod						RepetitionPeriod,
	repetitionLength						RepetitionLength,
	pCCPCH-Power							PCCPCH-Power,
	sCTD-Indicator							SCTD-Indicator,
--	iE-Extensions							ProtocolExtensionContainer { { PCCPCH-Information-Cell-SetupRqstTDD-ExtIEs} }		OPTIONAL,
	iE-Extensions							ProtocolExtensionContainer OPTIONAL,
	...
}

--PCCPCH-Information-Cell-SetupRqstTDD-ExtIEs NBAP-PROTOCOL-EXTENSION ::= {
--	...
--}

TimeSlotConfigurationList-Cell-SetupRqstTDD ::= SEQUENCE (SIZE (1..15)) OF TimeSlotConfigurationItem-Cell-SetupRqstTDD

TimeSlotConfigurationItem-Cell-SetupRqstTDD ::= SEQUENCE {
	timeSlot								TimeSlot,
	timeSlotStatus							TimeSlotStatus,
	timeSlotDirection						TimeSlotDirection,
--	iE-Extensions							ProtocolExtensionContainer { { TimeSlotConfigurationItem-Cell-SetupRqstTDD-ExtIEs} }		OPTIONAL,
	iE-Extensions							ProtocolExtensionContainer OPTIONAL,
	...
}

--TimeSlotConfigurationItem-Cell-SetupRqstTDD-ExtIEs NBAP-PROTOCOL-EXTENSION ::= {
--	...
--}

TimeSlotConfigurationList-LCR-Cell-SetupRqstTDD ::= SEQUENCE (SIZE (1..7)) OF TimeSlotConfigurationItem-LCR-Cell-SetupRqstTDD

TimeSlotConfigurationItem-LCR-Cell-SetupRqstTDD ::= SEQUENCE {
	timeSlotLCR								TimeSlotLCR,
	timeSlotStatus							TimeSlotStatus,
	timeSlotDirection						TimeSlotDirection,
--	iE-Extensions							ProtocolExtensionContainer { { TimeSlotConfigurationItem-LCR-Cell-SetupRqstTDD-ExtIEs} }		OPTIONAL,
	iE-Extensions							ProtocolExtensionContainer OPTIONAL,
	...
}

--TimeSlotConfigurationItem-LCR-Cell-SetupRqstTDD-ExtIEs NBAP-PROTOCOL-EXTENSION ::= {
--	...
--}

PCCPCH-LCR-Information-Cell-SetupRqstTDD ::= SEQUENCE {
	commonPhysicalChannelID					CommonPhysicalChannelID,
	tdd-PhysicalChannelOffset				TDD-PhysicalChannelOffset,
	repetitionPeriod						RepetitionPeriod,
	repetitionLength						RepetitionLength,
	pCCPCH-Power							PCCPCH-Power,
	sCTD-Indicator							SCTD-Indicator,
	tSTD-Indicator							TSTD-Indicator,
--	iE-Extensions							ProtocolExtensionContainer { { PCCPCH-LCR-Information-Cell-SetupRqstTDD-ExtIEs} }		OPTIONAL,
	iE-Extensions							ProtocolExtensionContainer OPTIONAL,
	...
}

--PCCPCH-LCR-Information-Cell-SetupRqstTDD-ExtIEs NBAP-PROTOCOL-EXTENSION ::= {
--	...
--}

DwPCH-LCR-Information-Cell-SetupRqstTDD ::= SEQUENCE {
	commonPhysicalChannelId			CommonPhysicalChannelID,
	tSTD-Indicator					TSTD-Indicator,
	dwPCH-Power						DwPCH-Power,
--	iE-Extensions					ProtocolExtensionContainer { { DwPCH-LCR-Information-Cell-SetupRqstTDD-ExtIEs} }		OPTIONAL,
	iE-Extensions					ProtocolExtensionContainer OPTIONAL,
	...
}

--DwPCH-LCR-Information-Cell-SetupRqstTDD-ExtIEs NBAP-PROTOCOL-EXTENSION ::= {
--	...
--}

IPDLParameter-Information-Cell-SetupRqstTDD ::= SEQUENCE {
	iPDL-TDD-Parameters						IPDL-TDD-Parameters,
	iPDL-Indicator							IPDL-Indicator,
--	iE-Extensions							ProtocolExtensionContainer { { IPDLParameter-Information-Cell-SetupRqstTDD-ExtIEs} }		OPTIONAL,
	iE-Extensions							ProtocolExtensionContainer OPTIONAL,
	...
}

--IPDLParameter-Information-Cell-SetupRqstTDD-ExtIEs NBAP-PROTOCOL-EXTENSION ::= {
--	...
--}
IPDLParameter-Information-LCR-Cell-SetupRqstTDD ::= SEQUENCE {
	iPDL-TDD-Parameters-LCR					IPDL-TDD-Parameters-LCR,
	iPDL-Indicator							IPDL-Indicator,
--	iE-Extensions							ProtocolExtensionContainer { { IPDLParameter-Information-LCR-Cell-SetupRqstTDD-ExtIEs} }		OPTIONAL,
	iE-Extensions							ProtocolExtensionContainer OPTIONAL,
	...
}

--IPDLParameter-Information-LCR-Cell-SetupRqstTDD-ExtIEs NBAP-PROTOCOL-EXTENSION ::= {
--	...
--}

-- **************************************************************
--
-- CELL SETUP RESPONSE
--
-- **************************************************************

--CellSetupResponse ::= SEQUENCE {
--	protocolIEs					ProtocolIE-Container	{{CellSetupResponse-IEs}},
--	protocolExtensions			ProtocolExtensionContainer	{{CellSetupResponse-Extensions}}		OPTIONAL,
--	...
--}
CellSetupResponse ::= SEQUENCE {
	protocolIEs					ProtocolIE-Container,
	protocolExtensions			ProtocolExtensionContainer	OPTIONAL,
	...
}

--CellSetupResponse-IEs NBAP-PROTOCOL-IES ::= {
--	{ ID	id-CriticalityDiagnostics		CRITICALITY		ignore			TYPE	CriticalityDiagnostics		PRESENCE	optional},
--	...
--}

--CellSetupResponse-Extensions NBAP-PROTOCOL-EXTENSION ::= {
--	...
--}

-- **************************************************************
--
-- CELL SETUP FAILURE
--
-- **************************************************************

--CellSetupFailure ::= SEQUENCE {
--	protocolIEs				ProtocolIE-Container	{{CellSetupFailure-IEs}},
--	protocolExtensions		ProtocolExtensionContainer	{{CellSetupFailure-Extensions}}			OPTIONAL,
--	...
--}

CellSetupFailure ::= SEQUENCE {
	protocolIEs				ProtocolIE-Container,
	protocolExtensions		ProtocolExtensionContainer	OPTIONAL,
	...
}

--CellSetupFailure-IEs NBAP-PROTOCOL-IES ::= {
--	{ ID	id-Cause							CRITICALITY ignore			TYPE	Cause				PRESENCE	mandatory	}|
--	{ ID	id-CriticalityDiagnostics			CRITICALITY ignore			TYPE	CriticalityDiagnostics		PRESENCE	optional	},
--	...
--}

--CellSetupFailure-Extensions NBAP-PROTOCOL-EXTENSION ::= {
--	...
--}

-- **************************************************************
--
-- CELL RECONFIGURATION REQUEST FDD
--
-- **************************************************************

--CellReconfigurationRequestFDD ::= SEQUENCE {
--	protocolIEs				ProtocolIE-Container	{{CellReconfigurationRequestFDD-IEs}},
--	protocolExtensions		ProtocolExtensionContainer	{{CellReconfigurationRequestFDD-Extensions}} 		OPTIONAL,
--	...
--}

CellReconfigurationRequestFDD ::= SEQUENCE {
	protocolIEs				ProtocolIE-Container,
	protocolExtensions		ProtocolExtensionContainer OPTIONAL,
	...
}

--CellReconfigurationRequestFDD-IEs NBAP-PROTOCOL-IES ::= {
--	{ ID	id-C-ID													CRITICALITY reject	TYPE C-ID												PRESENCE mandatory }|
--	{ ID	id-ConfigurationGenerationID							CRITICALITY reject	TYPE ConfigurationGenerationID									PRESENCE mandatory }|
--	{ ID	id-MaximumTransmissionPower								CRITICALITY reject	TYPE MaximumTransmissionPower									PRESENCE optional }|
--	{ ID	id-Synchronisation-Configuration-Cell-ReconfRqst		CRITICALITY reject	TYPE Synchronisation-Configuration-Cell-ReconfRqst		PRESENCE optional }|
--	{ ID	id-PrimarySCH-Information-Cell-ReconfRqstFDD			CRITICALITY reject	TYPE PrimarySCH-Information-Cell-ReconfRqstFDD			PRESENCE optional }|
--	{ ID	id-SecondarySCH-Information-Cell-ReconfRqstFDD			CRITICALITY reject	TYPE SecondarySCH-Information-Cell-ReconfRqstFDD			PRESENCE optional }|
--	{ ID	id-PrimaryCPICH-Information-Cell-ReconfRqstFDD			CRITICALITY reject	TYPE PrimaryCPICH-Information-Cell-ReconfRqstFDD			PRESENCE optional }|
--	{ ID	id-SecondaryCPICH-InformationList-Cell-ReconfRqstFDD	CRITICALITY reject	TYPE SecondaryCPICH-InformationList-Cell-ReconfRqstFDD		PRESENCE optional }|
--	{ ID	id-PrimaryCCPCH-Information-Cell-ReconfRqstFDD			CRITICALITY reject	TYPE PrimaryCCPCH-Information-Cell-ReconfRqstFDD			PRESENCE optional },
--	...
--}

--CellReconfigurationRequestFDD-Extensions NBAP-PROTOCOL-EXTENSION ::= {
--	{ID	id-IPDLParameter-Information-Cell-ReconfRqstFDD	CRITICALITY reject	EXTENSION IPDLParameter-Information-Cell-ReconfRqstFDD					PRESENCE optional }|
--	{ ID id-CellPortion-InformationList-Cell-ReconfRqstFDD	CRITICALITY reject	EXTENSION CellPortion-InformationList-Cell-ReconfRqstFDD			PRESENCE optional },
--	...
--}

Synchronisation-Configuration-Cell-ReconfRqst ::= SEQUENCE {
	n-INSYNC-IND			N-INSYNC-IND,
 	n-OUTSYNC-IND			N-OUTSYNC-IND,
 	t-RLFAILURE				T-RLFAILURE,
--	iE-Extensions			ProtocolExtensionContainer { { Synchronisation-Configuration-Cell-ReconfRqst-ExtIEs} }		OPTIONAL,
	iE-Extensions			ProtocolExtensionContainer OPTIONAL,
	...
}

--Synchronisation-Configuration-Cell-ReconfRqst-ExtIEs NBAP-PROTOCOL-EXTENSION ::= {
--	...
--}

PrimarySCH-Information-Cell-ReconfRqstFDD ::= SEQUENCE {
 	commonPhysicalChannelID					CommonPhysicalChannelID,
 	primarySCH-Power						DL-Power,
--	iE-Extensions							ProtocolExtensionContainer { { PrimarySCH-Information-Cell-ReconfRqstFDD-ExtIEs} }		OPTIONAL,
	iE-Extensions							ProtocolExtensionContainer OPTIONAL,
	...
 }

--PrimarySCH-Information-Cell-ReconfRqstFDD-ExtIEs NBAP-PROTOCOL-EXTENSION ::= {
--	...
--}

SecondarySCH-Information-Cell-ReconfRqstFDD ::= SEQUENCE {
 	commonPhysicalChannelID					CommonPhysicalChannelID,
 	secondarySCH-Power						DL-Power,
--	iE-Extensions							ProtocolExtensionContainer { { SecondarySCH-Information-Cell-ReconfRqstFDD-ExtIEs} }		OPTIONAL,
	iE-Extensions							ProtocolExtensionContainer OPTIONAL,
	...
 }

--SecondarySCH-Information-Cell-ReconfRqstFDD-ExtIEs NBAP-PROTOCOL-EXTENSION ::= {
--	...
--}

PrimaryCPICH-Information-Cell-ReconfRqstFDD ::= SEQUENCE {
 	commonPhysicalChannelID					CommonPhysicalChannelID,
	primaryCPICH-Power						PrimaryCPICH-Power,
--	iE-Extensions							ProtocolExtensionContainer { { PrimaryCPICH-Information-Cell-ReconfRqstFDD-ExtIEs} }		OPTIONAL,
	iE-Extensions							ProtocolExtensionContainer OPTIONAL,
	...
 }

--PrimaryCPICH-Information-Cell-ReconfRqstFDD-ExtIEs NBAP-PROTOCOL-EXTENSION ::= {
--	...
--}

--SecondaryCPICH-InformationList-Cell-ReconfRqstFDD ::= SEQUENCE (SIZE (1..maxSCPICHCell)) OF ProtocolIE-Single-Container{{ SecondaryCPICH-InformationItemIE-Cell-ReconfRqstFDD }}
SecondaryCPICH-InformationList-Cell-ReconfRqstFDD ::= SEQUENCE (SIZE (1..32)) OF ProtocolIE-Single-Container

--SecondaryCPICH-InformationItemIE-Cell-ReconfRqstFDD NBAP-PROTOCOL-IES ::= {
--	{ ID	id-SecondaryCPICH-InformationItem-Cell-ReconfRqstFDD	CRITICALITY reject	TYPE	SecondaryCPICH-InformationItem-Cell-ReconfRqstFDD		PRESENCE mandatory }
--}

SecondaryCPICH-InformationItem-Cell-ReconfRqstFDD ::= SEQUENCE {
 	commonPhysicalChannelID						CommonPhysicalChannelID,
 	secondaryCPICH-Power						DL-Power,
--	iE-Extensions								ProtocolExtensionContainer { { SecondaryCPICH-InformationItem-Cell-ReconfRqstFDD-ExtIEs} }		OPTIONAL,
	iE-Extensions								ProtocolExtensionContainer OPTIONAL,
	...
 }

--SecondaryCPICH-InformationItem-Cell-ReconfRqstFDD-ExtIEs NBAP-PROTOCOL-EXTENSION ::= {
--	...
--}
 
PrimaryCCPCH-Information-Cell-ReconfRqstFDD ::= SEQUENCE {
 	bCH-information							BCH-information-Cell-ReconfRqstFDD,
--	iE-Extensions							ProtocolExtensionContainer { { PrimaryCCPCH-Information-Cell-ReconfRqstFDD-ExtIEs} }		OPTIONAL,
	iE-Extensions							ProtocolExtensionContainer OPTIONAL,
	...
 }

--PrimaryCCPCH-Information-Cell-ReconfRqstFDD-ExtIEs NBAP-PROTOCOL-EXTENSION ::= {
--	...
--}

BCH-information-Cell-ReconfRqstFDD ::= SEQUENCE {
 	commonTransportChannelID				CommonTransportChannelID,
 	bCH-Power								DL-Power,
--	iE-Extensions							ProtocolExtensionContainer { { BCH-information-Cell-ReconfRqstFDD-ExtIEs} }		OPTIONAL,
	iE-Extensions							ProtocolExtensionContainer OPTIONAL,
	...
 }

--BCH-information-Cell-ReconfRqstFDD-ExtIEs NBAP-PROTOCOL-EXTENSION ::= {
--	...
--}

IPDLParameter-Information-Cell-ReconfRqstFDD::= SEQUENCE {
	iPDL-FDD-Parameters							IPDL-FDD-Parameters		OPTIONAL,
	iPDL-Indicator								IPDL-Indicator,
--	iE-Extensions							ProtocolExtensionContainer { { IPDLParameter-Information-Cell-ReconfRqstFDD-ExtIEs} }		OPTIONAL,
	iE-Extensions							ProtocolExtensionContainer OPTIONAL,
	...
}

--IPDLParameter-Information-Cell-ReconfRqstFDD-ExtIEs NBAP-PROTOCOL-EXTENSION ::= {
--	...
--}

--CellPortion-InformationList-Cell-ReconfRqstFDD ::= SEQUENCE (SIZE (1..maxNrOfCellPortionsPerCell)) OF ProtocolIE-Single-Container{{ CellPortion-InformationItemIE-Cell-ReconfRqstFDD }}
CellPortion-InformationList-Cell-ReconfRqstFDD ::= SEQUENCE (SIZE (1..64)) OF ProtocolIE-Single-Container

--CellPortion-InformationItemIE-Cell-ReconfRqstFDD NBAP-PROTOCOL-IES ::= {
--	{ ID id-CellPortion-InformationItem-Cell-ReconfRqstFDD	CRITICALITY reject	TYPE CellPortion-InformationItem-Cell-ReconfRqstFDD					PRESENCE	mandatory}
--}

CellPortion-InformationItem-Cell-ReconfRqstFDD::= SEQUENCE {
	cellPortionID							CellPortionID,
	maximumTransmissionPowerforCellPortion				MaximumTransmissionPower,
--	iE-Extensions							ProtocolExtensionContainer { { CellPortion-InformationItem-Cell-ReconfRqstFDD-ExtIEs} }		OPTIONAL,
	iE-Extensions							ProtocolExtensionContainer OPTIONAL,
	...
}

--CellPortion-InformationItem-Cell-ReconfRqstFDD-ExtIEs NBAP-PROTOCOL-EXTENSION ::= {
--...
--}

-- **************************************************************
--
-- CELL RECONFIGURATION REQUEST TDD
--
-- **************************************************************

--CellReconfigurationRequestTDD ::= SEQUENCE {
--	protocolIEs				ProtocolIE-Container	{{CellReconfigurationRequestTDD-IEs}},
--	protocolExtensions		ProtocolExtensionContainer	{{CellReconfigurationRequestTDD-Extensions}}		OPTIONAL,
--	...
--}
CellReconfigurationRequestTDD ::= SEQUENCE {
	protocolIEs				ProtocolIE-Container,
	protocolExtensions		ProtocolExtensionContainer	OPTIONAL,
	...
}

--CellReconfigurationRequestTDD-IEs NBAP-PROTOCOL-IES ::= {
--	{ ID id-C-ID											CRITICALITY reject	TYPE C-ID						PRESENCE mandatory }|
--	{ ID id-ConfigurationGenerationID						CRITICALITY reject	TYPE ConfigurationGenerationID				PRESENCE mandatory }|
--	{ ID id-Synchronisation-Configuration-Cell-ReconfRqst	CRITICALITY reject	TYPE Synchronisation-Configuration-Cell-ReconfRqst		PRESENCE optional }|
--	{ ID id-TimingAdvanceApplied							CRITICALITY reject	TYPE TimingAdvanceApplied				PRESENCE optional }|
--	{ ID id-SCH-Information-Cell-ReconfRqstTDD				CRITICALITY reject	TYPE SCH-Information-Cell-ReconfRqstTDD		PRESENCE optional }|
	-- Applicable to 3.84Mcps TDD only
--	{ ID id-PCCPCH-Information-Cell-ReconfRqstTDD			CRITICALITY reject	TYPE PCCPCH-Information-Cell-ReconfRqstTDD	PRESENCE optional }|
--	{ ID id-MaximumTransmissionPower						CRITICALITY reject	TYPE MaximumTransmissionPower				PRESENCE optional }|
--	{ ID id-DPCHConstant									CRITICALITY reject	TYPE ConstantValue				PRESENCE optional }|
	-- This IE shall be ignored by the Node B.
--	{ ID id-PUSCHConstant									CRITICALITY reject	TYPE ConstantValue				PRESENCE optional }|
	-- This IE shall be ignored by the Node B.
--	{ ID id-PRACHConstant									CRITICALITY reject	TYPE ConstantValue				PRESENCE optional }|
	-- This IE shall be ignored by the Node B.
--	{ ID id-TimeSlotConfigurationList-Cell-ReconfRqstTDD	CRITICALITY reject	TYPE TimeSlotConfigurationList-Cell-ReconfRqstTDD		PRESENCE optional },
	-- Mandatory for 3.84Mcps TDD only. Not Applicable to 1.28Mcps TDD.
--	...
--}

--CellReconfigurationRequestTDD-Extensions NBAP-PROTOCOL-EXTENSION ::= {
--	{ ID	id-TimeSlotConfigurationList-LCR-Cell-ReconfRqstTDD	CRITICALITY reject	EXTENSION TimeSlotConfigurationList-LCR-Cell-ReconfRqstTDD	PRESENCE optional }|
	-- Mandatory for 1.28Mcps TDD, Not Applicable to 3.84Mcps TDD
--	{ ID	id-DwPCH-LCR-Information-Cell-ReconfRqstTDD			CRITICALITY reject	EXTENSION DwPCH-LCR-Information-Cell-ReconfRqstTDD			PRESENCE optional }|
	-- Mandatory for 1.28Mcps TDD, Not Applicable to 3.84Mcps TDD
--	{ ID	id-IPDLParameter-Information-Cell-ReconfRqstTDD		CRITICALITY reject	EXTENSION IPDLParameter-Information-Cell-ReconfRqstTDD		PRESENCE optional }|
	-- Applicable to 3.84Mcps TDD only
--	{ ID	id-IPDLParameter-Information-LCR-Cell-ReconfRqstTDD	CRITICALITY reject	EXTENSION IPDLParameter-Information-LCR-Cell-ReconfRqstTDD	PRESENCE optional },
	-- Applicable to 1.28Mcps TDD only
--	...
--}

SCH-Information-Cell-ReconfRqstTDD ::= SEQUENCE {
	commonPhysicalChannelID					CommonPhysicalChannelID,
	sCH-Power								DL-Power,
--	iE-Extensions							ProtocolExtensionContainer { { PSCH-Information-Cell-ReconfRqstTDD-ExtIEs} }		OPTIONAL,
	iE-Extensions							ProtocolExtensionContainer OPTIONAL,
	...
}

--PSCH-Information-Cell-ReconfRqstTDD-ExtIEs NBAP-PROTOCOL-EXTENSION ::= {
--	...
--}

PCCPCH-Information-Cell-ReconfRqstTDD ::= SEQUENCE {
	commonPhysicalChannelID					CommonPhysicalChannelID,
	pCCPCH-Power							PCCPCH-Power,
--	iE-Extensions							ProtocolExtensionContainer { { PCCPCH-Information-Cell-ReconfRqstTDD-ExtIEs} }		OPTIONAL,
	iE-Extensions							ProtocolExtensionContainer OPTIONAL,
	...
}

--PCCPCH-Information-Cell-ReconfRqstTDD-ExtIEs NBAP-PROTOCOL-EXTENSION ::= {
--	...
--}

TimeSlotConfigurationList-Cell-ReconfRqstTDD ::= SEQUENCE (SIZE (1..15)) OF TimeSlotConfigurationItem-Cell-ReconfRqstTDD

TimeSlotConfigurationItem-Cell-ReconfRqstTDD ::= SEQUENCE {
	timeSlot								TimeSlot,
 	timeSlotStatus							TimeSlotStatus,
 	timeSlotDirection						TimeSlotDirection,
--	iE-Extensions							ProtocolExtensionContainer { { TimeSlotConfigurationItem-Cell-ReconfRqstTDD-ExtIEs} }		OPTIONAL,
	iE-Extensions							ProtocolExtensionContainer OPTIONAL,
	...
 }

--TimeSlotConfigurationItem-Cell-ReconfRqstTDD-ExtIEs NBAP-PROTOCOL-EXTENSION ::= {
--	...
--}

TimeSlotConfigurationList-LCR-Cell-ReconfRqstTDD ::= SEQUENCE (SIZE (1..7)) OF TimeSlotConfigurationItem-LCR-Cell-ReconfRqstTDD

TimeSlotConfigurationItem-LCR-Cell-ReconfRqstTDD ::= SEQUENCE {
	timeSlotLCR								TimeSlotLCR,
 	timeSlotStatus							TimeSlotStatus,
 	timeSlotDirection						TimeSlotDirection,
--	iE-Extensions							ProtocolExtensionContainer { { TimeSlotConfigurationItem-LCR-Cell-ReconfRqstTDD-ExtIEs} }		OPTIONAL,
	iE-Extensions							ProtocolExtensionContainer OPTIONAL,
	...
 }

--TimeSlotConfigurationItem-LCR-Cell-ReconfRqstTDD-ExtIEs NBAP-PROTOCOL-EXTENSION ::= {
--	...
--}

DwPCH-LCR-Information-Cell-ReconfRqstTDD ::= SEQUENCE {
	commonPhysicalChannelId					CommonPhysicalChannelID,
 	dwPCH-Power								DwPCH-Power,
--	iE-Extensions							ProtocolExtensionContainer { { DwPCH-LCR-Information-Cell-ReconfRqstTDD-ExtIEs} }		OPTIONAL,
	iE-Extensions							ProtocolExtensionContainer OPTIONAL,
	...
 }

--DwPCH-LCR-Information-Cell-ReconfRqstTDD-ExtIEs NBAP-PROTOCOL-EXTENSION ::= {
--	...
--}

IPDLParameter-Information-Cell-ReconfRqstTDD ::= SEQUENCE {
	iPDL-TDD-Parameters						IPDL-TDD-Parameters		OPTIONAL,
	iPDL-Indicator							IPDL-Indicator,
--	iE-Extensions							ProtocolExtensionContainer { { IPDLParameter-Information-Cell-ReconfRqstTDD-ExtIEs} }		OPTIONAL,
	iE-Extensions							ProtocolExtensionContainer OPTIONAL,
	...
}

--IPDLParameter-Information-Cell-ReconfRqstTDD-ExtIEs NBAP-PROTOCOL-EXTENSION ::= {
--	...
--}

IPDLParameter-Information-LCR-Cell-ReconfRqstTDD ::= SEQUENCE {
	iPDL-TDD-Parameters-LCR					IPDL-TDD-Parameters-LCR		OPTIONAL,
	iPDL-Indicator							IPDL-Indicator,
--	iE-Extensions							ProtocolExtensionContainer { { IPDLParameter-Information-LCR-Cell-ReconfRqstTDD-ExtIEs} }		OPTIONAL,
	iE-Extensions							ProtocolExtensionContainer OPTIONAL,
	...
}

--IPDLParameter-Information-LCR-Cell-ReconfRqstTDD-ExtIEs NBAP-PROTOCOL-EXTENSION ::= {
--	...
--}

-- **************************************************************
--
-- CELL RECONFIGURATION RESPONSE
--
-- **************************************************************

--CellReconfigurationResponse ::= SEQUENCE {
--	protocolIEs					ProtocolIE-Container	{{CellReconfigurationResponse-IEs}},
--	protocolExtensions			ProtocolExtensionContainer	{{CellReconfigurationResponse-Extensions}}		OPTIONAL,
--	...
--}
CellReconfigurationResponse ::= SEQUENCE {
	protocolIEs					ProtocolIE-Container,
	protocolExtensions			ProtocolExtensionContainer OPTIONAL,
	...
}

--CellReconfigurationResponse-IEs NBAP-PROTOCOL-IES ::= {
--	{ ID	id-CriticalityDiagnostics		CRITICALITY		ignore			TYPE	CriticalityDiagnostics		PRESENCE	optional},
--	...
--}

--CellReconfigurationResponse-Extensions NBAP-PROTOCOL-EXTENSION ::= {
--	...
--}

-- **************************************************************
--
-- CELL RECONFIGURATION FAILURE
--
-- **************************************************************

--CellReconfigurationFailure ::= SEQUENCE {
--	protocolIEs				ProtocolIE-Container	{{CellReconfigurationFailure-IEs}},
--	protocolExtensions		ProtocolExtensionContainer	{{CellReconfigurationFailure-Extensions}}		OPTIONAL,
--	...
--}
CellReconfigurationFailure ::= SEQUENCE {
	protocolIEs				ProtocolIE-Container,
	protocolExtensions		ProtocolExtensionContainer	OPTIONAL,
	...
}
--CellReconfigurationFailure-IEs NBAP-PROTOCOL-IES ::= {
--	{ ID id-Cause						CRITICALITY ignore			TYPE Cause							PRESENCE mandatory	}|
--	{ ID id-CriticalityDiagnostics		CRITICALITY ignore			TYPE CriticalityDiagnostics			PRESENCE optional	},
--	...
--}

--CellReconfigurationFailure-Extensions NBAP-PROTOCOL-EXTENSION ::= {
--	...
--}

-- **************************************************************
--
-- CELL DELETION REQUEST
--
-- **************************************************************

--CellDeletionRequest ::= SEQUENCE {
--	protocolIEs				ProtocolIE-Container	{{CellDeletionRequest-IEs}},
--	protocolExtensions		ProtocolExtensionContainer	{{CellDeletionRequest-Extensions}}		OPTIONAL,
--	...
--}

CellDeletionRequest ::= SEQUENCE {
	protocolIEs				ProtocolIE-Container,
	protocolExtensions		ProtocolExtensionContainer	OPTIONAL,
	...
}

--CellDeletionRequest-IEs NBAP-PROTOCOL-IES ::= {
--	{ ID	id-C-ID			CRITICALITY		reject			TYPE	C-ID		PRESENCE	mandatory},
--	...
--}

--CellDeletionRequest-Extensions NBAP-PROTOCOL-EXTENSION ::= {
--	...
--}

-- **************************************************************
--
-- CELL DELETION RESPONSE
--
-- **************************************************************

--CellDeletionResponse ::= SEQUENCE {
--	protocolIEs				ProtocolIE-Container	{{CellDeletionResponse-IEs}},
--	protocolExtensions		ProtocolExtensionContainer	{{CellDeletionResponse-Extensions}}		OPTIONAL,
--	...
--}

CellDeletionResponse ::= SEQUENCE {
	protocolIEs				ProtocolIE-Container,
	protocolExtensions		ProtocolExtensionContainer	OPTIONAL,
	...
}

--CellDeletionResponse-IEs NBAP-PROTOCOL-IES ::= {
--	{ ID	id-CriticalityDiagnostics		CRITICALITY		ignore			TYPE	CriticalityDiagnostics		PRESENCE	optional},
--	...
--}

--CellDeletionResponse-Extensions NBAP-PROTOCOL-EXTENSION ::= {
--	...
--}

-- **************************************************************
--
-- RESOURCE STATUS INDICATION
--
-- **************************************************************

--ResourceStatusIndication ::= SEQUENCE {
--	protocolIEs				ProtocolIE-Container	{{ResourceStatusIndication-IEs}},
--	protocolExtensions		ProtocolExtensionContainer	{{ResourceStatusIndication-Extensions}}		OPTIONAL,
--	...
--}
ResourceStatusIndication ::= SEQUENCE {
	protocolIEs				ProtocolIE-Container,
	protocolExtensions		ProtocolExtensionContainer	OPTIONAL,
	...
}
--ResourceStatusIndication-IEs NBAP-PROTOCOL-IES ::= {
--	{ ID id-IndicationType-ResourceStatusInd	CRITICALITY ignore	TYPE IndicationType-ResourceStatusInd		PRESENCE mandatory }|
--	{ ID id-Cause								CRITICALITY ignore	TYPE Cause							PRESENCE optional },
--	...
--}

--ResourceStatusIndication-Extensions NBAP-PROTOCOL-EXTENSION ::= {
--	...
--}

IndicationType-ResourceStatusInd ::= CHOICE {
	no-Failure								No-Failure-ResourceStatusInd,
	serviceImpacting						ServiceImpacting-ResourceStatusInd,
	...
}

No-Failure-ResourceStatusInd ::= SEQUENCE {
	local-Cell-InformationList				Local-Cell-InformationList-ResourceStatusInd,
	local-Cell-Group-InformationList		Local-Cell-Group-InformationList-ResourceStatusInd	OPTIONAL,
--	iE-Extensions							ProtocolExtensionContainer { { No-FailureItem-ResourceStatusInd-ExtIEs} }	OPTIONAL,
	iE-Extensions							ProtocolExtensionContainer OPTIONAL,
	...
}

--No-FailureItem-ResourceStatusInd-ExtIEs NBAP-PROTOCOL-EXTENSION ::= {
--	{ ID	id-Power-Local-Cell-Group-InformationList-ResourceStatusInd		CRITICALITY		ignore			EXTENSION	Power-Local-Cell-Group-InformationList-ResourceStatusInd		PRESENCE	optional	},
--	...
--}

--Local-Cell-InformationList-ResourceStatusInd ::= SEQUENCE(SIZE (1..maxLocalCellinNodeB)) OF ProtocolIE-Single-Container {{ Local-Cell-InformationItemIE-ResourceStatusInd }}
Local-Cell-InformationList-ResourceStatusInd ::= SEQUENCE(SIZE (1..256)) OF ProtocolIE-Single-Container

--Local-Cell-InformationItemIE-ResourceStatusInd NBAP-PROTOCOL-IES ::= {
--	{ ID id-Local-Cell-InformationItem-ResourceStatusInd   CRITICALITY ignore	TYPE Local-Cell-InformationItem-ResourceStatusInd		PRESENCE mandatory }
--}

Local-Cell-InformationItem-ResourceStatusInd ::= SEQUENCE {
	local-CellID								Local-Cell-ID,
	addorDeleteIndicator						AddorDeleteIndicator,
	dl-or-global-capacityCredit					DL-or-Global-CapacityCredit					OPTIONAL,
	-- This IE shall be present if AddorDeleteIndicator IE is set to “add”
	ul-capacityCredit							UL-CapacityCredit							OPTIONAL,
	commonChannelsCapacityConsumptionLaw 		CommonChannelsCapacityConsumptionLaw		OPTIONAL,
	-- This IE shall be present if AddorDeleteIndicator IE is set to “add”
	dedicatedChannelsCapacityConsumptionLaw 	DedicatedChannelsCapacityConsumptionLaw		OPTIONAL,
	-- This IE shall be present if AddorDeleteIndicator IE is set to “add”
	maximumDL-PowerCapability					MaximumDL-PowerCapability					OPTIONAL,
	-- This IE shall be present if AddorDeleteIndicator IE is set to “add”
	minSpreadingFactor							MinSpreadingFactor							OPTIONAL,
	-- This IE shall be present if AddorDeleteIndicator IE is set to “add”
	minimumDL-PowerCapability					MinimumDL-PowerCapability					OPTIONAL,
	-- This IE shall be present if AddorDeleteIndicator IE is set to “add”
	local-Cell-Group-ID							Local-Cell-ID								OPTIONAL,
--	iE-Extensions								ProtocolExtensionContainer { { Local-Cell-InformationItem-ResourceStatusInd-ExtIEs} }	OPTIONAL,
	iE-Extensions								ProtocolExtensionContainer OPTIONAL,
	...
}

--Local-Cell-InformationItem-ResourceStatusInd-ExtIEs NBAP-PROTOCOL-EXTENSION ::= {
--	{ ID	id-ReferenceClockAvailability		CRITICALITY ignore		EXTENSION ReferenceClockAvailability			PRESENCE	optional }|
	-- This IE shall be present if AddorDeleteIndicator IE is set to “add“ and the Local Cell is related to a TDD cell
--	{ ID	id-Power-Local-Cell-Group-ID		CRITICALITY ignore		EXTENSION Local-Cell-ID				PRESENCE	optional }|
--	{ ID	id-HSDPA-Capability					CRITICALITY ignore		EXTENSION HSDPA-Capability			PRESENCE	optional }|
--	{ ID	id-E-DCH-Capability					CRITICALITY ignore		EXTENSION E-DCH-Capability			PRESENCE	optional }|
--	{ ID	id-E-DCH-CapacityConsumptionLaw		CRITICALITY ignore		EXTENSION DedicatedChannelsCapacityConsumptionLaw		PRESENCE	optional },
--	...
--}

--Local-Cell-Group-InformationList-ResourceStatusInd ::= SEQUENCE(SIZE (1..maxLocalCellinNodeB)) OF ProtocolIE-Single-Container {{ Local-Cell-Group-InformationItemIE-ResourceStatusInd }}
Local-Cell-Group-InformationList-ResourceStatusInd ::= SEQUENCE(SIZE (1..256)) OF ProtocolIE-Single-Container

--Local-Cell-Group-InformationItemIE-ResourceStatusInd NBAP-PROTOCOL-IES ::= {
--	{ ID id-Local-Cell-Group-InformationItem-ResourceStatusInd   CRITICALITY ignore	TYPE Local-Cell-Group-InformationItem-ResourceStatusInd		PRESENCE mandatory }
--}

Local-Cell-Group-InformationItem-ResourceStatusInd::= SEQUENCE {
	local-Cell-Group-ID							Local-Cell-ID,
	dl-or-global-capacityCredit					DL-or-Global-CapacityCredit,
	ul-capacityCredit							UL-CapacityCredit		OPTIONAL,
	commonChannelsCapacityConsumptionLaw 		CommonChannelsCapacityConsumptionLaw,
	dedicatedChannelsCapacityConsumptionLaw 	DedicatedChannelsCapacityConsumptionLaw,
--	iE-Extensions								ProtocolExtensionContainer { { Local-Cell-Group-InformationItem-ResourceStatusInd-ExtIEs} }	OPTIONAL,
	iE-Extensions								ProtocolExtensionContainer OPTIONAL,
	...
}

--Local-Cell-Group-InformationItem-ResourceStatusInd-ExtIEs NBAP-PROTOCOL-EXTENSION ::= {
--	{ ID	id-E-DCH-CapacityConsumptionLaw		CRITICALITY ignore		EXTENSION DedicatedChannelsCapacityConsumptionLaw		PRESENCE	optional },
--	...
--}

--Power-Local-Cell-Group-InformationList-ResourceStatusInd ::= SEQUENCE(SIZE (1..maxLocalCellinNodeB)) OF ProtocolIE-Single-Container {{ Power-Local-Cell-Group-InformationItemIE-ResourceStatusInd }}
Power-Local-Cell-Group-InformationList-ResourceStatusInd ::= SEQUENCE(SIZE (1..256)) OF ProtocolIE-Single-Container

--Power-Local-Cell-Group-InformationItemIE-ResourceStatusInd NBAP-PROTOCOL-IES ::= {
--	{ ID	id-Power-Local-Cell-Group-InformationItem-ResourceStatusInd	CRITICALITY ignore	TYPE	Power-Local-Cell-Group-InformationItem-ResourceStatusInd		PRESENCE	mandatory	}
--}

Power-Local-Cell-Group-InformationItem-ResourceStatusInd::= SEQUENCE {
	power-Local-Cell-Group-ID					Local-Cell-ID,
	maximumDL-PowerCapability					MaximumDL-PowerCapability,
--	iE-Extensions								ProtocolExtensionContainer { { Power-Local-Cell-Group-InformationItem-ResourceStatusInd-ExtIEs} }	OPTIONAL,
	iE-Extensions								ProtocolExtensionContainer OPTIONAL,
	...
}

--Power-Local-Cell-Group-InformationItem-ResourceStatusInd-ExtIEs NBAP-PROTOCOL-EXTENSION ::= {
--	...
--}

ServiceImpacting-ResourceStatusInd ::= SEQUENCE {
	local-Cell-InformationList				Local-Cell-InformationList2-ResourceStatusInd	OPTIONAL,
	local-Cell-Group-InformationList		Local-Cell-Group-InformationList2-ResourceStatusInd	OPTIONAL,
	cCP-InformationList						CCP-InformationList-ResourceStatusInd 			OPTIONAL,
	cell-InformationList					Cell-InformationList-ResourceStatusInd 			OPTIONAL,
--	iE-Extensions							ProtocolExtensionContainer { { ServiceImpactingItem-ResourceStatusInd-ExtIEs} }		OPTIONAL,
	iE-Extensions							ProtocolExtensionContainer OPTIONAL,
	...
}

--ServiceImpactingItem-ResourceStatusInd-ExtIEs NBAP-PROTOCOL-EXTENSION ::= {
--	{ ID	id-Power-Local-Cell-Group-InformationList2-ResourceStatusInd		CRITICALITY		ignore			EXTENSION	Power-Local-Cell-Group-InformationList2-ResourceStatusInd		PRESENCE	optional	},
--	...
--}

--Local-Cell-InformationList2-ResourceStatusInd ::= SEQUENCE(SIZE (1..maxLocalCellinNodeB)) OF ProtocolIE-Single-Container {{ Local-Cell-InformationItemIE2-ResourceStatusInd }}
Local-Cell-InformationList2-ResourceStatusInd ::= SEQUENCE(SIZE (1..256)) OF ProtocolIE-Single-Container

--Local-Cell-InformationItemIE2-ResourceStatusInd NBAP-PROTOCOL-IES ::= {
--	{ ID id-Local-Cell-InformationItem2-ResourceStatusInd   CRITICALITY ignore	TYPE Local-Cell-InformationItem2-ResourceStatusInd		PRESENCE mandatory }
--}

Local-Cell-InformationItem2-ResourceStatusInd ::= SEQUENCE {
	local-Cell-ID								Local-Cell-ID,
	dl-or-global-capacityCredit					DL-or-Global-CapacityCredit				OPTIONAL,
	ul-capacityCredit							UL-CapacityCredit						OPTIONAL,
	commonChannelsCapacityConsumptionLaw		CommonChannelsCapacityConsumptionLaw	OPTIONAL,
	dedicatedChannelsCapacityConsumptionLaw		DedicatedChannelsCapacityConsumptionLaw	OPTIONAL,
	maximum-DL-PowerCapability					MaximumDL-PowerCapability				OPTIONAL,
	minSpreadingFactor							MinSpreadingFactor						OPTIONAL,
	minimumDL-PowerCapability					MinimumDL-PowerCapability				OPTIONAL,
--	iE-Extensions							ProtocolExtensionContainer { { Local-Cell-InformationItem2-ResourceStatusInd-ExtIEs} }		OPTIONAL,
	iE-Extensions							ProtocolExtensionContainer OPTIONAL,
	...
}

--Local-Cell-InformationItem2-ResourceStatusInd-ExtIEs NBAP-PROTOCOL-EXTENSION ::= {
--	{ ID	id-ReferenceClockAvailability		CRITICALITY ignore			EXTENSION ReferenceClockAvailability			PRESENCE	optional }|
--	{ ID	id-HSDPA-Capability					CRITICALITY ignore			EXTENSION HSDPA-Capability			PRESENCE	optional }|
--	{ ID	id-E-DCH-Capability					CRITICALITY ignore			EXTENSION E-DCH-Capability			PRESENCE	optional }|
--	{ ID	id-E-DCH-CapacityConsumptionLaw		CRITICALITY ignore		EXTENSION DedicatedChannelsCapacityConsumptionLaw		PRESENCE	optional },
--	...
--}

--Local-Cell-Group-InformationList2-ResourceStatusInd ::= SEQUENCE(SIZE (1..maxLocalCellinNodeB)) OF ProtocolIE-Single-Container {{ Local-Cell-Group-InformationItemIE2-ResourceStatusInd }}
Local-Cell-Group-InformationList2-ResourceStatusInd ::= SEQUENCE(SIZE (1..256)) OF ProtocolIE-Single-Container 

--Local-Cell-Group-InformationItemIE2-ResourceStatusInd NBAP-PROTOCOL-IES ::= {
--	{ ID id-Local-Cell-Group-InformationItem2-ResourceStatusInd   CRITICALITY ignore	TYPE Local-Cell-Group-InformationItem2-ResourceStatusInd		PRESENCE mandatory }
--}

Local-Cell-Group-InformationItem2-ResourceStatusInd ::= SEQUENCE {
	local-Cell-Group-ID							Local-Cell-ID,
	dl-or-global-capacityCredit					DL-or-Global-CapacityCredit					OPTIONAL,
	ul-capacityCredit							UL-CapacityCredit							OPTIONAL,
	commonChannelsCapacityConsumptionLaw		CommonChannelsCapacityConsumptionLaw		OPTIONAL,
	dedicatedChannelsCapacityConsumptionLaw		DedicatedChannelsCapacityConsumptionLaw		OPTIONAL,
--	iE-Extensions							ProtocolExtensionContainer { { Local-Cell-Group-InformationItem2-ResourceStatusInd-ExtIEs} }		OPTIONAL,
	iE-Extensions							ProtocolExtensionContainer OPTIONAL,
	...
}

--Local-Cell-Group-InformationItem2-ResourceStatusInd-ExtIEs NBAP-PROTOCOL-EXTENSION ::= {
--	{ ID	id-E-DCH-CapacityConsumptionLaw		CRITICALITY ignore		EXTENSION DedicatedChannelsCapacityConsumptionLaw		PRESENCE	optional },
--	...
--}

--Power-Local-Cell-Group-InformationList2-ResourceStatusInd ::= SEQUENCE(SIZE (1..maxLocalCellinNodeB)) OF ProtocolIE-Single-Container {{ Power-Local-Cell-Group-InformationItemIE2-ResourceStatusInd }}
Power-Local-Cell-Group-InformationList2-ResourceStatusInd ::= SEQUENCE(SIZE (1..256)) OF ProtocolIE-Single-Container

--Power-Local-Cell-Group-InformationItemIE2-ResourceStatusInd NBAP-PROTOCOL-IES ::= {
--	{ ID	id-Power-Local-Cell-Group-InformationItem2-ResourceStatusInd	CRITICALITY ignore	TYPE	Power-Local-Cell-Group-InformationItem2-ResourceStatusInd		PRESENCE	mandatory	}
--}

Power-Local-Cell-Group-InformationItem2-ResourceStatusInd::= SEQUENCE {
	power-Local-Cell-Group-ID					Local-Cell-ID,
	maximumDL-PowerCapability					MaximumDL-PowerCapability,
--	iE-Extensions								ProtocolExtensionContainer { { Power-Local-Cell-Group-InformationItem2-ResourceStatusInd-ExtIEs} }	OPTIONAL,
	iE-Extensions								ProtocolExtensionContainer OPTIONAL,
	...
}

--Power-Local-Cell-Group-InformationItem2-ResourceStatusInd-ExtIEs NBAP-PROTOCOL-EXTENSION ::= {
--	...
--}

--CCP-InformationList-ResourceStatusInd ::= SEQUENCE (SIZE (1..maxCCPinNodeB)) OF ProtocolIE-Single-Container {{ CCP-InformationItemIE-ResourceStatusInd }}
CCP-InformationList-ResourceStatusInd ::= SEQUENCE (SIZE (1..256)) OF ProtocolIE-Single-Container 

--CCP-InformationItemIE-ResourceStatusInd NBAP-PROTOCOL-IES ::= {
--	{ ID id-CCP-InformationItem-ResourceStatusInd   CRITICALITY ignore	TYPE CCP-InformationItem-ResourceStatusInd		PRESENCE mandatory }
--}

CCP-InformationItem-ResourceStatusInd ::= SEQUENCE {
	communicationControlPortID				CommunicationControlPortID,
	resourceOperationalState				ResourceOperationalState,
	availabilityStatus						AvailabilityStatus,
--	iE-Extensions							ProtocolExtensionContainer { { CCP-InformationItem-ResourceStatusInd-ExtIEs} }		OPTIONAL,
	iE-Extensions							ProtocolExtensionContainer OPTIONAL,
	...
}

--CCP-InformationItem-ResourceStatusInd-ExtIEs NBAP-PROTOCOL-EXTENSION ::= {
--	...
--}

--Cell-InformationList-ResourceStatusInd ::= SEQUENCE (SIZE (1..maxCellinNodeB)) OF ProtocolIE-Single-Container {{ Cell-InformationItemIE-ResourceStatusInd }}
Cell-InformationList-ResourceStatusInd ::= SEQUENCE (SIZE (1..256)) OF ProtocolIE-Single-Container

--Cell-InformationItemIE-ResourceStatusInd NBAP-PROTOCOL-IES ::= {
--	{ ID id-Cell-InformationItem-ResourceStatusInd   CRITICALITY ignore	TYPE Cell-InformationItem-ResourceStatusInd		PRESENCE mandatory }
--}

Cell-InformationItem-ResourceStatusInd  ::= SEQUENCE {
	c-ID									C-ID,
	resourceOperationalState 				ResourceOperationalState						OPTIONAL,
	availabilityStatus						AvailabilityStatus								OPTIONAL,
	primary-SCH-Information					P-SCH-Information-ResourceStatusInd				OPTIONAL, -- FDD only
	secondary-SCH-Information				S-SCH-Information-ResourceStatusInd				OPTIONAL, -- FDD only
	primary-CPICH-Information				P-CPICH-Information-ResourceStatusInd			OPTIONAL, -- FDD only
	secondary-CPICH-Information				S-CPICH-InformationList-ResourceStatusInd		OPTIONAL, -- FDD only
	primary-CCPCH-Information				P-CCPCH-Information-ResourceStatusInd			OPTIONAL,
	bCH-Information							BCH-Information-ResourceStatusInd 				OPTIONAL,
	secondary-CCPCH-InformationList			S-CCPCH-InformationList-ResourceStatusInd		OPTIONAL,
	pCH-Information							PCH-Information-ResourceStatusInd 				OPTIONAL,
	pICH-Information						PICH-Information-ResourceStatusInd				OPTIONAL,
	fACH-InformationList					FACH-InformationList-ResourceStatusInd 			OPTIONAL,
	pRACH-InformationList					PRACH-InformationList-ResourceStatusInd			OPTIONAL,
	rACH-InformationList					RACH-InformationList-ResourceStatusInd 			OPTIONAL,
	aICH-InformationList					AICH-InformationList-ResourceStatusInd 			OPTIONAL, -- FDD only
	notUsed-1-pCPCH-InformationList			NULL											OPTIONAL,
	notUsed-2-cPCH-InformationList			NULL											OPTIONAL,
	notUsed-3-aP-AICH-InformationList		NULL											OPTIONAL,
	notUsed-4-cDCA-ICH-InformationList		NULL											OPTIONAL,
	sCH-Information							SCH-Information-ResourceStatusInd 				OPTIONAL, -- Applicable to 3.84Mcps TDD only
--	iE-Extensions							ProtocolExtensionContainer { { Cell-InformationItem-ResourceStatusInd-ExtIEs} }	OPTIONAL,
	iE-Extensions							ProtocolExtensionContainer OPTIONAL,
	...
}

--Cell-InformationItem-ResourceStatusInd-ExtIEs NBAP-PROTOCOL-EXTENSION ::= {
--	{ ID id-FPACH-LCR-InformationList-ResourceStatusInd			CRITICALITY ignore	EXTENSION FPACH-LCR-InformationList-ResourceStatusInd			PRESENCE optional }|
	-- Applicable to 1.28Mcps TDD only
--	{ ID id-DwPCH-LCR-Information-ResourceStatusInd				CRITICALITY ignore	EXTENSION DwPCH-LCR-Information-ResourceStatusInd					PRESENCE optional }|
	-- Applicable to 1.28Mcps TDD only
--	{ ID id-HSDSCH-Resources-Information-ResourceStatusInd		CRITICALITY ignore	EXTENSION HS-DSCH-Resources-Information-ResourceStatusInd			PRESENCE optional }|
--	{ ID id-MICH-Information-ResourceStatusInd					CRITICALITY ignore	EXTENSION Common-PhysicalChannel-Status-Information				PRESENCE optional }|
--	{ ID id-S-CCPCH-InformationListExt-ResourceStatusInd		CRITICALITY ignore	EXTENSION S-CCPCH-InformationListExt-ResourceStatusInd			PRESENCE optional }|
	-- Applicable to 3.84Mcps TDD only, used when there are more than maxSCCPCHCell SCCPCHs in the message.
--	{ ID id-S-CCPCH-LCR-InformationListExt-ResourceStatusInd	CRITICALITY ignore	EXTENSION S-CCPCH-LCR-InformationListExt-ResourceStatusInd		PRESENCE optional }|
	-- Applicable to 1.28Mcps TDD only, used when there are more than maxSCCPCHCell SCCPCHs in the message.
--	{ ID id-E-DCH-Resources-Information-ResourceStatusInd		CRITICALITY ignore	EXTENSION E-DCH-Resources-Information-ResourceStatusInd			PRESENCE optional },
--	...
--}

--P-SCH-Information-ResourceStatusInd ::= ProtocolIE-Single-Container {{ P-SCH-InformationIE-ResourceStatusInd }}
P-SCH-Information-ResourceStatusInd ::= ProtocolIE-Single-Container

--P-SCH-InformationIE-ResourceStatusInd NBAP-PROTOCOL-IES ::= {
--	{ ID id-P-SCH-Information   CRITICALITY ignore	TYPE Common-PhysicalChannel-Status-Information		PRESENCE mandatory }
--}

--S-SCH-Information-ResourceStatusInd ::= ProtocolIE-Single-Container {{ S-SCH-InformationIE-ResourceStatusInd }}
S-SCH-Information-ResourceStatusInd ::= ProtocolIE-Single-Container

--S-SCH-InformationIE-ResourceStatusInd NBAP-PROTOCOL-IES ::= {
--	{ ID id-S-SCH-Information   CRITICALITY ignore	TYPE Common-PhysicalChannel-Status-Information		PRESENCE mandatory }
--}

--P-CPICH-Information-ResourceStatusInd ::= ProtocolIE-Single-Container {{ P-CPICH-InformationIE-ResourceStatusInd }}
P-CPICH-Information-ResourceStatusInd ::= ProtocolIE-Single-Container

--P-CPICH-InformationIE-ResourceStatusInd NBAP-PROTOCOL-IES ::= {
--	{ ID id-P-CPICH-Information   CRITICALITY ignore	TYPE Common-PhysicalChannel-Status-Information		PRESENCE mandatory }
--}

--S-CPICH-InformationList-ResourceStatusInd ::= SEQUENCE (SIZE (1..maxSCPICHCell)) OF ProtocolIE-Single-Container {{ S-CPICH-InformationItemIE-ResourceStatusInd }}
S-CPICH-InformationList-ResourceStatusInd ::= SEQUENCE (SIZE (1..32)) OF ProtocolIE-Single-Container

--S-CPICH-InformationItemIE-ResourceStatusInd NBAP-PROTOCOL-IES ::= {
--	{ ID id-S-CPICH-Information   CRITICALITY ignore	TYPE Common-PhysicalChannel-Status-Information		PRESENCE mandatory }
--}

--P-CCPCH-Information-ResourceStatusInd ::= ProtocolIE-Single-Container {{ P-CCPCH-InformationIE-ResourceStatusInd }}
P-CCPCH-Information-ResourceStatusInd ::= ProtocolIE-Single-Container

--P-CCPCH-InformationIE-ResourceStatusInd NBAP-PROTOCOL-IES ::= {
--	{ ID id-P-CCPCH-Information   CRITICALITY ignore	TYPE Common-PhysicalChannel-Status-Information		PRESENCE mandatory }
--}

--BCH-Information-ResourceStatusInd ::= ProtocolIE-Single-Container {{ BCH-InformationIE-ResourceStatusInd }}
BCH-Information-ResourceStatusInd ::= ProtocolIE-Single-Container

--BCH-InformationIE-ResourceStatusInd NBAP-PROTOCOL-IES ::= {
--	{ ID id-BCH-Information   CRITICALITY ignore	TYPE Common-TransportChannel-Status-Information		PRESENCE mandatory }
--}

--S-CCPCH-InformationList-ResourceStatusInd ::= SEQUENCE (SIZE (1..maxSCCPCHCell)) OF ProtocolIE-Single-Container {{ S-CCPCH-InformationItemIE-ResourceStatusInd }}
S-CCPCH-InformationList-ResourceStatusInd ::= SEQUENCE (SIZE (1..32)) OF ProtocolIE-Single-Container

--S-CCPCH-InformationItemIE-ResourceStatusInd NBAP-PROTOCOL-IES ::= {
--	{ ID id-S-CCPCH-Information   CRITICALITY ignore	TYPE Common-PhysicalChannel-Status-Information		PRESENCE mandatory }
--}

--PCH-Information-ResourceStatusInd ::= ProtocolIE-Single-Container {{ PCH-InformationIE-ResourceStatusInd }}
PCH-Information-ResourceStatusInd ::= ProtocolIE-Single-Container

--PCH-InformationIE-ResourceStatusInd NBAP-PROTOCOL-IES ::= {
--	{ ID id-PCH-Information   CRITICALITY ignore	TYPE Common-TransportChannel-Status-Information		PRESENCE mandatory }
--}

--PICH-Information-ResourceStatusInd ::= ProtocolIE-Single-Container {{ PICH-InformationIE-ResourceStatusInd }}
PICH-Information-ResourceStatusInd ::= ProtocolIE-Single-Container

--PICH-InformationIE-ResourceStatusInd NBAP-PROTOCOL-IES ::= {
--	{ ID id-PICH-Information   CRITICALITY ignore	TYPE Common-PhysicalChannel-Status-Information		PRESENCE mandatory }
--}

--FACH-InformationList-ResourceStatusInd ::= SEQUENCE (SIZE (1..maxFACHCell)) OF ProtocolIE-Single-Container {{ FACH-InformationItemIE-ResourceStatusInd }}
FACH-InformationList-ResourceStatusInd ::= SEQUENCE (SIZE (1..256)) OF ProtocolIE-Single-Container


--FACH-InformationItemIE-ResourceStatusInd NBAP-PROTOCOL-IES ::= {
--	{ ID id-FACH-Information   CRITICALITY ignore	TYPE Common-TransportChannel-Status-Information		PRESENCE mandatory }
--}

--PRACH-InformationList-ResourceStatusInd ::= SEQUENCE (SIZE (1..maxPRACHCell)) OF ProtocolIE-Single-Container {{ PRACH-InformationItemIE-ResourceStatusInd }}
PRACH-InformationList-ResourceStatusInd ::= SEQUENCE (SIZE (1..16)) OF ProtocolIE-Single-Container

--PRACH-InformationItemIE-ResourceStatusInd NBAP-PROTOCOL-IES ::= {
--	{ ID id-PRACH-Information   CRITICALITY ignore	TYPE Common-PhysicalChannel-Status-Information		PRESENCE mandatory }
--}

--RACH-InformationList-ResourceStatusInd ::= SEQUENCE (SIZE (1..maxPRACHCell)) OF ProtocolIE-Single-Container {{ RACH-InformationItemIE-ResourceStatusInd }}
RACH-InformationList-ResourceStatusInd ::= SEQUENCE (SIZE (1..16)) OF ProtocolIE-Single-Container


--RACH-InformationItemIE-ResourceStatusInd NBAP-PROTOCOL-IES ::= {
--	{ ID id-RACH-Information   CRITICALITY ignore	TYPE Common-TransportChannel-Status-Information		PRESENCE mandatory }
--}

--AICH-InformationList-ResourceStatusInd ::= SEQUENCE (SIZE (1..maxPRACHCell)) OF ProtocolIE-Single-Container {{ AICH-InformationItemIE-ResourceStatusInd }}
AICH-InformationList-ResourceStatusInd ::= SEQUENCE (SIZE (1..16)) OF ProtocolIE-Single-Container

--AICH-InformationItemIE-ResourceStatusInd NBAP-PROTOCOL-IES ::= {
--	{ ID id-AICH-Information   CRITICALITY ignore	TYPE Common-PhysicalChannel-Status-Information		PRESENCE mandatory }
--}

--SCH-Information-ResourceStatusInd ::= ProtocolIE-Single-Container {{ SCH-InformationIE-ResourceStatusInd }}
SCH-Information-ResourceStatusInd ::= ProtocolIE-Single-Container

--SCH-InformationIE-ResourceStatusInd NBAP-PROTOCOL-IES ::= {
--	{ ID id-SCH-Information   CRITICALITY ignore	TYPE Common-PhysicalChannel-Status-Information		PRESENCE mandatory }
--}

--FPACH-LCR-InformationList-ResourceStatusInd ::= SEQUENCE (SIZE (1..maxFPACHCell)) OF ProtocolIE-Single-Container {{ FPACH-LCR-InformationItemIE-ResourceStatusInd }}
FPACH-LCR-InformationList-ResourceStatusInd ::= SEQUENCE (SIZE (1..8)) OF ProtocolIE-Single-Container


--FPACH-LCR-InformationItemIE-ResourceStatusInd NBAP-PROTOCOL-IES ::= {
--	{ ID id-FPACH-LCR-Information  CRITICALITY ignore	TYPE Common-PhysicalChannel-Status-Information		PRESENCE mandatory }
--}

--DwPCH-LCR-Information-ResourceStatusInd ::= ProtocolIE-Single-Container {{ DwPCH-LCR-InformationIE-ResourceStatusInd }}
DwPCH-LCR-Information-ResourceStatusInd ::= ProtocolIE-Single-Container

--DwPCH-LCR-InformationIE-ResourceStatusInd NBAP-PROTOCOL-IES ::= {
--	{ ID id-DwPCH-LCR-Information   CRITICALITY ignore	TYPE Common-PhysicalChannel-Status-Information		PRESENCE mandatory }
--}

HS-DSCH-Resources-Information-ResourceStatusInd ::= SEQUENCE {
	resourceOperationalState			ResourceOperationalState,
	availabilityStatus					AvailabilityStatus,
--	iE-Extensions						ProtocolExtensionContainer  {{ HS-DSCH-Resources-Information-ResourceStatusInd-ExtIEs }}		OPTIONAL,
	iE-Extensions						ProtocolExtensionContainer OPTIONAL,
	...
}

--HS-DSCH-Resources-Information-ResourceStatusInd-ExtIEs NBAP-PROTOCOL-EXTENSION ::= {
--	...
--}

--S-CCPCH-InformationListExt-ResourceStatusInd ::= SEQUENCE (SIZE (1..maxSCCPCHCellinExt)) OF ProtocolIE-Single-Container {{ S-CCPCH-InformationItemIE-ResourceStatusInd }}
S-CCPCH-InformationListExt-ResourceStatusInd ::= SEQUENCE (SIZE (1..208)) OF ProtocolIE-Single-Container

--S-CCPCH-LCR-InformationListExt-ResourceStatusInd ::= SEQUENCE (SIZE (1..maxSCCPCHCellinExtLCR)) OF ProtocolIE-Single-Container {{ S-CCPCH-InformationItemIE-ResourceStatusInd }}
S-CCPCH-LCR-InformationListExt-ResourceStatusInd ::= SEQUENCE (SIZE (1..208)) OF ProtocolIE-Single-Container

E-DCH-Resources-Information-ResourceStatusInd ::= SEQUENCE {
	resourceOperationalState			ResourceOperationalState,
	availabilityStatus					AvailabilityStatus,
--	iE-Extensions						ProtocolExtensionContainer  {{ E-DCH-Resources-Information-ResourceStatusInd-ExtIEs }}		OPTIONAL,
	iE-Extensions						ProtocolExtensionContainer OPTIONAL,
	...
}

--E-DCH-Resources-Information-ResourceStatusInd-ExtIEs NBAP-PROTOCOL-EXTENSION ::= {
--	...
--}

-- **************************************************************
--
-- SYSTEM INFORMATION UPDATE REQUEST
--
-- **************************************************************

--SystemInformationUpdateRequest ::= SEQUENCE {
--	protocolIEs				ProtocolIE-Container	{{SystemInformationUpdateRequest-IEs}},
--	protocolExtensions		ProtocolExtensionContainer	{{SystemInformationUpdateRequest-Extensions}}		OPTIONAL,
--	...
--}
SystemInformationUpdateRequest ::= SEQUENCE {
	protocolIEs				ProtocolIE-Container,
	protocolExtensions		ProtocolExtensionContainer	OPTIONAL,
	...
}

--SystemInformationUpdateRequest-IEs NBAP-PROTOCOL-IES ::= {
--	{ ID id-C-ID												CRITICALITY reject	TYPE C-ID					PRESENCE mandatory }|
--	{ ID id-BCCH-ModificationTime								CRITICALITY reject	TYPE BCCH-ModificationTime				PRESENCE optional }|
--	{ ID id-MIB-SB-SIB-InformationList-SystemInfoUpdateRqst		CRITICALITY reject	TYPE MIB-SB-SIB-InformationList-SystemInfoUpdateRqst				PRESENCE mandatory },
--	...
--}

--SystemInformationUpdateRequest-Extensions NBAP-PROTOCOL-EXTENSION ::= {
--	...
--}

--MIB-SB-SIB-InformationList-SystemInfoUpdateRqst ::= SEQUENCE (SIZE (1..maxIB)) OF MIB-SB-SIB-InformationItem-SystemInfoUpdateRqst
MIB-SB-SIB-InformationList-SystemInfoUpdateRqst ::= SEQUENCE (SIZE (1..64)) OF MIB-SB-SIB-InformationItem-SystemInfoUpdateRqst

MIB-SB-SIB-InformationItem-SystemInfoUpdateRqst ::= SEQUENCE {
	iB-Type								IB-Type,	
	iB-OC-ID							IB-OC-ID,
	deletionIndicator					DeletionIndicator-SystemInfoUpdate,
--	iE-Extensions						ProtocolExtensionContainer { { MIB-SB-SIB-InformationItem-SystemInfoUpdateRqst-ExtIEs} }		OPTIONAL,
	iE-Extensions						ProtocolExtensionContainer OPTIONAL,
	...
}

--MIB-SB-SIB-InformationItem-SystemInfoUpdateRqst-ExtIEs NBAP-PROTOCOL-EXTENSION ::= {
--	...
--}

DeletionIndicator-SystemInfoUpdate ::= CHOICE {
	no-Deletion							No-Deletion-SystemInfoUpdate,
	yes-Deletion						NULL

}

No-Deletion-SystemInfoUpdate ::= SEQUENCE {
	sIB-Originator							SIB-Originator				OPTIONAL,
	-- This IE shall be present if the IB-Type IE is set to "SIB"
	iB-SG-REP								IB-SG-REP					OPTIONAL,
	segmentInformationList					SegmentInformationList-SystemInfoUpdate,
--	iE-Extensions							ProtocolExtensionContainer { { No-DeletionItem-SystemInfoUpdate-ExtIEs} }		OPTIONAL,
	iE-Extensions							ProtocolExtensionContainer OPTIONAL,
	...
}

--No-DeletionItem-SystemInfoUpdate-ExtIEs NBAP-PROTOCOL-EXTENSION ::= {
--	...
--}

--SegmentInformationList-SystemInfoUpdate ::= ProtocolIE-Single-Container {{ SegmentInformationListIEs-SystemInfoUpdate }}
SegmentInformationList-SystemInfoUpdate ::= ProtocolIE-Single-Container

--SegmentInformationListIEs-SystemInfoUpdate NBAP-PROTOCOL-IES ::= {
--	{ ID id-SegmentInformationListIE-SystemInfoUpdate   CRITICALITY reject	TYPE SegmentInformationListIE-SystemInfoUpdate		PRESENCE mandatory }
--}

--SegmentInformationListIE-SystemInfoUpdate ::= SEQUENCE (SIZE (1..maxIBSEG)) OF SegmentInformationItem-SystemInfoUpdate
SegmentInformationListIE-SystemInfoUpdate ::= SEQUENCE (SIZE (1..16)) OF SegmentInformationItem-SystemInfoUpdate

SegmentInformationItem-SystemInfoUpdate ::= SEQUENCE {
	iB-SG-POS								IB-SG-POS			OPTIONAL,
	segment-Type							Segment-Type		OPTIONAL,
	-- This IE shall be present if the SIB Originator IE is set to "CRNC" or the IB-Type IE is set to "MIB", "SB1" or "SB2"
	iB-SG-DATA								IB-SG-DATA			OPTIONAL,
	-- This IE shall be present if the SIB Originator IE is set to "CRNC" or the IB-Type IE is set to "MIB", "SB1" or "SB2"
--	iE-Extensions							ProtocolExtensionContainer { { SegmentInformationItem-SystemInfoUpdate-ExtIEs} }	OPTIONAL,
	iE-Extensions							ProtocolExtensionContainer OPTIONAL,
	...
}

--SegmentInformationItem-SystemInfoUpdate-ExtIEs NBAP-PROTOCOL-EXTENSION ::= {
--	...
--}

-- **************************************************************
--
-- SYSTEM INFORMATION UPDATE RESPONSE
--
-- **************************************************************

--SystemInformationUpdateResponse ::= SEQUENCE {
--	protocolIEs				ProtocolIE-Container    {{SystemInformationUpdateResponse-IEs}},
--	protocolExtensions		ProtocolExtensionContainer	{{SystemInformationUpdateResponse-Extensions}}		OPTIONAL,
--	...
--}

SystemInformationUpdateResponse ::= SEQUENCE {
	protocolIEs				ProtocolIE-Container,
	protocolExtensions		ProtocolExtensionContainer	OPTIONAL,
	...
}

--SystemInformationUpdateResponse-IEs NBAP-PROTOCOL-IES ::= {
--	{ ID	id-CriticalityDiagnostics		CRITICALITY		ignore			TYPE	CriticalityDiagnostics		PRESENCE	optional},
--	...
--}

--SystemInformationUpdateResponse-Extensions NBAP-PROTOCOL-EXTENSION ::= {
--	...
--}

-- **************************************************************
--
-- SYSTEM INFORMATION UPDATE FAILURE
--
-- **************************************************************

--SystemInformationUpdateFailure ::= SEQUENCE {
--	protocolIEs				ProtocolIE-Container	{{SystemInformationUpdateFailure-IEs}},
--	protocolExtensions		ProtocolExtensionContainer	{{SystemInformationUpdateFailure-Extensions}}		OPTIONAL,
--	...
--}

SystemInformationUpdateFailure ::= SEQUENCE {
	protocolIEs				ProtocolIE-Container,
	protocolExtensions		ProtocolExtensionContainer	OPTIONAL,
	...
}
--SystemInformationUpdateFailure-IEs NBAP-PROTOCOL-IES ::= {
--	{ ID	id-Cause							CRITICALITY		ignore			TYPE	Cause						PRESENCE	mandatory	}|
--	{ ID 	id-CriticalityDiagnostics			CRITICALITY		ignore			TYPE	CriticalityDiagnostics		PRESENCE	optional	},
--	...
--}

--SystemInformationUpdateFailure-Extensions NBAP-PROTOCOL-EXTENSION ::= {
--	...
--}

-- **************************************************************
--
-- RADIO LINK SETUP REQUEST FDD
--
-- **************************************************************

--RadioLinkSetupRequestFDD ::= SEQUENCE {
--	protocolIEs				ProtocolIE-Container	{{RadioLinkSetupRequestFDD-IEs}},
--	protocolExtensions		ProtocolExtensionContainer	{{RadioLinkSetupRequestFDD-Extensions}}			OPTIONAL,
--	...
--}
RadioLinkSetupRequestFDD ::= SEQUENCE {
	protocolIEs				ProtocolIE-Container,
	protocolExtensions		ProtocolExtensionContainer	OPTIONAL,
	...
}

--RadioLinkSetupRequestFDD-IEs NBAP-PROTOCOL-IES ::= {
--	{ ID id-CRNC-CommunicationContextID						CRITICALITY reject	TYPE CRNC-CommunicationContextID					PRESENCE mandatory }|
--	{ ID id-UL-DPCH-Information-RL-SetupRqstFDD				CRITICALITY reject	TYPE UL-DPCH-Information-RL-SetupRqstFDD			PRESENCE mandatory }|
--	{ ID id-DL-DPCH-Information-RL-SetupRqstFDD				CRITICALITY reject	TYPE DL-DPCH-Information-RL-SetupRqstFDD			PRESENCE optional }|
--	{ ID id-DCH-FDD-Information								CRITICALITY reject	TYPE DCH-FDD-Information					PRESENCE mandatory }|
--	{ ID id-RL-InformationList-RL-SetupRqstFDD				CRITICALITY notify	TYPE RL-InformationList-RL-SetupRqstFDD			PRESENCE mandatory }|
--	{ ID id-Transmission-Gap-Pattern-Sequence-Information		CRITICALITY reject	TYPE Transmission-Gap-Pattern-Sequence-Information								PRESENCE optional } |
--	{ ID id-Active-Pattern-Sequence-Information				CRITICALITY reject	TYPE Active-Pattern-Sequence-Information			PRESENCE optional },
--	...
--}

--RadioLinkSetupRequestFDD-Extensions NBAP-PROTOCOL-EXTENSION ::= {
--	{ ID id-DL-PowerBalancing-Information			CRITICALITY ignore	EXTENSION DL-PowerBalancing-Information		PRESENCE optional }|
--	{ ID id-HSDSCH-FDD-Information					CRITICALITY reject	EXTENSION HSDSCH-FDD-Information		PRESENCE optional }|
--	{ ID id-HSDSCH-RNTI								CRITICALITY reject	EXTENSION HSDSCH-RNTI			PRESENCE conditional }|
	-- The IE shall be present if HS-DSCH Information IE is present
--	{ ID id-HSPDSCH-RL-ID							CRITICALITY reject	EXTENSION RL-ID					PRESENCE conditional }|
	-- The IE shall be present if HS-DSCH Information IE is present
--	{ ID id-E-DPCH-Information-RL-SetupRqstFDD		CRITICALITY reject	EXTENSION E-DPCH-Information-RL-SetupRqstFDD	PRESENCE optional }|
--	{ ID id-E-DCH-FDD-Information					CRITICALITY reject	EXTENSION E-DCH-FDD-Information		PRESENCE conditional }|
	-- The IE shall be present if E-DPCH Information IE is present
--	{ ID id-Serving-E-DCH-RL-ID						CRITICALITY reject	EXTENSION Serving-E-DCH-RL-ID		PRESENCE conditional }|
	-- The IE shall be present if E-DPCH Information IE is present
--	{ ID id-F-DPCH-Information-RL-SetupRqstFDD	CRITICALITY reject	EXTENSION F-DPCH-Information-RL-SetupRqstFDD	PRESENCE optional }|
--	{ ID id-Initial-DL-DPCH-TimingAdjustment-Allowed		CRITICALITY ignore	EXTENSION Initial-DL-DPCH-TimingAdjustment-Allowed						PRESENCE optional },
--	...
--}

UL-DPCH-Information-RL-SetupRqstFDD ::= SEQUENCE {
	ul-ScramblingCode						UL-ScramblingCode,
	minUL-ChannelisationCodeLength			MinUL-ChannelisationCodeLength,
	maxNrOfUL-DPDCHs						MaxNrOfUL-DPDCHs		OPTIONAL,
	-- This IE shall be present if Min UL Channelisation Code length IE is set to 4 --
	ul-PunctureLimit						PunctureLimit,
	tFCS									TFCS,
	ul-DPCCH-SlotFormat						UL-DPCCH-SlotFormat,
	ul-SIR-Target							UL-SIR,
	diversityMode							DiversityMode,
	not-Used-sSDT-CellID-Length				NULL		OPTIONAL,
	not-Used-s-FieldLength					NULL			OPTIONAL,
--	iE-Extensions							ProtocolExtensionContainer { { UL-DPCH-Information-RL-SetupRqstFDD-ExtIEs} }	OPTIONAL,
	iE-Extensions							ProtocolExtensionContainer OPTIONAL,
	...
}

--UL-DPCH-Information-RL-SetupRqstFDD-ExtIEs NBAP-PROTOCOL-EXTENSION ::= {
--	{ ID id-DPC-Mode								CRITICALITY reject	EXTENSION DPC-Mode						PRESENCE optional }|
--	{ ID id-UL-DPDCH-Indicator-For-E-DCH-Operation	CRITICALITY reject	EXTENSION UL-DPDCH-Indicator-For-E-DCH-Operation		PRESENCE conditional },
	-- The IE shall be present if E-DPCH Information IE is present
--	...
--}

DL-DPCH-Information-RL-SetupRqstFDD ::= SEQUENCE {
	tFCS									TFCS,
	dl-DPCH-SlotFormat						DL-DPCH-SlotFormat,
	tFCI-SignallingMode						TFCI-SignallingMode,
	tFCI-Presence							TFCI-Presence					OPTIONAL,
	-- this IE shall be present if the DL DPCH slot format IE is set to any of the values from 12 to 16 --	
	multiplexingPosition					MultiplexingPosition,
	not-Used-pDSCH-RL-ID					NULL							OPTIONAL,
	not-Used-pDSCH-CodeMapping				NULL							OPTIONAL,
	powerOffsetInformation					PowerOffsetInformation-RL-SetupRqstFDD,
	fdd-TPC-DownlinkStepSize				FDD-TPC-DownlinkStepSize,
	limitedPowerIncrease					LimitedPowerIncrease,
	innerLoopDLPCStatus						InnerLoopDLPCStatus,
--	iE-Extensions							ProtocolExtensionContainer { { DL-DPCH-Information-RL-SetupRqstFDD-ExtIEs} }	OPTIONAL,
	iE-Extensions							ProtocolExtensionContainer OPTIONAL,
	...
}

--DL-DPCH-Information-RL-SetupRqstFDD-ExtIEs NBAP-PROTOCOL-EXTENSION ::= {
--	...
--}

PowerOffsetInformation-RL-SetupRqstFDD ::= SEQUENCE {
	pO1-ForTFCI-Bits						PowerOffset,
	pO2-ForTPC-Bits							PowerOffset,
	pO3-ForPilotBits						PowerOffset,
--	iE-Extensions							ProtocolExtensionContainer { { PowerOffsetInformation-RL-SetupRqstFDD-ExtIEs} }	OPTIONAL,
	iE-Extensions							ProtocolExtensionContainer OPTIONAL,
	...
}

--PowerOffsetInformation-RL-SetupRqstFDD-ExtIEs NBAP-PROTOCOL-EXTENSION ::= {
--	...
--}

--RL-InformationList-RL-SetupRqstFDD ::= SEQUENCE (SIZE (1..maxNrOfRLs)) OF
RL-InformationList-RL-SetupRqstFDD ::= SEQUENCE (SIZE (1..16)) OF ProtocolIE-Single-Container

--RL-InformationItemIE-RL-SetupRqstFDD NBAP-PROTOCOL-IES ::= {
--	{ ID	id-RL-InformationItem-RL-SetupRqstFDD			CRITICALITY		notify			TYPE	RL-InformationItem-RL-SetupRqstFDD		PRESENCE	mandatory}
--}

RL-InformationItem-RL-SetupRqstFDD ::= SEQUENCE {
	rL-ID								RL-ID,
	c-ID								C-ID,
	firstRLS-indicator					FirstRLS-Indicator,
	frameOffset							FrameOffset,
	chipOffset							ChipOffset,
	propagationDelay					PropagationDelay			OPTIONAL,
	diversityControlField				DiversityControlField		OPTIONAL,
	-- This IE shall be present if the RL is not the first one in the RL Information IE
	dl-CodeInformation					FDD-DL-CodeInformation,
	initialDL-transmissionPower			DL-Power,
	maximumDL-power						DL-Power,
	minimumDL-power						DL-Power,
	not-Used-sSDT-Cell-Identity			NULL							OPTIONAL,
	transmitDiversityIndicator			TransmitDiversityIndicator		OPTIONAL,
	-- This IE shall be present if Diversity Mode IE in UL DPCH Information group is not set to “none”
--	iE-Extensions						ProtocolExtensionContainer { { RL-InformationItem-RL-SetupRqstFDD-ExtIEs} }		OPTIONAL,
	iE-Extensions						ProtocolExtensionContainer OPTIONAL,
	...
}

--RL-InformationItem-RL-SetupRqstFDD-ExtIEs NBAP-PROTOCOL-EXTENSION ::= {
--	{ ID id-RL-Specific-DCH-Info						CRITICALITY ignore	EXTENSION RL-Specific-DCH-Info	PRESENCE optional }|
--	{ ID id-DelayedActivation							CRITICALITY reject	EXTENSION DelayedActivation	PRESENCE optional }|
--	{ ID id-Primary-CPICH-Usage-for-Channel-Estimation	CRITICALITY ignore	EXTENSION Primary-CPICH-Usage-for-Channel-Estimation	PRESENCE optional }|
--	{ ID id-Secondary-CPICH-Information					CRITICALITY ignore	EXTENSION CommonPhysicalChannelID	PRESENCE optional }|
--	{ ID id-E-DCH-RL-Indication							CRITICALITY reject	EXTENSION E-DCH-RL-Indication	PRESENCE optional }|
--	{ ID id-RL-Specific-E-DCH-Info						CRITICALITY ignore	EXTENSION RL-Specific-E-DCH-Info	PRESENCE optional }|
--	{ ID id-SynchronisationIndicator					CRITICALITY ignore	EXTENSION SynchronisationIndicator	PRESENCE optional },
--	...
--}
E-DPCH-Information-RL-SetupRqstFDD ::= SEQUENCE {
	maxSet-E-DPDCHs								Max-Set-E-DPDCHs,
	ul-PunctureLimit							PunctureLimit,
	e-TFCS-Information							E-TFCS-Information,
	e-TTI										E-TTI,
	e-DPCCH-PO									E-DPCCH-PO,
--	iE-Extensions								ProtocolExtensionContainer { { E-DPCH-Information-RL-SetupRqstFDD-ExtIEs} }		OPTIONAL,
	iE-Extensions								ProtocolExtensionContainer OPTIONAL,
	...
}

--E-DPCH-Information-RL-SetupRqstFDD-ExtIEs NBAP-PROTOCOL-EXTENSION ::= {
--	...
--}

F-DPCH-Information-RL-SetupRqstFDD ::= SEQUENCE {
	powerOffsetInformation				PowerOffsetInformation-F-DPCH-RL-SetupRqstFDD,
	fdd-TPC-DownlinkStepSize			FDD-TPC-DownlinkStepSize,
	limitedPowerIncrease				LimitedPowerIncrease,
	innerLoopDLPCStatus					InnerLoopDLPCStatus,
--	iE-Extensions						ProtocolExtensionContainer { { F-DPCH-Information-RL-SetupRqstFDD-ExtIEs} }					OPTIONAL,
	iE-Extensions						ProtocolExtensionContainer OPTIONAL,
	...
}

--F-DPCH-Information-RL-SetupRqstFDD-ExtIEs NBAP-PROTOCOL-EXTENSION ::= {
--	...
--}

PowerOffsetInformation-F-DPCH-RL-SetupRqstFDD ::= SEQUENCE {
	pO2-ForTPC-Bits						PowerOffset,
--	iE-Extensions						ProtocolExtensionContainer { { PowerOffsetInformation-F-DPCH-RL-SetupRqstFDD-ExtIEs} }	OPTIONAL,
	iE-Extensions						ProtocolExtensionContainer OPTIONAL,
	...
}

--PowerOffsetInformation-F-DPCH-RL-SetupRqstFDD-ExtIEs NBAP-PROTOCOL-EXTENSION ::= {
--	...
--}

-- **************************************************************
--
-- RADIO LINK SETUP REQUEST TDD
--
-- **************************************************************
--RadioLinkSetupRequestTDD ::= SEQUENCE {
--	protocolIEs				ProtocolIE-Container	{{RadioLinkSetupRequestTDD-IEs}},
--	protocolExtensions		ProtocolExtensionContainer	{{RadioLinkSetupRequestTDD-Extensions}}		OPTIONAL,
--	...
--}

RadioLinkSetupRequestTDD ::= SEQUENCE {
	protocolIEs				ProtocolIE-Container,
	protocolExtensions		ProtocolExtensionContainer	OPTIONAL,
	...
}

--RadioLinkSetupRequestTDD-IEs NBAP-PROTOCOL-IES ::= {
--	{ ID	id-CRNC-CommunicationContextID					CRITICALITY reject	TYPE CRNC-CommunicationContextID					PRESENCE mandatory }|
--	{ ID	id-UL-CCTrCH-InformationList-RL-SetupRqstTDD	CRITICALITY notify	TYPE UL-CCTrCH-InformationList-RL-SetupRqstTDD	PRESENCE optional }|
--	{ ID	id-DL-CCTrCH-InformationList-RL-SetupRqstTDD	CRITICALITY notify	TYPE DL-CCTrCH-InformationList-RL-SetupRqstTDD	PRESENCE optional }|
--	{ ID	id-DCH-TDD-Information							CRITICALITY reject	TYPE DCH-TDD-Information					PRESENCE optional }|
--	{ ID	id-DSCH-TDD-Information							CRITICALITY reject	TYPE DSCH-TDD-Information					PRESENCE optional }|
--	{ ID	id-USCH-Information								CRITICALITY reject	TYPE USCH-Information					PRESENCE optional }|
--	{ ID	id-RL-Information-RL-SetupRqstTDD				CRITICALITY reject	TYPE RL-Information-RL-SetupRqstTDD					PRESENCE mandatory },
--	...
--}

--RadioLinkSetupRequestTDD-Extensions NBAP-PROTOCOL-EXTENSION ::= {
--	{ ID id-HSDSCH-TDD-Information			CRITICALITY reject		EXTENSION HSDSCH-TDD-Information	PRESENCE optional	}|
--	{ ID id-HSDSCH-RNTI						CRITICALITY reject		EXTENSION HSDSCH-RNTI			PRESENCE conditional	}|
	-- The IE shall be present if HS-DSCH Information IE is present
--	{ ID id-HSPDSCH-RL-ID					CRITICALITY reject		EXTENSION RL-ID					PRESENCE conditional	}|
	-- The IE shall be present if HS-DSCH Information IE is present
--	{ ID id-PDSCH-RL-ID						CRITICALITY ignore		EXTENSION RL-ID					PRESENCE optional },
--	...
--}

-- UL-CCTrCH-InformationList-RL-SetupRqstTDD ::= SEQUENCE (SIZE(1..maxNrOfCCTrCHs)) OF

-- FIX ME ???
UL-CCTrCH-InformationList-RL-SetupRqstTDD ::= SEQUENCE (SIZE(1..16)) OF ProtocolIE-Single-Container

--UL-CCTrCH-InformationItemIE-RL-SetupRqstTDD NBAP-PROTOCOL-IES ::= {
--	{ ID	id-UL-CCTrCH-InformationItem-RL-SetupRqstTDD		CRITICALITY		notify			TYPE	UL-CCTrCH-InformationItem-RL-SetupRqstTDD		PRESENCE	mandatory}
--}

UL-CCTrCH-InformationItem-RL-SetupRqstTDD ::= SEQUENCE {
	cCTrCH-ID								CCTrCH-ID,
	tFCS									TFCS,
	tFCI-Coding								TFCI-Coding,
	punctureLimit							PunctureLimit,
	uL-DPCH-Information						UL-DPCH-Information-RL-SetupRqstTDD		OPTIONAL, 	-- Applicable to 3.84Mcps TDD only
--	iE-Extensions							ProtocolExtensionContainer { { UL-CCTrCH-InformationItem-RL-SetupRqstTDD-ExtIEs} }		OPTIONAL,
	iE-Extensions							ProtocolExtensionContainer OPTIONAL,
	...
}

--UL-CCTrCH-InformationItem-RL-SetupRqstTDD-ExtIEs NBAP-PROTOCOL-EXTENSION ::= {
--	{ ID id-UL-DPCH-LCR-Information-RL-SetupRqstTDD		CRITICALITY notify	EXTENSION UL-DPCH-LCR-Information-RL-SetupRqstTDD	PRESENCE optional	}|
	-- Applicable to 1.28Mcps TDD only
--	{ ID id-UL-SIRTarget								CRITICALITY reject	EXTENSION UL-SIR						PRESENCE optional	}|
	-- Mandatory for 1.28Mcps TDD, Not Applicable to 3.84Mcps TDD.
--	{ ID id-TDD-TPC-UplinkStepSize-LCR-RL-SetupRqstTDD	CRITICALITY reject	EXTENSION TDD-TPC-UplinkStepSize-LCR					PRESENCE optional	},
	-- Mandatory for 1.28Mcps TDD, Not Applicable to 3.84Mcps TDD.
--	...
--}

UL-DPCH-Information-RL-SetupRqstTDD ::= ProtocolIE-Single-Container

--UL-DPCH-InformationIE-RL-SetupRqstTDD NBAP-PROTOCOL-IES ::= {
--	{ ID id-UL-DPCH-InformationList-RL-SetupRqstTDD		CRITICALITY notify	TYPE UL-DPCH-InformationItem-RL-SetupRqstTDD		PRESENCE mandatory	}
--}

UL-DPCH-InformationItem-RL-SetupRqstTDD ::= SEQUENCE {
	repetitionPeriod						RepetitionPeriod,
	repetitionLength						RepetitionLength,
	tdd-DPCHOffset							TDD-DPCHOffset,
	uL-Timeslot-Information					UL-Timeslot-Information,
--	iE-Extensions							ProtocolExtensionContainer { { UL-DPCH-InformationItem-RL-SetupRqstTDD-ExtIEs} }		OPTIONAL,
	iE-Extensions							ProtocolExtensionContainer OPTIONAL,
	...
}

--UL-DPCH-InformationItem-RL-SetupRqstTDD-ExtIEs NBAP-PROTOCOL-EXTENSION ::= {
--	...
--}

UL-DPCH-LCR-Information-RL-SetupRqstTDD ::= SEQUENCE {
	repetitionPeriod						RepetitionPeriod,
	repetitionLength						RepetitionLength,
	tdd-DPCHOffset							TDD-DPCHOffset,
	uL-TimeslotLCR-Information				UL-TimeslotLCR-Information,
--	iE-Extensions							ProtocolExtensionContainer { { UL-DPCH-LCR-InformationItem-RL-SetupRqstTDD-ExtIEs} }		OPTIONAL,
	iE-Extensions							ProtocolExtensionContainer OPTIONAL,
	...
}

--UL-DPCH-LCR-InformationItem-RL-SetupRqstTDD-ExtIEs NBAP-PROTOCOL-EXTENSION ::= {
--	...
--}

--DL-CCTrCH-InformationList-RL-SetupRqstTDD ::= SEQUENCE (SIZE (1..maxNrOfCCTrCHs)) OF ProtocolIE-Single-Container{{ DL-CCTrCH-InformationItemIE-RL-SetupRqstTDD }}
DL-CCTrCH-InformationList-RL-SetupRqstTDD ::= SEQUENCE (SIZE (1..16)) OF ProtocolIE-Single-Container

--DL-CCTrCH-InformationItemIE-RL-SetupRqstTDD NBAP-PROTOCOL-IES ::= {
--	{ ID	id-DL-CCTrCH-InformationItem-RL-SetupRqstTDD			CRITICALITY		notify			TYPE	DL-CCTrCH-InformationItem-RL-SetupRqstTDD		PRESENCE	mandatory}
--}

DL-CCTrCH-InformationItem-RL-SetupRqstTDD ::= SEQUENCE {
	cCTrCH-ID								CCTrCH-ID,
	tFCS									TFCS,
	tFCI-Coding								TFCI-Coding,
	punctureLimit							PunctureLimit,
	tdd-TPC-DownlinkStepSize				TDD-TPC-DownlinkStepSize,
	cCTrCH-TPCList							CCTrCH-TPCList-RL-SetupRqstTDD			OPTIONAL,
	dL-DPCH-Information						DL-DPCH-Information-RL-SetupRqstTDD		OPTIONAL, 	-- Applicable to 3.84Mcps TDD only
--	iE-Extensions							ProtocolExtensionContainer { { DL-CCTrCH-InformationItem-RL-SetupRqstTDD-ExtIEs} }		OPTIONAL,
	iE-Extensions							ProtocolExtensionContainer OPTIONAL,
	...
}

--DL-CCTrCH-InformationItem-RL-SetupRqstTDD-ExtIEs NBAP-PROTOCOL-EXTENSION ::= {
--	{ ID id-DL-DPCH-LCR-Information-RL-SetupRqstTDD	CRITICALITY notify		EXTENSION 	DL-DPCH-LCR-Information-RL-SetupRqstTDD		PRESENCE optional	}|
	-- Applicable to 1.28Mcps TDD only
--	{ ID id-CCTrCH-Initial-DL-Power-RL-SetupRqstTDD		CRITICALITY ignore		EXTENSION DL-Power		PRESENCE optional	}|
--	{ ID id-CCTrCH-Maximum-DL-Power-RL-SetupRqstTDD		CRITICALITY ignore		EXTENSION DL-Power		PRESENCE optional	}|
--	{ ID id-CCTrCH-Minimum-DL-Power-RL-SetupRqstTDD		CRITICALITY ignore		EXTENSION DL-Power		PRESENCE optional	},
--	...
--}

--CCTrCH-TPCList-RL-SetupRqstTDD ::= SEQUENCE (SIZE (1..maxNrOfCCTrCHs)) OF CCTrCH-TPCItem-RL-SetupRqstTDD
CCTrCH-TPCList-RL-SetupRqstTDD ::= SEQUENCE (SIZE (1..16)) OF CCTrCH-TPCItem-RL-SetupRqstTDD

CCTrCH-TPCItem-RL-SetupRqstTDD	 ::= SEQUENCE {
	cCTrCH-ID								CCTrCH-ID,
--	iE-Extensions							ProtocolExtensionContainer { { CCTrCH-TPCItem-RL-SetupRqstTDD-ExtIEs} }		OPTIONAL,
	iE-Extensions							ProtocolExtensionContainer OPTIONAL,
	...
}

--CCTrCH-TPCItem-RL-SetupRqstTDD-ExtIEs NBAP-PROTOCOL-EXTENSION ::= {
--	...
--}

--DL-DPCH-Information-RL-SetupRqstTDD ::= ProtocolIE-Single-Container{{ DL-DPCH-InformationIE-RL-SetupRqstTDD }}
DL-DPCH-Information-RL-SetupRqstTDD ::= ProtocolIE-Single-Container

--DL-DPCH-InformationIE-RL-SetupRqstTDD NBAP-PROTOCOL-IES ::= {
--	{ ID id-DL-DPCH-InformationList-RL-SetupRqstTDD		CRITICALITY notify	TYPE DL-DPCH-InformationItem-RL-SetupRqstTDD		PRESENCE mandatory	}
--}

DL-DPCH-InformationItem-RL-SetupRqstTDD	 ::= SEQUENCE {
	repetitionPeriod						RepetitionPeriod,
	repetitionLength						RepetitionLength,
	tdd-DPCHOffset							TDD-DPCHOffset,
	dL-Timeslot-Information					DL-Timeslot-Information,
--	iE-Extensions							ProtocolExtensionContainer { { DL-DPCH-InformationItem-RL-SetupRqstTDD-ExtIEs} }		OPTIONAL,
	iE-Extensions							ProtocolExtensionContainer OPTIONAL,
	...
}

--DL-DPCH-InformationItem-RL-SetupRqstTDD-ExtIEs NBAP-PROTOCOL-EXTENSION ::= {
--	...
--}

DL-DPCH-LCR-Information-RL-SetupRqstTDD ::= SEQUENCE {
	repetitionPeriod						RepetitionPeriod,
	repetitionLength						RepetitionLength,
	tdd-DPCHOffset							TDD-DPCHOffset,
	dL-TimeslotLCR-Information				DL-TimeslotLCR-Information,
	tstdIndicator							TSTD-Indicator,
--	iE-Extensions							ProtocolExtensionContainer { { DL-DPCH-LCR-InformationItem-RL-SetupRqstTDD-ExtIEs} }		OPTIONAL,
	iE-Extensions							ProtocolExtensionContainer OPTIONAL,
	...
}

--DL-DPCH-LCR-InformationItem-RL-SetupRqstTDD-ExtIEs NBAP-PROTOCOL-EXTENSION ::= {
--	...
--}

RL-Information-RL-SetupRqstTDD ::= SEQUENCE {
	rL-ID									RL-ID,
	c-ID									C-ID,
	frameOffset								FrameOffset,
	specialBurstScheduling					SpecialBurstScheduling,
	initialDL-transmissionPower				DL-Power,
	maximumDL-power							DL-Power,
	minimumDL-power							DL-Power,
	dL-TimeSlotISCPInfo						DL-TimeslotISCPInfo	OPTIONAL, 	-- Applicable to 3.84Mcps TDD only
--	iE-Extensions							ProtocolExtensionContainer { { RL-Information-RL-SetupRqstTDD-ExtIEs} }		OPTIONAL,
	iE-Extensions							ProtocolExtensionContainer OPTIONAL,
	...
}

--RL-Information-RL-SetupRqstTDD-ExtIEs NBAP-PROTOCOL-EXTENSION ::= {
--	{ ID id-TimeslotISCP-LCR-InfoList-RL-SetupRqstTDD	CRITICALITY reject	EXTENSION DL-TimeslotISCPInfoLCR			PRESENCE optional }|
	-- Applicable to 1.28Mcps TDD only
--	{ ID id-RL-Specific-DCH-Info						CRITICALITY ignore	EXTENSION RL-Specific-DCH-Info			PRESENCE optional }|
--	{ ID id-DelayedActivation CRITICALITY reject EXTENSION DelayedActivation PRESENCE optional }|
--	{ ID id-UL-Synchronisation-Parameters-LCR			CRITICALITY reject	EXTENSION UL-Synchronisation-Parameters-LCR	PRESENCE optional },
	-- Mandatory for 1.28Mcps TDD, Not Applicable to 3.84Mcps TDD
--	...
--}

-- **************************************************************
--
-- RADIO LINK SETUP RESPONSE FDD
--
-- **************************************************************

--RadioLinkSetupResponseFDD ::= SEQUENCE {
--	protocolIEs				ProtocolIE-Container	{{RadioLinkSetupResponseFDD-IEs}},
--	protocolExtensions		ProtocolExtensionContainer	{{RadioLinkSetupResponseFDD-Extensions}}		OPTIONAL,
--	...
--}
RadioLinkSetupResponseFDD ::= SEQUENCE {
	protocolIEs				ProtocolIE-Container,
	protocolExtensions		ProtocolExtensionContainer	OPTIONAL,
	...
}

--RadioLinkSetupResponseFDD-IEs NBAP-PROTOCOL-IES ::= {
--	{ ID id-CRNC-CommunicationContextID					CRITICALITY ignore	TYPE CRNC-CommunicationContextID					PRESENCE mandatory }|
--	{ ID id-NodeB-CommunicationContextID				CRITICALITY ignore	TYPE NodeB-CommunicationContextID					PRESENCE mandatory }|
--	{ ID id-CommunicationControlPortID					CRITICALITY ignore	TYPE CommunicationControlPortID					PRESENCE mandatory }|
--	{ ID id-RL-InformationResponseList-RL-SetupRspFDD	CRITICALITY ignore	TYPE RL-InformationResponseList-RL-SetupRspFDD		PRESENCE mandatory }|
--	{ ID id-CriticalityDiagnostics						CRITICALITY ignore	TYPE CriticalityDiagnostics					PRESENCE optional },
--	...
--}

--RadioLinkSetupResponseFDD-Extensions NBAP-PROTOCOL-EXTENSION ::= {
--	{ ID id-HSDSCH-FDD-Information-Response				CRITICALITY ignore	EXTENSION HSDSCH-FDD-Information-Response				PRESENCE optional },
--	...
--}

--RL-InformationResponseList-RL-SetupRspFDD ::= SEQUENCE (SIZE (1..maxNrOfRLs)) OF ProtocolIE-Single-Container{{ RL-InformationResponseItemIE-RL-SetupRspFDD }}
RL-InformationResponseList-RL-SetupRspFDD ::= SEQUENCE (SIZE (1..16)) OF ProtocolIE-Single-Container
	
--RL-InformationResponseItemIE-RL-SetupRspFDD NBAP-PROTOCOL-IES ::= {
--	{ ID	id-RL-InformationResponseItem-RL-SetupRspFDD			CRITICALITY		ignore		TYPE	RL-InformationResponseItem-RL-SetupRspFDD		PRESENCE	mandatory}
--}

RL-InformationResponseItem-RL-SetupRspFDD ::= SEQUENCE {
	rL-ID											RL-ID,
	rL-Set-ID										RL-Set-ID,
	received-total-wide-band-power					Received-total-wide-band-power-Value,
	diversityIndication								DiversityIndication-RL-SetupRspFDD,
	not-Used-dSCH-InformationResponseList			NULL							OPTIONAL,
	sSDT-SupportIndicator							SSDT-SupportIndicator,
--	iE-Extensions									ProtocolExtensionContainer { { RL-InformationResponseItem-RL-SetupRspFDD-ExtIEs} }		OPTIONAL,
	iE-Extensions									ProtocolExtensionContainer OPTIONAL,
	...
}

--RL-InformationResponseItem-RL-SetupRspFDD-ExtIEs NBAP-PROTOCOL-EXTENSION ::= {
--	{ ID id-DL-PowerBalancing-ActivationIndicator		CRITICALITY ignore	EXTENSION DL-PowerBalancing-ActivationIndicator			PRESENCE optional }|
--	{ ID id-E-DCH-RL-Set-ID								CRITICALITY ignore	EXTENSION RL-Set-ID							PRESENCE optional }|
--	{ ID id-E-DCH-FDD-DL-Control-Channel-Information	CRITICALITY ignore	EXTENSION E-DCH-FDD-DL-Control-Channel-Information		PRESENCE optional }|
--	{ ID id-Initial-DL-DPCH-TimingAdjustment			CRITICALITY ignore	EXTENSION DL-DPCH-TimingAdjustment						PRESENCE optional },
--	...
--}

DiversityIndication-RL-SetupRspFDD ::= CHOICE {
	combining									Combining-RL-SetupRspFDD,
	nonCombiningOrFirstRL						NonCombiningOrFirstRL-RL-SetupRspFDD
}

Combining-RL-SetupRspFDD ::= SEQUENCE {
	rL-ID										RL-ID,
--	iE-Extensions								ProtocolExtensionContainer { { Combining-RL-SetupRspFDD-ExtIEs} }		OPTIONAL,
	iE-Extensions								ProtocolExtensionContainer OPTIONAL,
	...
}

--Combining-RL-SetupRspFDD-ExtIEs NBAP-PROTOCOL-EXTENSION ::= {
--	...
--}

NonCombiningOrFirstRL-RL-SetupRspFDD ::= SEQUENCE {
	dCH-InformationResponse						DCH-InformationResponse,
--	iE-Extensions									ProtocolExtensionContainer { { NonCombiningOrFirstRLItem-RL-SetupRspFDD-ExtIEs} }		OPTIONAL,
	iE-Extensions									ProtocolExtensionContainer OPTIONAL,
	...
}

--NonCombiningOrFirstRLItem-RL-SetupRspFDD-ExtIEs NBAP-PROTOCOL-EXTENSION ::= {
--	{ ID id-E-DCH-FDD-Information-Response		CRITICALITY ignore	EXTENSION E-DCH-FDD-Information-Response		PRESENCE optional },
--	...
--}

-- **************************************************************
--
-- RADIO LINK SETUP RESPONSE TDD
--
-- **************************************************************

--RadioLinkSetupResponseTDD ::= SEQUENCE {
--	protocolIEs				ProtocolIE-Container	{{RadioLinkSetupResponseTDD-IEs}},
--	protocolExtensions		ProtocolExtensionContainer	{{RadioLinkSetupResponseTDD-Extensions}}		OPTIONAL,
--	...
--}
RadioLinkSetupResponseTDD ::= SEQUENCE {
	protocolIEs				ProtocolIE-Container,
	protocolExtensions		ProtocolExtensionContainer	OPTIONAL,
	...
}

--RadioLinkSetupResponseTDD-IEs NBAP-PROTOCOL-IES ::= {
--	{ ID id-CRNC-CommunicationContextID				CRITICALITY ignore	TYPE CRNC-CommunicationContextID				PRESENCE mandatory }|
--	{ ID id-NodeB-CommunicationContextID			CRITICALITY ignore	TYPE NodeB-CommunicationContextID				PRESENCE mandatory }|
--	{ ID id-CommunicationControlPortID				CRITICALITY ignore	TYPE CommunicationControlPortID				PRESENCE mandatory }|
--	{ ID id-RL-InformationResponse-RL-SetupRspTDD	CRITICALITY ignore	TYPE RL-InformationResponse-RL-SetupRspTDD				PRESENCE optional }|
	-- Mandatory for 3.84Mcps TDD, Not Applicable to 1.28Mcps TDD
--	{ ID id-CriticalityDiagnostics					CRITICALITY ignore	TYPE CriticalityDiagnostics				PRESENCE optional },
--	...
--}

--RadioLinkSetupResponseTDD-Extensions NBAP-PROTOCOL-EXTENSION ::= {
--	{ ID id-RL-InformationResponse-LCR-RL-SetupRspTDD	CRITICALITY ignore	EXTENSION RL-InformationResponse-LCR-RL-SetupRspTDD		PRESENCE 	optional	}|
	-- Mandatory for 1.28Mcps TDD, Not Applicable to 3.84Mcps TDD
--	{ ID id-HSDSCH-TDD-Information-Response			CRITICALITY ignore		EXTENSION HSDSCH-TDD-Information-Response		PRESENCE optional	},
--	...
--}

RL-InformationResponse-RL-SetupRspTDD ::= SEQUENCE {
	rL-ID											RL-ID,
	uL-TimeSlot-ISCP-Info							UL-TimeSlot-ISCP-Info,
	ul-PhysCH-SF-Variation							UL-PhysCH-SF-Variation,
	dCH-InformationResponseList						DCH-InformationResponseList-RL-SetupRspTDD			OPTIONAL,
	dSCH-InformationResponseList					DSCH-InformationResponseList-RL-SetupRspTDD			OPTIONAL,
	uSCH-InformationResponseList					USCH-InformationResponseList-RL-SetupRspTDD			OPTIONAL,
--	iE-Extensions									ProtocolExtensionContainer { { RL-InformationResponseList-RL-SetupRspTDD-ExtIEs} }		OPTIONAL,
	iE-Extensions									ProtocolExtensionContainer OPTIONAL,
	...
}

--RL-InformationResponseList-RL-SetupRspTDD-ExtIEs NBAP-PROTOCOL-EXTENSION ::= {
--	...
--}

--DCH-InformationResponseList-RL-SetupRspTDD ::= ProtocolIE-Single-Container{{ DCH-InformationResponseListIEs-RL-SetupRspTDD }}
DCH-InformationResponseList-RL-SetupRspTDD ::= ProtocolIE-Single-Container

--DCH-InformationResponseListIEs-RL-SetupRspTDD NBAP-PROTOCOL-IES ::= {
--	{ ID id-DCH-InformationResponse	CRITICALITY 	ignore		TYPE 	DCH-InformationResponse  PRESENCE	mandatory}
--}

--DSCH-InformationResponseList-RL-SetupRspTDD ::= ProtocolIE-Single-Container {{ DSCH-InformationResponseListIEs-RL-SetupRspTDD }}
DSCH-InformationResponseList-RL-SetupRspTDD ::= ProtocolIE-Single-Container


--DSCH-InformationResponseListIEs-RL-SetupRspTDD NBAP-PROTOCOL-IES ::= {
--	{ ID id-DSCH-InformationResponse   CRITICALITY ignore	TYPE DSCH-InformationResponse		PRESENCE mandatory }
--}

--USCH-InformationResponseList-RL-SetupRspTDD ::= ProtocolIE-Single-Container {{ USCH-InformationResponseListIEs-RL-SetupRspTDD }}
USCH-InformationResponseList-RL-SetupRspTDD ::= ProtocolIE-Single-Container


--USCH-InformationResponseListIEs-RL-SetupRspTDD NBAP-PROTOCOL-IES ::= {
--	{ ID id-USCH-InformationResponse   CRITICALITY ignore	TYPE USCH-InformationResponse		PRESENCE mandatory }
--}

RL-InformationResponse-LCR-RL-SetupRspTDD ::= SEQUENCE {
	rL-ID											RL-ID,
	uL-TimeSlot-ISCP-LCR-Info						UL-TimeSlot-ISCP-LCR-Info,
	ul-PhysCH-SF-Variation							UL-PhysCH-SF-Variation,
	dCH-InformationResponseList						DCH-InformationResponseList-RL-SetupRspTDD			OPTIONAL,
	dSCH-InformationResponseList					DSCH-InformationResponseList-RL-SetupRspTDD			OPTIONAL,
	uSCH-InformationResponseList					USCH-InformationResponseList-RL-SetupRspTDD			OPTIONAL,
--	iE-Extensions									ProtocolExtensionContainer { { RL-InformationResponseList-LCR-RL-SetupRspTDD-ExtIEs} }		OPTIONAL,
	iE-Extensions									ProtocolExtensionContainer OPTIONAL,
	...
}

--RL-InformationResponseList-LCR-RL-SetupRspTDD-ExtIEs NBAP-PROTOCOL-EXTENSION ::= {
--	...
--}

-- **************************************************************
--
-- RADIO LINK SETUP FAILURE FDD
--
-- **************************************************************

--RadioLinkSetupFailureFDD ::= SEQUENCE {
--	protocolIEs				ProtocolIE-Container	{{RadioLinkSetupFailureFDD-IEs}},
--	protocolExtensions		ProtocolExtensionContainer	{{RadioLinkSetupFailureFDD-Extensions}}		OPTIONAL,
--	...
--}

RadioLinkSetupFailureFDD ::= SEQUENCE {
	protocolIEs				ProtocolIE-Container,
	protocolExtensions		ProtocolExtensionContainer	OPTIONAL,
	...
}

--RadioLinkSetupFailureFDD-IEs NBAP-PROTOCOL-IES ::= {
--	{ ID id-CRNC-CommunicationContextID			CRITICALITY ignore	TYPE CRNC-CommunicationContextID		PRESENCE mandatory }|
--	{ ID id-NodeB-CommunicationContextID		CRITICALITY ignore	TYPE NodeB-CommunicationContextID		PRESENCE conditional }|
	-- This IE shall be present if at least one of the radio links has been successfully set up
--	{ ID id-CommunicationControlPortID			CRITICALITY ignore	TYPE CommunicationControlPortID		PRESENCE optional }|
--	{ ID id-CauseLevel-RL-SetupFailureFDD		CRITICALITY ignore	TYPE CauseLevel-RL-SetupFailureFDD		PRESENCE mandatory }|
--	{ ID id-CriticalityDiagnostics				CRITICALITY ignore	TYPE CriticalityDiagnostics			PRESENCE optional },
--	...
--}

--RadioLinkSetupFailureFDD-Extensions NBAP-PROTOCOL-EXTENSION ::= {
--	...
--}

CauseLevel-RL-SetupFailureFDD ::= CHOICE {
	generalCause		GeneralCauseList-RL-SetupFailureFDD,
	rLSpecificCause		RLSpecificCauseList-RL-SetupFailureFDD,
	...
}

GeneralCauseList-RL-SetupFailureFDD ::= SEQUENCE {
	cause										Cause,
--	iE-Extensions								ProtocolExtensionContainer { { GeneralCauseItem-RL-SetupFailureFDD-ExtIEs} }		OPTIONAL,
	iE-Extensions								ProtocolExtensionContainer OPTIONAL,
	...
}

--GeneralCauseItem-RL-SetupFailureFDD-ExtIEs NBAP-PROTOCOL-EXTENSION ::= {
--	...
--}

RLSpecificCauseList-RL-SetupFailureFDD ::= SEQUENCE {
	unsuccessful-RL-InformationRespList-RL-SetupFailureFDD		Unsuccessful-RL-InformationRespList-RL-SetupFailureFDD,
	successful-RL-InformationRespList-RL-SetupFailureFDD		Successful-RL-InformationRespList-RL-SetupFailureFDD	OPTIONAL,
--	iE-Extensions								ProtocolExtensionContainer { { RLSpecificCauseItem-RL-SetupFailureFDD-ExtIEs} }		OPTIONAL,
	iE-Extensions								ProtocolExtensionContainer OPTIONAL,
	...
}

--RLSpecificCauseItem-RL-SetupFailureFDD-ExtIEs NBAP-PROTOCOL-EXTENSION ::= {
--	{ ID id-HSDSCH-FDD-Information-Response		CRITICALITY ignore		EXTENSION HSDSCH-FDD-Information-Response			PRESENCE optional },
--	...
--}

--Unsuccessful-RL-InformationRespList-RL-SetupFailureFDD ::= SEQUENCE (SIZE (1..maxNrOfRLs))	OF ProtocolIE-Single-Container {{ Unsuccessful-RL-InformationRespItemIE-RL-SetupFailureFDD }}
Unsuccessful-RL-InformationRespList-RL-SetupFailureFDD ::= SEQUENCE (SIZE (1..16))	OF ProtocolIE-Single-Container


--Unsuccessful-RL-InformationRespItemIE-RL-SetupFailureFDD NBAP-PROTOCOL-IES ::= {
--	{ ID	id-Unsuccessful-RL-InformationRespItem-RL-SetupFailureFDD		CRITICALITY		ignore		TYPE	Unsuccessful-RL-InformationRespItem-RL-SetupFailureFDD		PRESENCE	mandatory}
--}

Unsuccessful-RL-InformationRespItem-RL-SetupFailureFDD ::= SEQUENCE {
	rL-ID										RL-ID,
	cause										Cause,
--	iE-Extensions								ProtocolExtensionContainer { { Unsuccessful-RL-InformationRespItem-RL-SetupFailureFDD-ExtIEs} }		OPTIONAL,
	iE-Extensions								ProtocolExtensionContainer OPTIONAL,
	...
}

--Unsuccessful-RL-InformationRespItem-RL-SetupFailureFDD-ExtIEs NBAP-PROTOCOL-EXTENSION ::= {
--	...
--}

--Successful-RL-InformationRespList-RL-SetupFailureFDD ::= SEQUENCE (SIZE (1.. maxNrOfRLs)) OF ProtocolIE-Single-Container	{{ Successful-RL-InformationRespItemIE-RL-SetupFailureFDD }}
Successful-RL-InformationRespList-RL-SetupFailureFDD ::= SEQUENCE (SIZE (1.. 16)) OF ProtocolIE-Single-Container	


--Successful-RL-InformationRespItemIE-RL-SetupFailureFDD NBAP-PROTOCOL-IES ::= {
--	{ ID	id-Successful-RL-InformationRespItem-RL-SetupFailureFDD			CRITICALITY		ignore 		TYPE	Successful-RL-InformationRespItem-RL-SetupFailureFDD		PRESENCE	mandatory}
--}

Successful-RL-InformationRespItem-RL-SetupFailureFDD ::= SEQUENCE {
	rL-ID										RL-ID,
	rL-Set-ID									RL-Set-ID,
	received-total-wide-band-power				Received-total-wide-band-power-Value,
	diversityIndication							DiversityIndication-RL-SetupFailureFDD,
	not-Used-dSCH-InformationResponseList		NULL						OPTIONAL,
	not-Used-tFCI2-BearerInformationResponse	NULL						OPTIONAL,
	sSDT-SupportIndicator						SSDT-SupportIndicator,
--	iE-Extensions								ProtocolExtensionContainer { { Successful-RL-InformationRespItem-RL-SetupFailureFDD-ExtIEs} }		OPTIONAL,
	iE-Extensions								ProtocolExtensionContainer OPTIONAL,
	...
}

--Successful-RL-InformationRespItem-RL-SetupFailureFDD-ExtIEs NBAP-PROTOCOL-EXTENSION ::= {
--	{ ID id-DL-PowerBalancing-ActivationIndicator		CRITICALITY ignore	EXTENSION DL-PowerBalancing-ActivationIndicator			PRESENCE optional }|
--	{ ID id-E-DCH-RL-Set-ID								CRITICALITY ignore	EXTENSION RL-Set-ID							PRESENCE optional }|
--	{ ID id-E-DCH-FDD-DL-Control-Channel-Information	CRITICALITY ignore	EXTENSION E-DCH-FDD-DL-Control-Channel-Information		PRESENCE optional }|
--	{ ID id-Initial-DL-DPCH-TimingAdjustment			CRITICALITY ignore	EXTENSION DL-DPCH-TimingAdjustment						PRESENCE optional },
--	...
--}

DiversityIndication-RL-SetupFailureFDD ::= CHOICE {
 	combining									Combining-RL-SetupFailureFDD,
 	nonCombiningOrFirstRL						NonCombiningOrFirstRL-RL-SetupFailureFDD
}

Combining-RL-SetupFailureFDD ::= SEQUENCE {
 	rL-ID										RL-ID,
--	iE-Extensions								ProtocolExtensionContainer { { CombiningItem-RL-SetupFailureFDD-ExtIEs} }		OPTIONAL,
	iE-Extensions								ProtocolExtensionContainer OPTIONAL,
	...
 }

--CombiningItem-RL-SetupFailureFDD-ExtIEs NBAP-PROTOCOL-EXTENSION ::= {
--	...
--}

NonCombiningOrFirstRL-RL-SetupFailureFDD ::= SEQUENCE {
 	dCH-InformationResponse						DCH-InformationResponse,
--	iE-Extensions									ProtocolExtensionContainer { { NonCombiningOrFirstRLItem-RL-SetupFailureFDD-ExtIEs} }		OPTIONAL,
	iE-Extensions									ProtocolExtensionContainer OPTIONAL,
	...
}

--NonCombiningOrFirstRLItem-RL-SetupFailureFDD-ExtIEs NBAP-PROTOCOL-EXTENSION ::= {
--	{ ID id-E-DCH-FDD-Information-Response		CRITICALITY ignore	EXTENSION E-DCH-FDD-Information-Response		PRESENCE optional },
--	...
--}

-- **************************************************************
--
-- RADIO LINK SETUP FAILURE TDD
--
-- **************************************************************

--RadioLinkSetupFailureTDD ::= SEQUENCE {
--	protocolIEs				ProtocolIE-Container	{{RadioLinkSetupFailureTDD-IEs}},
--	protocolExtensions		ProtocolExtensionContainer	{{RadioLinkSetupFailureTDD-Extensions}}			OPTIONAL,
--	...
--}
RadioLinkSetupFailureTDD ::= SEQUENCE {
	protocolIEs				ProtocolIE-Container,
	protocolExtensions		ProtocolExtensionContainer	OPTIONAL,
	...
}
--RadioLinkSetupFailureTDD-IEs NBAP-PROTOCOL-IES ::= {
--	{ ID	id-CRNC-CommunicationContextID			CRITICALITY ignore	TYPE CRNC-CommunicationContextID		PRESENCE mandatory	}|
--	{ ID	id-CauseLevel-RL-SetupFailureTDD		CRITICALITY ignore	TYPE CauseLevel-RL-SetupFailureTDD		PRESENCE mandatory	}|
--	{ ID	id-CriticalityDiagnostics				CRITICALITY ignore	TYPE CriticalityDiagnostics		PRESENCE optional	},
--	...
--}

--RadioLinkSetupFailureTDD-Extensions NBAP-PROTOCOL-EXTENSION ::= {
--	...
--}

CauseLevel-RL-SetupFailureTDD ::= CHOICE {
	generalCause		GeneralCauseList-RL-SetupFailureTDD,
	rLSpecificCause		RLSpecificCauseList-RL-SetupFailureTDD,
	...
}

GeneralCauseList-RL-SetupFailureTDD ::= SEQUENCE {
	cause						Cause,
--	iE-Extensions				ProtocolExtensionContainer { { GeneralCauseItem-RL-SetupFailureTDD-ExtIEs} }		OPTIONAL,
	iE-Extensions				ProtocolExtensionContainer OPTIONAL,
	...
}

--GeneralCauseItem-RL-SetupFailureTDD-ExtIEs NBAP-PROTOCOL-EXTENSION ::= {
--	...
--}

RLSpecificCauseList-RL-SetupFailureTDD ::= SEQUENCE {
	unsuccessful-RL-InformationRespItem-RL-SetupFailureTDD	Unsuccessful-RL-InformationRespItem-RL-SetupFailureTDD,
--	iE-Extensions											ProtocolExtensionContainer { { RLSpecificCauseItem-RL-SetupFailureTDD-ExtIEs} }		OPTIONAL,
	iE-Extensions											ProtocolExtensionContainer OPTIONAL,
	...
}

--RLSpecificCauseItem-RL-SetupFailureTDD-ExtIEs NBAP-PROTOCOL-EXTENSION ::= {
--	...
--}

--Unsuccessful-RL-InformationRespItem-RL-SetupFailureTDD ::= ProtocolIE-Single-Container { {Unsuccessful-RL-InformationRespItemIE-RL-SetupFailureTDD} }
Unsuccessful-RL-InformationRespItem-RL-SetupFailureTDD ::= ProtocolIE-Single-Container 

--Unsuccessful-RL-InformationRespItemIE-RL-SetupFailureTDD NBAP-PROTOCOL-IES ::= {
--	{ ID	id-Unsuccessful-RL-InformationResp-RL-SetupFailureTDD		CRITICALITY	ignore 		TYPE 	Unsuccessful-RL-InformationResp-RL-SetupFailureTDD		PRESENCE	mandatory	}
--}

Unsuccessful-RL-InformationResp-RL-SetupFailureTDD ::= SEQUENCE {
	rL-ID										RL-ID,
	cause										Cause,
--	iE-Extensions								ProtocolExtensionContainer { { Unsuccessful-RL-InformationResp-RL-SetupFailureTDD-ExtIEs} }		OPTIONAL,
	iE-Extensions								ProtocolExtensionContainer OPTIONAL,
	...
}

--Unsuccessful-RL-InformationResp-RL-SetupFailureTDD-ExtIEs NBAP-PROTOCOL-EXTENSION ::= {
--	...
--}

-- **************************************************************
--
-- RADIO LINK ADDITION REQUEST FDD
--
-- **************************************************************
--RadioLinkAdditionRequestFDD ::= SEQUENCE {
--	protocolIEs				ProtocolIE-Container	{{RadioLinkAdditionRequestFDD-IEs}},
--	protocolExtensions		ProtocolExtensionContainer	{{RadioLinkAdditionRequestFDD-Extensions}}			OPTIONAL,
--	...
--}

RadioLinkAdditionRequestFDD ::= SEQUENCE {
	protocolIEs				ProtocolIE-Container,
	protocolExtensions		ProtocolExtensionContainer	OPTIONAL,
	...
}

--RadioLinkAdditionRequestFDD-IEs NBAP-PROTOCOL-IES ::= {
--	{ ID id-NodeB-CommunicationContextID			CRITICALITY reject	TYPE NodeB-CommunicationContextID		PRESENCE	mandatory	} |
--	{ ID id-Compressed-Mode-Deactivation-Flag		CRITICALITY reject	TYPE Compressed-Mode-Deactivation-Flag		PRESENCE optional }|
--	{ ID id-RL-InformationList-RL-AdditionRqstFDD	CRITICALITY notify	TYPE RL-InformationList-RL-AdditionRqstFDD		PRESENCE	mandatory	},
--	...
--}

--RadioLinkAdditionRequestFDD-Extensions NBAP-PROTOCOL-EXTENSION ::= {
--	{ ID id-Initial-DL-DPCH-TimingAdjustment-Allowed		CRITICALITY ignore	EXTENSION Initial-DL-DPCH-TimingAdjustment-Allowed						PRESENCE optional },
--	...
--}

--RL-InformationList-RL-AdditionRqstFDD	::= SEQUENCE (SIZE (1..maxNrOfRLs-1)) OF ProtocolIE-Single-Container {{ RL-InformationItemIE-RL-AdditionRqstFDD}}
RL-InformationList-RL-AdditionRqstFDD	::= SEQUENCE (SIZE (1..15)) OF ProtocolIE-Single-Container

--RL-InformationItemIE-RL-AdditionRqstFDD NBAP-PROTOCOL-IES ::= {
--	{ ID id-RL-InformationItem-RL-AdditionRqstFDD	CRITICALITY notify	TYPE RL-InformationItem-RL-AdditionRqstFDD			PRESENCE	mandatory}
--}

RL-InformationItem-RL-AdditionRqstFDD ::= SEQUENCE {
	rL-ID										RL-ID,
	c-ID										C-ID,
	frameOffset									FrameOffset,
	chipOffset									ChipOffset,
	diversityControlField						DiversityControlField,
	dl-CodeInformation							FDD-DL-CodeInformation,
	initialDL-TransmissionPower					DL-Power						OPTIONAL,
 	maximumDL-Power								DL-Power						OPTIONAL,
 	minimumDL-Power								DL-Power						OPTIONAL,
 	not-Used-sSDT-CellIdentity					NULL							OPTIONAL,
	transmitDiversityIndicator					TransmitDiversityIndicator		OPTIONAL,
--	iE-Extensions								ProtocolExtensionContainer { { RL-InformationItem-RL-AdditionRqstFDD-ExtIEs} }		OPTIONAL,
	iE-Extensions								ProtocolExtensionContainer OPTIONAL,
	...
}

--RL-InformationItem-RL-AdditionRqstFDD-ExtIEs NBAP-PROTOCOL-EXTENSION ::= {
--	{ ID id-DLReferencePower							CRITICALITY ignore	EXTENSION DL-Power							PRESENCE optional }|
--	{ ID id-RL-Specific-DCH-Info						CRITICALITY ignore	EXTENSION RL-Specific-DCH-Info						PRESENCE optional }|
--	{ ID id-DelayedActivation							CRITICALITY reject	EXTENSION DelayedActivation						PRESENCE optional }|
--	{ ID id-E-DCH-RL-Indication							CRITICALITY reject	EXTENSION E-DCH-RL-Indication						PRESENCE optional }|
--	{ ID id-RL-Specific-E-DCH-Info						CRITICALITY ignore	EXTENSION RL-Specific-E-DCH-Info						PRESENCE optional }|
--	{ ID id-SynchronisationIndicator					CRITICALITY ignore	EXTENSION SynchronisationIndicator						PRESENCE optional },
--	...
--}

-- **************************************************************
--
-- RADIO LINK ADDITION REQUEST TDD
--
-- **************************************************************

--RadioLinkAdditionRequestTDD ::= SEQUENCE {
--	protocolIEs				ProtocolIE-Container	{{RadioLinkAdditionRequestTDD-IEs}},
--	protocolExtensions		ProtocolExtensionContainer	{{RadioLinkAdditionRequestTDD-Extensions}}		OPTIONAL,
--	...
--}
RadioLinkAdditionRequestTDD ::= SEQUENCE {
	protocolIEs				ProtocolIE-Container,
	protocolExtensions		ProtocolExtensionContainer	OPTIONAL,
	...
}

--RadioLinkAdditionRequestTDD-IEs NBAP-PROTOCOL-IES ::= {
--	{ ID id-NodeB-CommunicationContextID					CRITICALITY reject	TYPE NodeB-CommunicationContextID						PRESENCE mandatory }|
--	{ ID id-UL-CCTrCH-InformationList-RL-AdditionRqstTDD	CRITICALITY reject	TYPE UL-CCTrCH-InformationList-RL-AdditionRqstTDD	PRESENCE optional }|
--	{ ID id-DL-CCTrCH-InformationList-RL-AdditionRqstTDD	CRITICALITY reject	TYPE DL-CCTrCH-InformationList-RL-AdditionRqstTDD	PRESENCE optional }|
--	{ ID id-RL-Information-RL-AdditionRqstTDD				CRITICALITY reject	TYPE RL-Information-RL-AdditionRqstTDD					PRESENCE mandatory },
--	...
--}

--RadioLinkAdditionRequestTDD-Extensions NBAP-PROTOCOL-EXTENSION ::= {
--	...
--}

--UL-CCTrCH-InformationList-RL-AdditionRqstTDD ::= SEQUENCE (SIZE (1..maxNrOfCCTrCHs)) OF UL-CCTrCH-InformationItem-RL-AdditionRqstTDD
UL-CCTrCH-InformationList-RL-AdditionRqstTDD ::= SEQUENCE (SIZE (1..16)) OF UL-CCTrCH-InformationItem-RL-AdditionRqstTDD

UL-CCTrCH-InformationItem-RL-AdditionRqstTDD ::= SEQUENCE {
	cCTrCH-ID									CCTrCH-ID,
	uL-DPCH-Information							UL-DPCH-InformationList-RL-AdditionRqstTDD		OPTIONAL, -- Applicable to 3.84cps TDD only
--	iE-Extensions								ProtocolExtensionContainer { { UL-CCTrCH-InformationItem-RL-AdditionRqstTDD-ExtIEs} }		OPTIONAL,
	iE-Extensions								ProtocolExtensionContainer OPTIONAL,
	...
}

--UL-CCTrCH-InformationItem-RL-AdditionRqstTDD-ExtIEs NBAP-PROTOCOL-EXTENSION ::= {
--	{ ID	id-UL-DPCH-InformationItem-LCR-RL-AdditionRqstTDD	CRITICALITY notify	EXTENSION	UL-DPCH-InformationItem-LCR-RL-AdditionRqstTDD			PRESENCE	optional }|
	-- Applicable to 1.28cps TDD only
--	{ ID 	id-TDD-TPC-UplinkStepSize-LCR-RL-AdditionRqstTDD	CRITICALITY reject	EXTENSION	TDD-TPC-UplinkStepSize-LCR	PRESENCE optional	}, 
	-- Applicable to 1.28cps TDD only
--	...
--}

--UL-DPCH-InformationList-RL-AdditionRqstTDD ::= ProtocolIE-Single-Container {{ UL-DPCH-InformationItemIE-RL-AdditionRqstTDD }}
UL-DPCH-InformationList-RL-AdditionRqstTDD ::= ProtocolIE-Single-Container

--UL-DPCH-InformationItemIE-RL-AdditionRqstTDD NBAP-PROTOCOL-IES ::= {
--	{ ID	id-UL-DPCH-InformationItem-RL-AdditionRqstTDD			CRITICALITY		notify			TYPE	UL-DPCH-InformationItem-RL-AdditionRqstTDD			PRESENCE	optional}
	-- For 3.84Mcps TDD only
--}

UL-DPCH-InformationItem-RL-AdditionRqstTDD ::= SEQUENCE {	
	repetitionPeriod						RepetitionPeriod,
	repetitionLength						RepetitionLength,
	tdd-DPCHOffset							TDD-DPCHOffset,
	uL-Timeslot-Information					UL-Timeslot-Information,
--	iE-Extensions							ProtocolExtensionContainer { { UL-DPCH-InformationItem-RL-AdditionRqstTDD-ExtIEs} }		OPTIONAL,
	iE-Extensions							ProtocolExtensionContainer OPTIONAL,
	...
}

--UL-DPCH-InformationItem-RL-AdditionRqstTDD-ExtIEs  NBAP-PROTOCOL-EXTENSION ::= {
--	...
--}

--DL-CCTrCH-InformationList-RL-AdditionRqstTDD ::= SEQUENCE (SIZE (1..maxNrOfCCTrCHs)) OF DL-CCTrCH-InformationItem-RL-AdditionRqstTDD
DL-CCTrCH-InformationList-RL-AdditionRqstTDD ::= SEQUENCE (SIZE (1..16)) OF DL-CCTrCH-InformationItem-RL-AdditionRqstTDD

DL-CCTrCH-InformationItem-RL-AdditionRqstTDD ::= SEQUENCE {
	cCTrCH-ID						CCTrCH-ID,
	dL-DPCH-Information				DL-DPCH-InformationList-RL-AdditionRqstTDD		OPTIONAL, 	-- Applicable to 3.84Mcps TDD only
--	iE-Extensions					ProtocolExtensionContainer { { DL-CCTrCH-InformationItem-RL-AdditionRqstTDD-ExtIEs} }		OPTIONAL,
	iE-Extensions					ProtocolExtensionContainer OPTIONAL,
	...
}

--DL-CCTrCH-InformationItem-RL-AdditionRqstTDD-ExtIEs  NBAP-PROTOCOL-EXTENSION ::= {
--	{ ID	id-DL-DPCH-InformationItem-LCR-RL-AdditionRqstTDD	CRITICALITY notify		EXTENSION DL-DPCH-InformationItem-LCR-RL-AdditionRqstTDD			PRESENCE	optional }|
	-- Applicable to 1.28Mcps TDD only
--	{ ID id-CCTrCH-Initial-DL-Power-RL-AdditionRqstTDD			CRITICALITY ignore		EXTENSION DL-Power				PRESENCE optional	}|
--	{ ID id-TDD-TPC-DownlinkStepSize-RL-AdditionRqstTDD			CRITICALITY reject		EXTENSION TDD-TPC-DownlinkStepSize	PRESENCE optional	}|
--	{ ID id-CCTrCH-Maximum-DL-Power-RL-AdditionRqstTDD			CRITICALITY ignore		EXTENSION DL-Power				PRESENCE optional	}|
--	{ ID id-CCTrCH-Minimum-DL-Power-RL-AdditionRqstTDD			CRITICALITY ignore		EXTENSION DL-Power				PRESENCE optional	},
--	...
--}

--DL-DPCH-InformationList-RL-AdditionRqstTDD ::= ProtocolIE-Single-Container {{ DL-DPCH-InformationItemIE-RL-AdditionRqstTDD }}
DL-DPCH-InformationList-RL-AdditionRqstTDD ::= ProtocolIE-Single-Container

--DL-DPCH-InformationItemIE-RL-AdditionRqstTDD NBAP-PROTOCOL-IES ::= {
--	{ ID	id-DL-DPCH-InformationItem-RL-AdditionRqstTDD		CRITICALITY		notify		TYPE	DL-DPCH-InformationItem-RL-AdditionRqstTDD		PRESENCE mandatory}
--}

DL-DPCH-InformationItem-RL-AdditionRqstTDD ::= SEQUENCE {
	repetitionPeriod						RepetitionPeriod,
	repetitionLength						RepetitionLength,
	tdd-DPCHOffset							TDD-DPCHOffset,
	dL-Timeslot-Information				DL-Timeslot-Information,
--	iE-Extensions								ProtocolExtensionContainer { { DL-DPCH-InformationItem-RL-AdditionRqstTDD-ExtIEs} }			OPTIONAL,
	iE-Extensions								ProtocolExtensionContainer OPTIONAL,
	...
}

--DL-DPCH-InformationItem-RL-AdditionRqstTDD-ExtIEs  NBAP-PROTOCOL-EXTENSION ::= {
--	...
--}

RL-Information-RL-AdditionRqstTDD ::= SEQUENCE {
 	rL-ID										RL-ID,
 	c-ID										C-ID,
 	frameOffset									FrameOffset,
 	diversityControlField						DiversityControlField,
	initial-DL-Transmission-Power				DL-Power			OPTIONAL,
 	maximumDL-Power								DL-Power			OPTIONAL,
 	minimumDL-Power								DL-Power			OPTIONAL,
	dL-TimeSlotISCPInfo							DL-TimeslotISCPInfo	OPTIONAL, 	-- Applicable to 3.84Mcps TDD only
--	iE-Extensions								ProtocolExtensionContainer { { RL-information-RL-AdditionRqstTDD-ExtIEs} }			OPTIONAL,
	iE-Extensions								ProtocolExtensionContainer OPTIONAL,
	...
 }

--RL-information-RL-AdditionRqstTDD-ExtIEs  NBAP-PROTOCOL-EXTENSION ::= {
--	{ ID id-TimeslotISCP-InformationList-LCR-RL-AdditionRqstTDD			CRITICALITY		reject			EXTENSION	DL-TimeslotISCPInfoLCR			PRESENCE	optional }|
	-- Applicable to 1.28Mcps TDD only
--	{ ID id-RL-Specific-DCH-Info		CRITICALITY	ignore		EXTENSION 	RL-Specific-DCH-Info	PRESENCE 	optional	}|
--	{ ID id-DelayedActivation CRITICALITY reject EXTENSION DelayedActivation PRESENCE optional }|
--	{ ID id-UL-Synchronisation-Parameters-LCR			CRITICALITY	reject		EXTENSION 	UL-Synchronisation-Parameters-LCR		PRESENCE 	optional	},
	-- Mandatory for 1.28Mcps TDD, Not Applicable to 3.84Mcps TDD
--	...
--}

UL-DPCH-InformationItem-LCR-RL-AdditionRqstTDD ::= SEQUENCE {
	repetitionPeriod						RepetitionPeriod,
	repetitionLength						RepetitionLength,
	tdd-DPCHOffset							TDD-DPCHOffset,
	uL-TimeslotLCR-Information				UL-TimeslotLCR-Information,
--	iE-Extensions							ProtocolExtensionContainer { { UL-DPCH-InformationItem-LCR-RL-AdditionRqstTDD-ExtIEs} }		OPTIONAL,
	iE-Extensions							ProtocolExtensionContainer OPTIONAL,
	...
}

--UL-DPCH-InformationItem-LCR-RL-AdditionRqstTDD-ExtIEs NBAP-PROTOCOL-EXTENSION ::= {
--	...
--}

DL-DPCH-InformationItem-LCR-RL-AdditionRqstTDD ::= SEQUENCE {
	repetitionPeriod						RepetitionPeriod,
	repetitionLength						RepetitionLength,
	tdd-DPCHOffset							TDD-DPCHOffset,
	dL-TimeslotLCR-Information				DL-TimeslotLCR-Information,
--	iE-Extensions							ProtocolExtensionContainer { { DL-DPCH-InformationItem-LCR-RL-AdditionRqstTDD-ExtIEs} }		OPTIONAL,
	iE-Extensions							ProtocolExtensionContainer OPTIONAL,
	...
}

--DL-DPCH-InformationItem-LCR-RL-AdditionRqstTDD-ExtIEs NBAP-PROTOCOL-EXTENSION ::= {
--	...
--}

-- **************************************************************
--
-- RADIO LINK ADDITION RESPONSE FDD
--
-- **************************************************************

--RadioLinkAdditionResponseFDD ::= SEQUENCE {
--	protocolIEs				ProtocolIE-Container	{{RadioLinkAdditionResponseFDD-IEs}},
--	protocolExtensions		ProtocolExtensionContainer	{{RadioLinkAdditionResponseFDD-Extensions}}			OPTIONAL,
--	...
--}
RadioLinkAdditionResponseFDD ::= SEQUENCE {
	protocolIEs				ProtocolIE-Container,
	protocolExtensions		ProtocolExtensionContainer OPTIONAL,
	...
}
--RadioLinkAdditionResponseFDD-IEs NBAP-PROTOCOL-IES ::= {
--	{ ID id-CRNC-CommunicationContextID						CRITICALITY ignore	TYPE CRNC-CommunicationContextID						PRESENCE mandatory }|
--	{ ID id-RL-InformationResponseList-RL-AdditionRspFDD	CRITICALITY ignore	TYPE RL-InformationResponseList-RL-AdditionRspFDD	PRESENCE mandatory }|
--	{ ID id-CriticalityDiagnostics							CRITICALITY ignore	TYPE CriticalityDiagnostics						PRESENCE optional },
--	...
--}

--RadioLinkAdditionResponseFDD-Extensions NBAP-PROTOCOL-EXTENSION ::= {
--	...
--}

--RL-InformationResponseList-RL-AdditionRspFDD ::= SEQUENCE (SIZE (1..maxNrOfRLs-1)) OF ProtocolIE-Single-Container {{ RL-InformationResponseItemIE-RL-AdditionRspFDD }}
RL-InformationResponseList-RL-AdditionRspFDD ::= SEQUENCE (SIZE (1..15)) OF ProtocolIE-Single-Container

--RL-InformationResponseItemIE-RL-AdditionRspFDD NBAP-PROTOCOL-IES ::= {
--	{ ID id-RL-InformationResponseItem-RL-AdditionRspFDD	CRITICALITY ignore	TYPE RL-InformationResponseItem-RL-AdditionRspFDD	PRESENCE mandatory }
--}

RL-InformationResponseItem-RL-AdditionRspFDD ::= SEQUENCE {
	rL-ID								RL-ID,
	rL-Set-ID							RL-Set-ID,
	received-total-wide-band-power		Received-total-wide-band-power-Value,
	diversityIndication					DiversityIndication-RL-AdditionRspFDD,
	sSDT-SupportIndicator				SSDT-SupportIndicator,
--	iE-Extensions						ProtocolExtensionContainer { { RL-InformationResponseItem-RL-AdditionRspFDD-ExtIEs} }		OPTIONAL,
	iE-Extensions						ProtocolExtensionContainer OPTIONAL,
	...
}

--RL-InformationResponseItem-RL-AdditionRspFDD-ExtIEs  NBAP-PROTOCOL-EXTENSION ::= {
--	{ ID id-DL-PowerBalancing-ActivationIndicator		CRITICALITY ignore	EXTENSION DL-PowerBalancing-ActivationIndicator			PRESENCE optional }|
--	{ ID id-E-DCH-RL-Set-ID								CRITICALITY ignore	EXTENSION RL-Set-ID							PRESENCE optional }|
--	{ ID id-E-DCH-FDD-DL-Control-Channel-Information	CRITICALITY ignore	EXTENSION E-DCH-FDD-DL-Control-Channel-Information		PRESENCE optional }|
--	{ ID id-Initial-DL-DPCH-TimingAdjustment			CRITICALITY ignore	EXTENSION DL-DPCH-TimingAdjustment						PRESENCE optional },
--	...
--}

DiversityIndication-RL-AdditionRspFDD ::= CHOICE {
	combining										Combining-RL-AdditionRspFDD,
	non-combining									Non-Combining-RL-AdditionRspFDD
}

Combining-RL-AdditionRspFDD ::= SEQUENCE {
 	rL-ID											RL-ID,
--	iE-Extensions									ProtocolExtensionContainer { { CombiningItem-RL-AdditionRspFDD-ExtIEs} }		OPTIONAL,
	iE-Extensions									ProtocolExtensionContainer OPTIONAL,
	...
}

--CombiningItem-RL-AdditionRspFDD-ExtIEs  NBAP-PROTOCOL-EXTENSION ::= {
--	...
--}

Non-Combining-RL-AdditionRspFDD ::= SEQUENCE {
	dCH-InformationResponse						DCH-InformationResponse,
--	iE-Extensions									ProtocolExtensionContainer { { Non-CombiningItem-RL-AdditionRspFDD-ExtIEs} }		OPTIONAL,
	iE-Extensions									ProtocolExtensionContainer OPTIONAL,
	...
}

--Non-CombiningItem-RL-AdditionRspFDD-ExtIEs  NBAP-PROTOCOL-EXTENSION ::= {
--	{ ID id-E-DCH-FDD-Information-Response				CRITICALITY ignore	EXTENSION E-DCH-FDD-Information-Response				PRESENCE optional },
--	...
--}

-- **************************************************************
--
-- RADIO LINK ADDITION RESPONSE TDD
--
-- **************************************************************

--RadioLinkAdditionResponseTDD ::= SEQUENCE {
--	protocolIEs				ProtocolIE-Container	{{RadioLinkAdditionResponseTDD-IEs}},
--	protocolExtensions		ProtocolExtensionContainer	{{RadioLinkAdditionResponseTDD-Extensions}}		OPTIONAL,
--	...
--}
RadioLinkAdditionResponseTDD ::= SEQUENCE {
	protocolIEs				ProtocolIE-Container,
	protocolExtensions		ProtocolExtensionContainer	OPTIONAL,
	...
}
--RadioLinkAdditionResponseTDD-IEs NBAP-PROTOCOL-IES ::= {
--	{ ID	id-CRNC-CommunicationContextID					CRITICALITY	ignore	TYPE	CRNC-CommunicationContextID						PRESENCE 	mandatory	}|
--	{ ID	id-RL-InformationResponse-RL-AdditionRspTDD		CRITICALITY	ignore	TYPE	RL-InformationResponse-RL-AdditionRspTDD	PRESENCE 	optional	}|
		-- Mandatory for 3.84Mcps TDD, Not Applicable to 1.28Mcps TDD
--	{ ID	id-CriticalityDiagnostics						CRITICALITY	ignore	TYPE	CriticalityDiagnostics						PRESENCE	optional	},
--	...
--}

--RadioLinkAdditionResponseTDD-Extensions NBAP-PROTOCOL-EXTENSION ::= {
--	{ ID id-RL-InformationResponse-LCR-RL-AdditionRspTDD		CRITICALITY ignore			EXTENSION	RL-InformationResponse-LCR-RL-AdditionRspTDD 	PRESENCE optional },
	-- Mandatory for 1.28Mcps TDD, Not Applicable to 3.84Mcps TDD
--	...
--}

RL-InformationResponse-RL-AdditionRspTDD ::= SEQUENCE {
	rL-ID										RL-ID,
	uL-TimeSlot-ISCP-Info						UL-TimeSlot-ISCP-Info,
	ul-PhysCH-SF-Variation						UL-PhysCH-SF-Variation,
	dCH-Information								DCH-Information-RL-AdditionRspTDD				OPTIONAL,
	dSCH-InformationResponseList				DSCH-InformationResponseList-RL-AdditionRspTDD		OPTIONAL,
	uSCH-InformationResponseList				USCH-InformationResponseList-RL-AdditionRspTDD		OPTIONAL,
--	iE-Extensions								ProtocolExtensionContainer { { RL-InformationResponse-RL-AdditionRspTDD-ExtIEs} }		OPTIONAL,
	iE-Extensions								ProtocolExtensionContainer OPTIONAL,
	...
}

--RL-InformationResponse-RL-AdditionRspTDD-ExtIEs  NBAP-PROTOCOL-EXTENSION ::= {
--	...
--}

DCH-Information-RL-AdditionRspTDD ::= SEQUENCE {
	diversityIndication					DiversityIndication-RL-AdditionRspTDD,
--	iE-Extensions					ProtocolExtensionContainer { { DCH-Information-RL-AdditionRspTDD-ExtIEs} } OPTIONAL,
	iE-Extensions					ProtocolExtensionContainer OPTIONAL,
	...
}

--DCH-Information-RL-AdditionRspTDD-ExtIEs NBAP-PROTOCOL-EXTENSION ::= {
--	...
--}

DiversityIndication-RL-AdditionRspTDD ::= CHOICE {
	combining									Combining-RL-AdditionRspTDD,	-- Indicates whether the old Transport Bearer shall be reused or not
	non-Combining								Non-Combining-RL-AdditionRspTDD
}

Combining-RL-AdditionRspTDD ::= SEQUENCE {
	rL-ID										RL-ID,	-- Reference RL
--	iE-Extensions								ProtocolExtensionContainer { { CombiningItem-RL-AdditionRspTDD-ExtIEs} }		OPTIONAL,
	iE-Extensions								ProtocolExtensionContainer OPTIONAL,
	...
}

--CombiningItem-RL-AdditionRspTDD-ExtIEs  NBAP-PROTOCOL-EXTENSION ::= {
--	...
--}

Non-Combining-RL-AdditionRspTDD ::= SEQUENCE {
	dCH-InformationResponse					DCH-InformationResponse,
--	iE-Extensions								ProtocolExtensionContainer { { Non-CombiningItem-RL-AdditionRspTDD-ExtIEs} }			OPTIONAL,
	iE-Extensions								ProtocolExtensionContainer OPTIONAL,
	...
}

--Non-CombiningItem-RL-AdditionRspTDD-ExtIEs  NBAP-PROTOCOL-EXTENSION ::= {
--	...
--}

--DSCH-InformationResponseList-RL-AdditionRspTDD ::= ProtocolIE-Single-Container {{ DSCH-InformationResponseListIEs-RL-AdditionRspTDD }}
DSCH-InformationResponseList-RL-AdditionRspTDD ::= ProtocolIE-Single-Container

--DSCH-InformationResponseListIEs-RL-AdditionRspTDD NBAP-PROTOCOL-IES ::= {
--	{ ID id-DSCH-InformationResponse   CRITICALITY ignore	TYPE DSCH-InformationResponse		PRESENCE mandatory }
--}

--USCH-InformationResponseList-RL-AdditionRspTDD ::= ProtocolIE-Single-Container {{ USCH-InformationResponseListIEs-RL-AdditionRspTDD }}
USCH-InformationResponseList-RL-AdditionRspTDD ::= ProtocolIE-Single-Container 

--USCH-InformationResponseListIEs-RL-AdditionRspTDD NBAP-PROTOCOL-IES ::= {
--	{ ID id-USCH-InformationResponse   CRITICALITY ignore	TYPE USCH-InformationResponse		PRESENCE mandatory }
--}

RL-InformationResponse-LCR-RL-AdditionRspTDD ::= SEQUENCE {
	rL-ID										RL-ID,
	uL-TimeSlot-ISCP-InfoLCR					UL-TimeSlot-ISCP-LCR-Info,
	ul-PhysCH-SF-Variation						UL-PhysCH-SF-Variation,
	dCH-Information								DCH-Information-RL-AdditionRspTDD				OPTIONAL,
	dSCH-InformationResponseList				DSCH-InformationResponseList-RL-AdditionRspTDD		OPTIONAL,
	uSCH-InformationResponseList				USCH-InformationResponseList-RL-AdditionRspTDD		OPTIONAL,
--	iE-Extensions								ProtocolExtensionContainer { { RL-InformationResponse-LCR-RL-AdditionRspTDD-ExtIEs} }		OPTIONAL,
	iE-Extensions								ProtocolExtensionContainer OPTIONAL,
	...
}

--RL-InformationResponse-LCR-RL-AdditionRspTDD-ExtIEs  NBAP-PROTOCOL-EXTENSION ::= {
--	...
--}

-- **************************************************************
--
-- RADIO LINK ADDITION FAILURE FDD
--
-- **************************************************************

--RadioLinkAdditionFailureFDD ::= SEQUENCE {
--	protocolIEs				ProtocolIE-Container	{{RadioLinkAdditionFailureFDD-IEs}},
--	protocolExtensions		ProtocolExtensionContainer	{{RadioLinkAdditionFailureFDD-Extensions}}		OPTIONAL,
--	...
--}
RadioLinkAdditionFailureFDD ::= SEQUENCE {
	protocolIEs				ProtocolIE-Container,
	protocolExtensions		ProtocolExtensionContainer	OPTIONAL,
	...
}
--RadioLinkAdditionFailureFDD-IEs NBAP-PROTOCOL-IES ::= {
--	{ ID id-CRNC-CommunicationContextID				CRITICALITY ignore		TYPE CRNC-CommunicationContextID					PRESENCE mandatory }|
--	{ ID id-CauseLevel-RL-AdditionFailureFDD		CRITICALITY ignore		TYPE CauseLevel-RL-AdditionFailureFDD					PRESENCE mandatory }|
--	{ ID id-CriticalityDiagnostics					CRITICALITY ignore		TYPE CriticalityDiagnostics					PRESENCE optional },
--	...
--}

--RadioLinkAdditionFailureFDD-Extensions NBAP-PROTOCOL-EXTENSION ::= {
--	...
--}

CauseLevel-RL-AdditionFailureFDD ::= CHOICE {
	generalCause		GeneralCauseList-RL-AdditionFailureFDD,
	rLSpecificCause		RLSpecificCauseList-RL-AdditionFailureFDD,
	...
}

GeneralCauseList-RL-AdditionFailureFDD ::= SEQUENCE {
	cause										Cause,
--	iE-Extensions								ProtocolExtensionContainer { { GeneralCauseItem-RL-AdditionFailureFDD-ExtIEs} }			OPTIONAL,
	iE-Extensions								ProtocolExtensionContainer OPTIONAL,
	...
}

--GeneralCauseItem-RL-AdditionFailureFDD-ExtIEs  NBAP-PROTOCOL-EXTENSION ::= {
--	...
--}

RLSpecificCauseList-RL-AdditionFailureFDD ::= SEQUENCE {
	unsuccessful-RL-InformationRespList-RL-AdditionFailureFDD		Unsuccessful-RL-InformationRespList-RL-AdditionFailureFDD,
	successful-RL-InformationRespList-RL-AdditionFailureFDD			Successful-RL-InformationRespList-RL-AdditionFailureFDD					OPTIONAL,
--	iE-Extensions								ProtocolExtensionContainer { { RLSpecificCauseItem-RL-AdditionFailureFDD-ExtIEs} }			OPTIONAL,
	iE-Extensions								ProtocolExtensionContainer OPTIONAL,
	...
}

--RLSpecificCauseItem-RL-AdditionFailureFDD-ExtIEs  NBAP-PROTOCOL-EXTENSION ::= {
--	...
--}

--Unsuccessful-RL-InformationRespList-RL-AdditionFailureFDD ::= SEQUENCE	(SIZE (1..maxNrOfRLs-1)) OF ProtocolIE-Single-Container {{ Unsuccessful-RL-InformationRespItemIE-RL-AdditionFailureFDD }}
Unsuccessful-RL-InformationRespList-RL-AdditionFailureFDD ::= SEQUENCE	(SIZE (1..15)) OF ProtocolIE-Single-Container

--Unsuccessful-RL-InformationRespItemIE-RL-AdditionFailureFDD NBAP-PROTOCOL-IES ::= {
--	{ ID	id-Unsuccessful-RL-InformationRespItem-RL-AdditionFailureFDD		CRITICALITY		ignore		TYPE	Unsuccessful-RL-InformationRespItem-RL-AdditionFailureFDD	PRESENCE	mandatory}
--}

Unsuccessful-RL-InformationRespItem-RL-AdditionFailureFDD ::= SEQUENCE {
	rL-ID										RL-ID,
	cause										Cause,
--	iE-Extensions								ProtocolExtensionContainer { { Unsuccessful-RL-InformationRespItem-RL-AdditionFailureFDD-ExtIEs} }			OPTIONAL,
	iE-Extensions								ProtocolExtensionContainer OPTIONAL,
	...
}

--Unsuccessful-RL-InformationRespItem-RL-AdditionFailureFDD-ExtIEs  NBAP-PROTOCOL-EXTENSION ::= {
--	...
--}

--Successful-RL-InformationRespList-RL-AdditionFailureFDD ::= SEQUENCE (SIZE (1..maxNrOfRLs-2)) OF ProtocolIE-Single-Container {{ Successful-RL-InformationRespItemIE-RL-AdditionFailureFDD }}
Successful-RL-InformationRespList-RL-AdditionFailureFDD ::= SEQUENCE (SIZE (1..14)) OF ProtocolIE-Single-Container

--Successful-RL-InformationRespItemIE-RL-AdditionFailureFDD NBAP-PROTOCOL-IES ::= {
--	{ ID	id-Successful-RL-InformationRespItem-RL-AdditionFailureFDD		CRITICALITY		ignore		TYPE	Successful-RL-InformationRespItem-RL-AdditionFailureFDD		PRESENCE	mandatory}
--}

Successful-RL-InformationRespItem-RL-AdditionFailureFDD ::= SEQUENCE {
	rL-ID										RL-ID,
	rL-Set-ID									RL-Set-ID,
	received-total-wide-band-power				Received-total-wide-band-power-Value,
	diversityIndication							DiversityIndication-RL-AdditionFailureFDD,
	sSDT-SupportIndicator						SSDT-SupportIndicator,
--	iE-Extensions								ProtocolExtensionContainer { { Successful-RL-InformationRespItem-RL-AdditionFailureFDD-ExtIEs} }		OPTIONAL,
	iE-Extensions								ProtocolExtensionContainer
	OPTIONAL,
	...
}

--Successful-RL-InformationRespItem-RL-AdditionFailureFDD-ExtIEs  NBAP-PROTOCOL-EXTENSION ::= {
--	{ ID id-DL-PowerBalancing-ActivationIndicator		CRITICALITY ignore	EXTENSION DL-PowerBalancing-ActivationIndicator			PRESENCE optional }|
--	{ ID id-E-DCH-RL-Set-ID								CRITICALITY ignore	EXTENSION RL-Set-ID							PRESENCE optional }|
--	{ ID id-E-DCH-FDD-DL-Control-Channel-Information	CRITICALITY ignore	EXTENSION E-DCH-FDD-DL-Control-Channel-Information		PRESENCE optional }|
--	{ ID id-Initial-DL-DPCH-TimingAdjustment			CRITICALITY ignore	EXTENSION DL-DPCH-TimingAdjustment						PRESENCE optional },
--	...
--}

DiversityIndication-RL-AdditionFailureFDD ::= CHOICE {
 	combining						Combining-RL-AdditionFailureFDD,
 	non-Combining					Non-Combining-RL-AdditionFailureFDD
}

Combining-RL-AdditionFailureFDD ::= SEQUENCE {
 	rL-ID										RL-ID,
--	iE-Extensions								ProtocolExtensionContainer { { CombiningItem-RL-AdditionFailureFDD-ExtIEs} }			OPTIONAL,
	iE-Extensions								ProtocolExtensionContainer OPTIONAL,
	...
 }

--CombiningItem-RL-AdditionFailureFDD-ExtIEs NBAP-PROTOCOL-EXTENSION ::= {
--	{ ID id-E-DCH-FDD-Information-Response				CRITICALITY ignore	EXTENSION E-DCH-FDD-Information-Response				PRESENCE optional },
--	...
--}

Non-Combining-RL-AdditionFailureFDD ::= SEQUENCE {
 	dCH-InformationResponse						DCH-InformationResponse,
--	iE-Extensions								ProtocolExtensionContainer { { Non-CombiningItem-RL-AdditionFailureFDD-ExtIEs} }			OPTIONAL,
	iE-Extensions								ProtocolExtensionContainer OPTIONAL,
	...
}

--Non-CombiningItem-RL-AdditionFailureFDD-ExtIEs NBAP-PROTOCOL-EXTENSION ::= {
--	...
--}

-- **************************************************************
--
-- RADIO LINK ADDITION FAILURE TDD
--
-- **************************************************************
--RadioLinkAdditionFailureTDD ::= SEQUENCE {
--	protocolIEs				ProtocolIE-Container	{{RadioLinkAdditionFailureTDD-IEs}},
--	protocolExtensions		ProtocolExtensionContainer	{{RadioLinkAdditionFailureTDD-Extensions}}		OPTIONAL,
--	...
--}
RadioLinkAdditionFailureTDD ::= SEQUENCE {
	protocolIEs				ProtocolIE-Container,
	protocolExtensions		ProtocolExtensionContainer OPTIONAL,
	...
}
--RadioLinkAdditionFailureTDD-IEs NBAP-PROTOCOL-IES ::= {
--	{ ID	id-CRNC-CommunicationContextID				CRITICALITY ignore		TYPE CRNC-CommunicationContextID			PRESENCE mandatory }|
--	{ ID    id-CauseLevel-RL-AdditionFailureTDD			CRITICALITY ignore		TYPE CauseLevel-RL-AdditionFailureTDD		PRESENCE mandatory }|
--	{ ID	id-CriticalityDiagnostics					CRITICALITY ignore		TYPE CriticalityDiagnostics			PRESENCE optional },
--	...
--}

--RadioLinkAdditionFailureTDD-Extensions NBAP-PROTOCOL-EXTENSION ::= {
--	...
--}

CauseLevel-RL-AdditionFailureTDD ::= CHOICE {
	generalCause		GeneralCauseList-RL-AdditionFailureTDD,
	rLSpecificCause		RLSpecificCauseList-RL-AdditionFailureTDD,
	...
}

GeneralCauseList-RL-AdditionFailureTDD ::= SEQUENCE {
	cause						Cause,
--	iE-Extensions				ProtocolExtensionContainer { { GeneralCauseItem-RL-AdditionFailureTDD-ExtIEs} }		OPTIONAL,
	iE-Extensions				ProtocolExtensionContainer OPTIONAL,
	...
}

--GeneralCauseItem-RL-AdditionFailureTDD-ExtIEs NBAP-PROTOCOL-EXTENSION ::= {
--	...
--}

RLSpecificCauseList-RL-AdditionFailureTDD ::= SEQUENCE {
	unsuccessful-RL-InformationRespItem-RL-AdditionFailureTDD	Unsuccessful-RL-InformationRespItem-RL-AdditionFailureTDD,
--	iE-Extensions												ProtocolExtensionContainer { { RLSpecificCauseItem-RL-AdditionFailureTDD-ExtIEs} }		OPTIONAL,
	iE-Extensions												ProtocolExtensionContainer OPTIONAL,
	...
}

--RLSpecificCauseItem-RL-AdditionFailureTDD-ExtIEs NBAP-PROTOCOL-EXTENSION ::= {
--	...
--}

--Unsuccessful-RL-InformationRespItem-RL-AdditionFailureTDD ::= ProtocolIE-Single-Container { {Unsuccessful-RL-InformationRespItemIE-RL-AdditionFailureTDD} }
Unsuccessful-RL-InformationRespItem-RL-AdditionFailureTDD ::= ProtocolIE-Single-Container


--Unsuccessful-RL-InformationRespItemIE-RL-AdditionFailureTDD NBAP-PROTOCOL-IES ::= {
--	{ ID id-Unsuccessful-RL-InformationResp-RL-AdditionFailureTDD	CRITICALITY ignore	TYPE Unsuccessful-RL-InformationResp-RL-AdditionFailureTDD	PRESENCE mandatory }
--}

Unsuccessful-RL-InformationResp-RL-AdditionFailureTDD ::= SEQUENCE {
	rL-ID									RL-ID,
	cause									Cause,
--	iE-Extensions							ProtocolExtensionContainer { { Unsuccessful-RL-InformationResp-RL-AdditionFailureTDD-ExtIEs} }		OPTIONAL,
	iE-Extensions							ProtocolExtensionContainer OPTIONAL,
	...
}

--Unsuccessful-RL-InformationResp-RL-AdditionFailureTDD-ExtIEs  NBAP-PROTOCOL-EXTENSION ::= {
--	...
--}

-- **************************************************************
--
-- RADIO LINK RECONFIGURATION PREPARE FDD
--
-- **************************************************************

--RadioLinkReconfigurationPrepareFDD ::= SEQUENCE {
--	protocolIEs				ProtocolIE-Container	{{RadioLinkReconfigurationPrepareFDD-IEs}},
--	protocolExtensions		ProtocolExtensionContainer	{{RadioLinkReconfigurationPrepareFDD-Extensions}}		OPTIONAL,
--	...
--}

RadioLinkReconfigurationPrepareFDD ::= SEQUENCE {
	protocolIEs				ProtocolIE-Container,
	protocolExtensions		ProtocolExtensionContainer OPTIONAL,
	...
}

--RadioLinkReconfigurationPrepareFDD-IEs NBAP-PROTOCOL-IES ::= {
--	{ ID id-NodeB-CommunicationContextID					CRITICALITY reject	TYPE NodeB-CommunicationContextID							PRESENCE mandatory }|
--	{ ID id-UL-DPCH-Information-RL-ReconfPrepFDD			CRITICALITY reject	TYPE UL-DPCH-Information-RL-ReconfPrepFDD					PRESENCE optional }|
--	{ ID id-DL-DPCH-Information-RL-ReconfPrepFDD			CRITICALITY reject	TYPE DL-DPCH-Information-RL-ReconfPrepFDD					PRESENCE optional }|
--	{ ID id-FDD-DCHs-to-Modify								CRITICALITY reject	TYPE FDD-DCHs-to-Modify							PRESENCE optional }|
--	{ ID id-DCHs-to-Add-FDD									CRITICALITY reject	TYPE DCH-FDD-Information							PRESENCE optional }|
--	{ ID id-DCH-DeleteList-RL-ReconfPrepFDD					CRITICALITY reject	TYPE DCH-DeleteList-RL-ReconfPrepFDD						PRESENCE optional }|
--	{ ID id-RL-InformationList-RL-ReconfPrepFDD				CRITICALITY reject	TYPE RL-InformationList-RL-ReconfPrepFDD					PRESENCE optional }|
--	{ ID id-Transmission-Gap-Pattern-Sequence-Information	CRITICALITY reject	TYPE Transmission-Gap-Pattern-Sequence-Information		PRESENCE optional },
--	...
--}

--RadioLinkReconfigurationPrepareFDD-Extensions NBAP-PROTOCOL-EXTENSION ::= {
--	{ ID id-SignallingBearerRequestIndicator		CRITICALITY reject	EXTENSION SignallingBearerRequestIndicator					PRESENCE optional }|
--	{ ID id-HSDSCH-FDD-Information					CRITICALITY reject	EXTENSION HSDSCH-FDD-Information					PRESENCE optional }|
--	{ ID id-HSDSCH-Information-to-Modify			CRITICALITY reject	EXTENSION HSDSCH-Information-to-Modify					PRESENCE optional }|
--	{ ID id-HSDSCH-MACdFlows-to-Add					CRITICALITY reject	EXTENSION HSDSCH-MACdFlows-Information					PRESENCE optional }|
--	{ ID id-HSDSCH-MACdFlows-to-Delete				CRITICALITY reject	EXTENSION HSDSCH-MACdFlows-to-Delete					PRESENCE optional }|
--	{ ID id-HSDSCH-RNTI								CRITICALITY reject	EXTENSION HSDSCH-RNTI						PRESENCE conditional }|
	-- The IE shall be present if HS-PDSCH RL ID IE is present.
--	{ ID id-HSPDSCH-RL-ID							CRITICALITY reject	EXTENSION RL-ID								PRESENCE optional }|
--	{ ID id-E-DPCH-Information-RL-ReconfPrepFDD		CRITICALITY reject	EXTENSION E-DPCH-Information-RL-ReconfPrepFDD				PRESENCE optional }|
--	{ ID id-E-DCH-FDD-Information					CRITICALITY reject	EXTENSION E-DCH-FDD-Information					PRESENCE optional }|
--	{ ID id-E-DCH-FDD-Information-to-Modify			CRITICALITY reject	EXTENSION E-DCH-FDD-Information-to-Modify					PRESENCE optional }|
--	{ ID id-E-DCH-MACdFlows-to-Add					CRITICALITY reject	EXTENSION E-DCH-MACdFlows-Information					PRESENCE optional }|
--	{ ID id-E-DCH-MACdFlows-to-Delete				CRITICALITY reject	EXTENSION E-DCH-MACdFlows-to-Delete					PRESENCE optional }|
--	{ ID id-Serving-E-DCH-RL-ID						CRITICALITY reject	EXTENSION Serving-E-DCH-RL-ID					PRESENCE optional }|
--	{ ID id-F-DPCH-Information-RL-ReconfPrepFDD		CRITICALITY reject	EXTENSION F-DPCH-Information-RL-ReconfPrepFDD				PRESENCE optional },
--	...
--}

UL-DPCH-Information-RL-ReconfPrepFDD ::= SEQUENCE {
	ul-ScramblingCode								UL-ScramblingCode					OPTIONAL,
	ul-SIR-Target									UL-SIR								OPTIONAL,
	minUL-ChannelisationCodeLength					MinUL-ChannelisationCodeLength		OPTIONAL,
	maxNrOfUL-DPDCHs								MaxNrOfUL-DPDCHs					OPTIONAL,
	-- This IE shall be present if minUL-ChannelisationCodeLength Ie is set to 4 
	ul-PunctureLimit								PunctureLimit						OPTIONAL,
	tFCS											TFCS								OPTIONAL,
	ul-DPCCH-SlotFormat								UL-DPCCH-SlotFormat					OPTIONAL,
	diversityMode									DiversityMode						OPTIONAL,
	not-Used-sSDT-CellIDLength						NULL								OPTIONAL,
	not-Used-s-FieldLength							NULL								OPTIONAL,
--	iE-Extensions									ProtocolExtensionContainer { { UL-DPCH-Information-RL-ReconfPrepFDD-ExtIEs} }		OPTIONAL,
	iE-Extensions									ProtocolExtensionContainer OPTIONAL,
	...
}

--UL-DPCH-Information-RL-ReconfPrepFDD-ExtIEs  NBAP-PROTOCOL-EXTENSION ::= {
--	{ ID id-UL-DPDCH-Indicator-For-E-DCH-Operation	CRITICALITY reject	EXTENSION UL-DPDCH-Indicator-For-E-DCH-Operation			PRESENCE optional },
--	...
--}

DL-DPCH-Information-RL-ReconfPrepFDD ::= SEQUENCE {
	tFCS											TFCS								OPTIONAL,
	dl-DPCH-SlotFormat								DL-DPCH-SlotFormat					OPTIONAL,
	tFCI-SignallingMode								TFCI-SignallingMode					OPTIONAL,
	tFCI-Presence									TFCI-Presence						OPTIONAL,
	-- This IE shall be present if the DL DPCH Slot Format IE is set to any of the values from 12 to 16
	multiplexingPosition							MultiplexingPosition 				OPTIONAL,
	not-Used-pDSCH-CodeMapping						NULL								OPTIONAL,
	not-Used-pDSCH-RL-ID							NULL								OPTIONAL,
	limitedPowerIncrease							LimitedPowerIncrease				OPTIONAL,
--	iE-Extensions									ProtocolExtensionContainer { { DL-DPCH-Information-RL-ReconfPrepFDD-ExtIEs} }		OPTIONAL,
	iE-Extensions									ProtocolExtensionContainer OPTIONAL,
	...
}

--DL-DPCH-Information-RL-ReconfPrepFDD-ExtIEs  NBAP-PROTOCOL-EXTENSION ::= {
--	{ ID id-DL-DPCH-Power-Information-RL-ReconfPrepFDD	CRITICALITY reject	EXTENSION DL-DPCH-Power-Information-RL-ReconfPrepFDD	PRESENCE optional },
--	...
--}

DL-DPCH-Power-Information-RL-ReconfPrepFDD ::= SEQUENCE {
	powerOffsetInformation					PowerOffsetInformation-RL-ReconfPrepFDD,
	fdd-TPC-DownlinkStepSize				FDD-TPC-DownlinkStepSize,
	innerLoopDLPCStatus						InnerLoopDLPCStatus,
--	iE-Extensions							ProtocolExtensionContainer { { DL-DPCH-Power-Information-RL-ReconfPrepFDD-ExtIEs } }			OPTIONAL,
	iE-Extensions							ProtocolExtensionContainer OPTIONAL,
	...
}

--DL-DPCH-Power-Information-RL-ReconfPrepFDD-ExtIEs NBAP-PROTOCOL-EXTENSION ::= {
--	...
--}

PowerOffsetInformation-RL-ReconfPrepFDD ::= SEQUENCE {
	pO1-ForTFCI-Bits						PowerOffset,
	pO2-ForTPC-Bits							PowerOffset,
	pO3-ForPilotBits						PowerOffset,
--	iE-Extensions							ProtocolExtensionContainer { { PowerOffsetInformation-RL-ReconfPrepFDD-ExtIEs} }		OPTIONAL,
	iE-Extensions							ProtocolExtensionContainer OPTIONAL,
	...
}

--PowerOffsetInformation-RL-ReconfPrepFDD-ExtIEs NBAP-PROTOCOL-EXTENSION ::= {
--	...
--}

--DCH-DeleteList-RL-ReconfPrepFDD ::= SEQUENCE (SIZE (1..maxNrOfDCHs)) OF DCH-DeleteItem-RL-ReconfPrepFDD
DCH-DeleteList-RL-ReconfPrepFDD ::= SEQUENCE (SIZE (1..128)) OF DCH-DeleteItem-RL-ReconfPrepFDD

DCH-DeleteItem-RL-ReconfPrepFDD ::= SEQUENCE {
	dCH-ID											DCH-ID,
--	iE-Extensions									ProtocolExtensionContainer { { DCH-DeleteItem-RL-ReconfPrepFDD-ExtIEs} }		OPTIONAL,
	iE-Extensions									ProtocolExtensionContainer OPTIONAL,
	...
}

--DCH-DeleteItem-RL-ReconfPrepFDD-ExtIEs  NBAP-PROTOCOL-EXTENSION ::= {
--	...
--}

--RL-InformationList-RL-ReconfPrepFDD ::= SEQUENCE (SIZE (1..maxNrOfRLs)) OF ProtocolIE-Single-Container {{ RL-InformationItemIE-RL-ReconfPrepFDD }}
RL-InformationList-RL-ReconfPrepFDD ::= SEQUENCE (SIZE (1..16)) OF ProtocolIE-Single-Container

--RL-InformationItemIE-RL-ReconfPrepFDD NBAP-PROTOCOL-IES ::= {
--	{ ID	id-RL-InformationItem-RL-ReconfPrepFDD			CRITICALITY		reject			TYPE 	RL-InformationItem-RL-ReconfPrepFDD		PRESENCE	mandatory}
--}

RL-InformationItem-RL-ReconfPrepFDD ::= SEQUENCE {
	rL-ID											RL-ID,
	dl-CodeInformation							FDD-DL-CodeInformation		OPTIONAL,
	maxDL-Power										DL-Power									OPTIONAL,
	minDL-Power										DL-Power									OPTIONAL,
	not-Used-sSDT-Indication							NULL									OPTIONAL,
	not-Used-sSDT-Cell-Identity							NULL									OPTIONAL,
	transmitDiversityIndicator						TransmitDiversityIndicator					OPTIONAL,
	-- This IE shall be present if Diversity Mode IE is present in UL DPCH Information IE and it is not set to “none”
--	iE-Extensions									ProtocolExtensionContainer { { RL-InformationItem-RL-ReconfPrepFDD-ExtIEs} }		OPTIONAL,
	iE-Extensions									ProtocolExtensionContainer OPTIONAL,
	...
}

--RL-InformationItem-RL-ReconfPrepFDD-ExtIEs  NBAP-PROTOCOL-EXTENSION ::= {
--	{ ID id-DLReferencePower						CRITICALITY ignore	EXTENSION DL-Power						PRESENCE optional }|
--	{ ID id-RL-Specific-DCH-Info					CRITICALITY ignore	EXTENSION RL-Specific-DCH-Info				PRESENCE optional }|
--	{ ID id-DL-DPCH-TimingAdjustment				CRITICALITY reject	EXTENSION DL-DPCH-TimingAdjustment				PRESENCE optional }|
--	{ ID id-Primary-CPICH-Usage-for-Channel-Estimation		CRITICALITY ignore	EXTENSION Primary-CPICH-Usage-for-Channel-Estimation					PRESENCE optional}|
--	{ ID id-Secondary-CPICH-Information-Change		CRITICALITY ignore	EXTENSION Secondary-CPICH-Information-Change			PRESENCE optional }|
--	{ ID id-E-DCH-RL-Indication						CRITICALITY reject	EXTENSION E-DCH-RL-Indication				PRESENCE optional }|
--	{ ID id-RL-Specific-E-DCH-Info					CRITICALITY ignore	EXTENSION RL-Specific-E-DCH-Info				PRESENCE optional },
--	...
--}

E-DPCH-Information-RL-ReconfPrepFDD ::= SEQUENCE {
	maxSet-E-DPDCHs								Max-Set-E-DPDCHs													OPTIONAL,
	ul-PunctureLimit							PunctureLimit														OPTIONAL,
	e-TFCS-Information								E-TFCS-Information														OPTIONAL,
	e-TTI										E-TTI																OPTIONAL,
	e-DPCCH-PO									E-DPCCH-PO																					OPTIONAL,
--	iE-Extensions								ProtocolExtensionContainer { { E-DPCH-Information-RL-ReconfPrepFDD-ExtIEs} }		OPTIONAL,
	iE-Extensions								ProtocolExtensionContainer OPTIONAL,
	...
}

--E-DPCH-Information-RL-ReconfPrepFDD-ExtIEs NBAP-PROTOCOL-EXTENSION ::= {
--	...
--}

F-DPCH-Information-RL-ReconfPrepFDD ::= SEQUENCE {
	powerOffsetInformation				PowerOffsetInformation-F-DPCH-RL-ReconfPrepFDD,
	fdd-TPC-DownlinkStepSize			FDD-TPC-DownlinkStepSize,
	limitedPowerIncrease				LimitedPowerIncrease,
	innerLoopDLPCStatus					InnerLoopDLPCStatus,
--	iE-Extensions						ProtocolExtensionContainer { { F-DPCH-Information-RL-ReconfPrepFDD-ExtIEs} }					OPTIONAL,
	iE-Extensions						ProtocolExtensionContainer OPTIONAL,
	...
}

--F-DPCH-Information-RL-ReconfPrepFDD-ExtIEs NBAP-PROTOCOL-EXTENSION ::= {
--	...
--}

PowerOffsetInformation-F-DPCH-RL-ReconfPrepFDD ::= SEQUENCE {
	pO2-ForTPC-Bits						PowerOffset,
--	iE-Extensions						ProtocolExtensionContainer { { PowerOffsetInformation-F-DPCH-RL-ReconfPrepFDD-ExtIEs} }		OPTIONAL,
	iE-Extensions						ProtocolExtensionContainer OPTIONAL,
	...
}

--PowerOffsetInformation-F-DPCH-RL-ReconfPrepFDD-ExtIEs NBAP-PROTOCOL-EXTENSION ::= {
--	...
--}

-- **************************************************************
--
-- RADIO LINK RECONFIGURATION PREPARE TDD
--
-- **************************************************************

--RadioLinkReconfigurationPrepareTDD ::= SEQUENCE {
--	protocolIEs				ProtocolIE-Container	{{RadioLinkReconfigurationPrepareTDD-IEs}},
--	protocolExtensions		ProtocolExtensionContainer	{{RadioLinkReconfigurationPrepareTDD-Extensions}}		OPTIONAL,
--	...
--}
RadioLinkReconfigurationPrepareTDD ::= SEQUENCE {
	protocolIEs				ProtocolIE-Container,
	protocolExtensions		ProtocolExtensionContainer OPTIONAL,
	...
}

--RadioLinkReconfigurationPrepareTDD-IEs NBAP-PROTOCOL-IES ::= {
--	{ ID id-NodeB-CommunicationContextID						CRITICALITY reject	TYPE NodeB-CommunicationContextID				PRESENCE mandatory }|
--	{ ID id-UL-CCTrCH-InformationAddList-RL-ReconfPrepTDD		CRITICALITY reject	TYPE UL-CCTrCH-InformationAddList-RL-ReconfPrepTDD			PRESENCE optional }|
--	{ ID id-UL-CCTrCH-InformationModifyList-RL-ReconfPrepTDD	CRITICALITY reject	TYPE UL-CCTrCH-InformationModifyList-RL-ReconfPrepTDD			PRESENCE optional }|
--	{ ID id-UL-CCTrCH-InformationDeleteList-RL-ReconfPrepTDD	CRITICALITY reject	TYPE UL-CCTrCH-InformationDeleteList-RL-ReconfPrepTDD			PRESENCE optional }|
--	{ ID id-DL-CCTrCH-InformationAddList-RL-ReconfPrepTDD		CRITICALITY reject	TYPE DL-CCTrCH-InformationAddList-RL-ReconfPrepTDD			PRESENCE optional	}|
--	{ ID id-DL-CCTrCH-InformationModifyList-RL-ReconfPrepTDD	CRITICALITY reject	TYPE DL-CCTrCH-InformationModifyList-RL-ReconfPrepTDD			PRESENCE optional }|
--	{ ID id-DL-CCTrCH-InformationDeleteList-RL-ReconfPrepTDD	CRITICALITY reject	TYPE DL-CCTrCH-InformationDeleteList-RL-ReconfPrepTDD			PRESENCE optional }|
--	{ ID id-TDD-DCHs-to-Modify									CRITICALITY reject	TYPE TDD-DCHs-to-Modify					PRESENCE optional }|
--	{ ID id-DCHs-to-Add-TDD										CRITICALITY reject	TYPE DCH-TDD-Information					PRESENCE optional }|
--	{ ID id-DCH-DeleteList-RL-ReconfPrepTDD						CRITICALITY reject	TYPE DCH-DeleteList-RL-ReconfPrepTDD			PRESENCE optional }|
--	{ ID id-DSCH-Information-ModifyList-RL-ReconfPrepTDD		CRITICALITY reject	TYPE DSCH-Information-ModifyList-RL-ReconfPrepTDD				PRESENCE optional }|
--	{ ID id-DSCHs-to-Add-TDD									CRITICALITY reject	TYPE DSCH-TDD-Information					PRESENCE optional }|
--	{ ID id-DSCH-Information-DeleteList-RL-ReconfPrepTDD		CRITICALITY reject	TYPE DSCH-Information-DeleteList-RL-ReconfPrepTDD				PRESENCE optional }|
--	{ ID id-USCH-Information-ModifyList-RL-ReconfPrepTDD		CRITICALITY reject	TYPE USCH-Information-ModifyList-RL-ReconfPrepTDD				PRESENCE optional }|
--	{ ID id-USCH-Information-Add								CRITICALITY reject	TYPE USCH-Information					PRESENCE optional }|
--	{ ID id-USCH-Information-DeleteList-RL-ReconfPrepTDD		CRITICALITY reject	TYPE USCH-Information-DeleteList-RL-ReconfPrepTDD				PRESENCE optional }|
--	{ ID id-RL-Information-RL-ReconfPrepTDD						CRITICALITY reject	TYPE RL-Information-RL-ReconfPrepTDD			PRESENCE optional },
-- This RL Information is the for the 1st RL IE repetition
--	...
--}

--RadioLinkReconfigurationPrepareTDD-Extensions NBAP-PROTOCOL-EXTENSION ::= {
--	{ ID	id-SignallingBearerRequestIndicator		CRITICALITY reject	EXTENSION SignallingBearerRequestIndicator				PRESENCE optional }|
--	{ ID	id-HSDSCH-TDD-Information				CRITICALITY reject	EXTENSION HSDSCH-TDD-Information				PRESENCE optional	}|
--	{ ID	id-HSDSCH-Information-to-Modify			CRITICALITY reject	EXTENSION HSDSCH-Information-to-Modify				PRESENCE optional }|
--	{ ID	id-HSDSCH-MACdFlows-to-Add				CRITICALITY reject	EXTENSION HSDSCH-MACdFlows-Information				PRESENCE optional }|
--	{ ID	id-HSDSCH-MACdFlows-to-Delete			CRITICALITY reject	EXTENSION HSDSCH-MACdFlows-to-Delete				PRESENCE optional }|
--	{ ID	id-HSDSCH-RNTI							CRITICALITY reject	EXTENSION HSDSCH-RNTI					PRESENCE conditional }|
	-- The IE shall be present if HS-PDSCH RL ID IE is present.
--	{ ID	id-HSPDSCH-RL-ID						CRITICALITY reject	EXTENSION RL-ID							PRESENCE optional }|
--	{ ID	id-PDSCH-RL-ID							CRITICALITY ignore	EXTENSION RL-ID							PRESENCE optional }|
--	{ ID	id-multiple-RL-Information-RL-ReconfPrepTDD		CRITICALITY reject	EXTENSION MultipleRL-Information-RL-ReconfPrepTDD		PRESENCE optional	},
-- This RL Information is the for the 2nd and beyond repetition of RL information,
--	...
--}

--UL-CCTrCH-InformationAddList-RL-ReconfPrepTDD ::= SEQUENCE (SIZE (1..maxNrOfCCTrCHs)) OF UL-CCTrCH-InformationAddItem-RL-ReconfPrepTDD
UL-CCTrCH-InformationAddList-RL-ReconfPrepTDD ::= SEQUENCE (SIZE (1..16)) OF UL-CCTrCH-InformationAddItem-RL-ReconfPrepTDD

UL-CCTrCH-InformationAddItem-RL-ReconfPrepTDD ::= SEQUENCE {
	cCTrCH-ID									CCTrCH-ID,
	tFCS										TFCS,
	tFCI-Coding									TFCI-Coding,
	punctureLimit								PunctureLimit,
	ul-DPCH-InformationList						UL-DPCH-InformationAddList-RL-ReconfPrepTDD	OPTIONAL,
-- This DPCH Information is the for the first RL repetition, DPCH information for RL repetitions 2 and on, should be defined in MultipleRL-UL-DPCH-InformationAddList-RL-ReconfPrepTDD
--	iE-Extensions								ProtocolExtensionContainer { { UL-CCTrCH-InformationAddItem-RL-ReconfPrepTDD-ExtIEs} }		OPTIONAL,
	iE-Extensions								ProtocolExtensionContainer OPTIONAL,
	...
}

--UL-CCTrCH-InformationAddItem-RL-ReconfPrepTDD-ExtIEs  NBAP-PROTOCOL-EXTENSION ::= {
--	{ ID id-UL-DPCH-LCR-InformationAddListIE-RL-ReconfPrepTDD	CRITICALITY reject	EXTENSION UL-DPCH-LCR-InformationAddList-RL-ReconfPrepTDD		PRESENCE optional }|
	-- Applicable to 1.28Mcps TDD only
-- This DPCH Information is the for the first RL repetition, DPCH information for RL repetitions 2 and on, should be defined in MultipleRL-UL-DPCH-InformationAddList-RL-ReconfPrepTDD
--	{ ID id-UL-SIRTarget										CRITICALITY reject	EXTENSION UL-SIR	PRESENCE optional }|
	-- Mandatory for 1.28Mcps TDD, Not Applicable to 3.84Mcps TDD.
-- This Information is the for the first RL repetition, SIR Target information for RL repetitions 2 and on, should be defined in MultipleRL-UL-DPCH-InformationAddList-RL-ReconfPrepTDD
--	{ ID id-TDD-TPC-UplinkStepSize-InformationAdd-LCR-RL-ReconfPrepTDD	CRITICALITY reject	EXTENSION TDD-TPC-UplinkStepSize-LCR	PRESENCE optional	}|
-- This Information is the for the first RL repetition, TPCinformation for RL repetitions 2 and on, should be defined in MultipleRL-UL-DPCH-InformationAddList-RL-ReconfPrepTDD
	-- Mandatory for 1.28Mcps TDD, Not Applicable to 3.84Mcps TDD.
--	{ ID id-RL-ID												CRITICALITY ignore	EXTENSION RL-ID	PRESENCE optional }|
-- This is the RL ID for the first RL repetition
--	{ ID id-multipleRL-ul-DPCH-InformationList					CRITICALITY reject	EXTENSION MultipleRL-UL-DPCH-InformationAddList-RL-ReconfPrepTDD	PRESENCE optional },
-- This Information is the for the 2nd and beyond RL repetition,
--	...
--}

--MultipleRL-UL-DPCH-InformationAddList-RL-ReconfPrepTDD ::= SEQUENCE (SIZE (1..maxNrOfRLs-1)) OF MultipleRL-UL-DPCH-InformationAddListIE-RL-ReconfPrepTDD
MultipleRL-UL-DPCH-InformationAddList-RL-ReconfPrepTDD ::= SEQUENCE (SIZE (1..15)) OF MultipleRL-UL-DPCH-InformationAddListIE-RL-ReconfPrepTDD
--Includes the 2nd through the max number of radio link repetitions.

MultipleRL-UL-DPCH-InformationAddListIE-RL-ReconfPrepTDD ::= SEQUENCE {
	ul-DPCH-InformationList						UL-DPCH-InformationAddList-RL-ReconfPrepTDD		OPTIONAL,
	ul-DPCH-InformationListLCR					UL-DPCH-LCR-InformationAddList-RL-ReconfPrepTDD	OPTIONAL,
	ul-sir-target								UL-SIR											OPTIONAL,
	-- Mandatory for 1.28Mcps TDD, Not Applicable to 3.84Mcps TDD.
	tDD-TPC-UplinkStepSize-LCR 					TDD-TPC-UplinkStepSize-LCR						OPTIONAL,
	-- Mandatory for 1.28Mcps TDD, Not Applicable to 3.84Mcps TDD.
	rL-ID										RL-ID		OPTIONAL,
--	iE-Extensions								ProtocolExtensionContainer { { MultipleRL-UL-DPCH-InformationAddListIE-RL-ReconfPrepTDD-ExtIEs} }		OPTIONAL,
	iE-Extensions								ProtocolExtensionContainer OPTIONAL,

...
}

--MultipleRL-UL-DPCH-InformationAddListIE-RL-ReconfPrepTDD-ExtIEs  NBAP-PROTOCOL-EXTENSION ::= {
--	...
--}

--UL-DPCH-InformationAddList-RL-ReconfPrepTDD ::= ProtocolIE-Single-Container {{ UL-DPCH-InformationAddListIEs-RL-ReconfPrepTDD }}
UL-DPCH-InformationAddList-RL-ReconfPrepTDD ::= ProtocolIE-Single-Container

--UL-DPCH-InformationAddListIEs-RL-ReconfPrepTDD NBAP-PROTOCOL-IES ::= {
--	{ ID id-UL-DPCH-InformationAddListIE-RL-ReconfPrepTDD   CRITICALITY reject		TYPE UL-DPCH-InformationAddItem-RL-ReconfPrepTDD		PRESENCE mandatory }
--}

UL-DPCH-InformationAddItem-RL-ReconfPrepTDD ::= SEQUENCE {
	repetitionPeriod						RepetitionPeriod,
	repetitionLength						RepetitionLength,
	tdd-DPCHOffset							TDD-DPCHOffset,
	uL-Timeslot-Information					UL-Timeslot-Information,
--	iE-Extensions							ProtocolExtensionContainer { { UL-DPCH-InformationAddItem-RL-ReconfPrepTDD-ExtIEs} }		OPTIONAL,
	iE-Extensions							ProtocolExtensionContainer OPTIONAL,
	...
}

--UL-DPCH-InformationAddItem-RL-ReconfPrepTDD-ExtIEs  NBAP-PROTOCOL-EXTENSION ::= {
--	...
--}

UL-DPCH-LCR-InformationAddList-RL-ReconfPrepTDD ::= SEQUENCE {
	repetitionPeriod						RepetitionPeriod,
	repetitionLength						RepetitionLength,
	tdd-DPCHOffset							TDD-DPCHOffset,
	uL-Timeslot-InformationLCR				UL-TimeslotLCR-Information,
--	iE-Extensions							ProtocolExtensionContainer { { UL-DPCH-LCR-InformationAddItem-RL-ReconfPrepTDD-ExtIEs} }		OPTIONAL,
	iE-Extensions							ProtocolExtensionContainer OPTIONAL,
	...
}

--UL-DPCH-LCR-InformationAddItem-RL-ReconfPrepTDD-ExtIEs  NBAP-PROTOCOL-EXTENSION ::= {
--	...
--}

--UL-CCTrCH-InformationModifyList-RL-ReconfPrepTDD ::= SEQUENCE (SIZE (1..maxNrOfCCTrCHs)) OF UL-CCTrCH-InformationModifyItem-RL-ReconfPrepTDD
UL-CCTrCH-InformationModifyList-RL-ReconfPrepTDD ::= SEQUENCE (SIZE (1..16)) OF UL-CCTrCH-InformationModifyItem-RL-ReconfPrepTDD

UL-CCTrCH-InformationModifyItem-RL-ReconfPrepTDD ::= SEQUENCE {
	cCTrCH-ID									CCTrCH-ID,
	tFCS										TFCS												OPTIONAL,
	tFCI-Coding									TFCI-Coding											OPTIONAL,
	punctureLimit								PunctureLimit 										OPTIONAL,
	ul-DPCH-InformationAddList					UL-DPCH-InformationModify-AddList-RL-ReconfPrepTDD	OPTIONAL,
-- This DPCH Information is the for the first RL repetition, DPCH information for RL repetitions 2 and on, should be defined in MultipleRL-UL-DPCH-InformationModifyList-RL-ReconfPrepTDD
	ul-DPCH-InformationModifyList				UL-DPCH-InformationModify-ModifyList-RL-ReconfPrepTDD	OPTIONAL,
-- This DPCH Information is the for the first RL repetition, DPCH information for RL repetitions 2 and on, should be defined in MultipleRL-UL-DPCH-InformationModifyList-RL-ReconfPrepTDD
	ul-DPCH-InformationDeleteList				UL-DPCH-InformationModify-DeleteList-RL-ReconfPrepTDD	OPTIONAL,
-- This DPCH Information is the for the first RL repetition, DPCH information for RL repetitions 2 and on, should be defined in MultipleRL-UL-DPCH-InformationModifyList-RL-ReconfPrepTDD
--	iE-Extensions								ProtocolExtensionContainer { { UL-CCTrCH-InformationModifyItem-RL-ReconfPrepTDD-ExtIEs} }		OPTIONAL,
	iE-Extensions								ProtocolExtensionContainer OPTIONAL,
	...
}

--UL-CCTrCH-InformationModifyItem-RL-ReconfPrepTDD-ExtIEs  NBAP-PROTOCOL-EXTENSION ::= {
--	{ ID id-UL-DPCH-LCR-InformationModify-AddList	 CRITICALITY reject		EXTENSION	 UL-DPCH-LCR-InformationModify-AddList-RL-ReconfPrepTDD		PRESENCE optional }|
	-- Applicable to 1.28Mcps TDD only
-- This DPCH Information is the for the first RL repetition, DPCH information for RL repetitions 2 and on, should be defined in MultipleRL-UL-DPCH-InformationModifyList-RL-ReconfPrepTDD
--	{ ID id-UL-SIRTarget		CRITICALITY reject		EXTENSION		UL-SIR		PRESENCE optional	}|
	-- Applicable to 1.28Mcps TDD only.
-- This Information is the for the first RL repetition, SIR Target information for RL repetitions 2 and on, should be defined in MultipleRL-UL-DPCH-InformationModifyList-RL-ReconfPrepTDD
--	{ ID id-TDD-TPC-UplinkStepSize-InformationModify-LCR-RL-ReconfPrepTDD		CRITICALITY reject		EXTENSION	TDD-TPC-UplinkStepSize-LCR	PRESENCE optional	}|
	-- Applicable to 1.28Mcps TDD only
-- This Information is the for the first RL repetition, Step Size information for RL repetitions 2 and on, should be defined in MultipleRL-UL-DPCH-InformationModifyList-RL-ReconfPrepTDD
--	{ ID id-RL-ID										CRITICALITY ignore		EXTENSION		RL-ID		PRESENCE optional	}|
-- This is the RL ID for the first RL repetition
--	{ ID id-multipleRL-ul-DPCH-InformationModifyList	CRITICALITY reject		EXTENSION		MultipleRL-UL-DPCH-InformationModifyList-RL-ReconfPrepTDD	PRESENCE optional	},
-- This DPCH Information is the for the 2nd and beyond RL repetition,
--	...
--}

--UL-DPCH-InformationModify-AddList-RL-ReconfPrepTDD ::= ProtocolIE-Single-Container {{ UL-DPCH-InformationModify-AddListIEs-RL-ReconfPrepTDD }}
UL-DPCH-InformationModify-AddList-RL-ReconfPrepTDD ::= ProtocolIE-Single-Container

--UL-DPCH-InformationModify-AddListIEs-RL-ReconfPrepTDD NBAP-PROTOCOL-IES ::= {
--	{ ID id-UL-DPCH-InformationModify-AddListIE-RL-ReconfPrepTDD   CRITICALITY reject		TYPE UL-DPCH-InformationModify-AddItem-RL-ReconfPrepTDD		PRESENCE mandatory }
--}

--MultipleRL-UL-DPCH-InformationModifyList-RL-ReconfPrepTDD ::= SEQUENCE (SIZE (1..maxNrOfRLs-1)) OF MultipleRL-UL-DPCH-InformationModifyListIE-RL-ReconfPrepTDD
MultipleRL-UL-DPCH-InformationModifyList-RL-ReconfPrepTDD ::= SEQUENCE (SIZE (1..15)) OF MultipleRL-UL-DPCH-InformationModifyListIE-RL-ReconfPrepTDD
--Includes the 2nd through the max number of radio link information repetitions.

MultipleRL-UL-DPCH-InformationModifyListIE-RL-ReconfPrepTDD ::= SEQUENCE {
	ul-DPCH-InformationAddList					UL-DPCH-InformationModify-AddList-RL-ReconfPrepTDD	OPTIONAL,
	ul-DPCH-InformationModifyList				UL-DPCH-InformationModify-ModifyList-RL-ReconfPrepTDD	OPTIONAL,
	ul-DPCH-InformationDeleteList				UL-DPCH-InformationModify-DeleteList-RL-ReconfPrepTDD	OPTIONAL,
	ul-DPCH-InformationAddListLCR				UL-DPCH-LCR-InformationModify-AddList-RL-ReconfPrepTDD	OPTIONAL,
	ul-sir-target								UL-SIR		OPTIONAL,
	tDD-TPC-UplinkStepSize-LCR					TDD-TPC-UplinkStepSize-LCR	OPTIONAL,
	rL-ID										RL-ID		OPTIONAL,
-- This DPCH Information is the for the 2nd and beyond RL repetitions, 
--	iE-Extensions								ProtocolExtensionContainer { { MultipleRL-UL-DPCH-InformationModifyListIE-RL-ReconfPrepTDD-ExtIEs} }		OPTIONAL,
	iE-Extensions								ProtocolExtensionContainer OPTIONAL,
...
}

--MultipleRL-UL-DPCH-InformationModifyListIE-RL-ReconfPrepTDD-ExtIEs  NBAP-PROTOCOL-EXTENSION ::= {
--	...
--}

UL-DPCH-InformationModify-AddItem-RL-ReconfPrepTDD ::= SEQUENCE {
	repetitionPeriod						RepetitionPeriod,
	repetitionLength						RepetitionLength,
	tdd-DPCHOffset							TDD-DPCHOffset,
	uL-Timeslot-Information					UL-Timeslot-Information,
--	iE-Extensions							ProtocolExtensionContainer { { UL-DPCH-InformationModify-AddItem-RL-ReconfPrepTDD-ExtIEs} }		OPTIONAL,
	iE-Extensions							ProtocolExtensionContainer OPTIONAL,
	...
}

--UL-DPCH-InformationModify-AddItem-RL-ReconfPrepTDD-ExtIEs  NBAP-PROTOCOL-EXTENSION ::= {
--	...
--}

UL-DPCH-LCR-InformationModify-AddList-RL-ReconfPrepTDD ::= SEQUENCE {
	repetitionPeriod						RepetitionPeriod,
	repetitionLength						RepetitionLength,
	tdd-DPCHOffset							TDD-DPCHOffset,
	uL-Timeslot-InformationLCR				UL-TimeslotLCR-Information,
--	iE-Extensions							ProtocolExtensionContainer { { UL-DPCH-LCR-InformationModify-AddItem-RL-ReconfPrepTDD-ExtIEs} }		OPTIONAL,
	iE-Extensions							ProtocolExtensionContainer OPTIONAL,
	...
}

--UL-DPCH-LCR-InformationModify-AddItem-RL-ReconfPrepTDD-ExtIEs  NBAP-PROTOCOL-EXTENSION ::= {
--	...
--}

--UL-DPCH-InformationModify-ModifyList-RL-ReconfPrepTDD ::= ProtocolIE-Single-Container {{ UL-DPCH-InformationModify-ModifyListIEs-RL-ReconfPrepTDD }}
UL-DPCH-InformationModify-ModifyList-RL-ReconfPrepTDD ::= ProtocolIE-Single-Container

--UL-DPCH-InformationModify-ModifyListIEs-RL-ReconfPrepTDD NBAP-PROTOCOL-IES ::= {
--	{ ID id-UL-DPCH-InformationModify-ModifyListIE-RL-ReconfPrepTDD   CRITICALITY reject		TYPE UL-DPCH-InformationModify-ModifyItem-RL-ReconfPrepTDD		PRESENCE mandatory }
--}

UL-DPCH-InformationModify-ModifyItem-RL-ReconfPrepTDD ::= SEQUENCE {
	repetitionPeriod						RepetitionPeriod	OPTIONAL,
	repetitionLength						RepetitionLength	OPTIONAL,
	tdd-DPCHOffset							TDD-DPCHOffset		OPTIONAL,
	uL-Timeslot-InformationModify-ModifyList-RL-ReconfPrepTDD				UL-Timeslot-InformationModify-ModifyList-RL-ReconfPrepTDD			OPTIONAL,
--	iE-Extensions							ProtocolExtensionContainer { { UL-DPCH-InformationModify-ModifyItem-RL-ReconfPrepTDD-ExtIEs} }		OPTIONAL,
	iE-Extensions							ProtocolExtensionContainer OPTIONAL,
	...
}

--UL-DPCH-InformationModify-ModifyItem-RL-ReconfPrepTDD-ExtIEs  NBAP-PROTOCOL-EXTENSION ::= {
--	{ ID id-UL-TimeslotLCR-Information-RL-ReconfPrepTDD   	CRITICALITY reject		EXTENSION 	UL-TimeslotLCR-InformationModify-ModifyList-RL-ReconfPrepTDD		PRESENCE optional },
	-- Applicable to 1.28Mcps TDD only
--	...
--}

--UL-Timeslot-InformationModify-ModifyList-RL-ReconfPrepTDD ::= SEQUENCE (SIZE (1..maxNrOfULTSs)) OF UL-Timeslot-InformationModify-ModifyItem-RL-ReconfPrepTDD
	-- Applicable to 3.84Mcps TDD only
UL-Timeslot-InformationModify-ModifyList-RL-ReconfPrepTDD ::= SEQUENCE (SIZE (1..15)) OF UL-Timeslot-InformationModify-ModifyItem-RL-ReconfPrepTDD	
-- Applicable to 3.84Mcps TDD only

UL-Timeslot-InformationModify-ModifyItem-RL-ReconfPrepTDD ::= SEQUENCE {
	timeSlot								TimeSlot,
	midambleShiftAndBurstType				MidambleShiftAndBurstType		OPTIONAL,
	tFCI-Presence							TFCI-Presence		OPTIONAL,
	uL-Code-InformationModify-ModifyList-RL-ReconfPrepTDD				UL-Code-InformationModify-ModifyList-RL-ReconfPrepTDD		OPTIONAL,
--	iE-Extensions							ProtocolExtensionContainer { { UL-Timeslot-InformationModify-ModifyItem-RL-ReconfPrepTDD-ExtIEs} }		OPTIONAL,
	iE-Extensions							ProtocolExtensionContainer OPTIONAL,
	...
}

--UL-Timeslot-InformationModify-ModifyItem-RL-ReconfPrepTDD-ExtIEs NBAP-PROTOCOL-EXTENSION ::= {
--	...
--}

--UL-Code-InformationModify-ModifyList-RL-ReconfPrepTDD ::= SEQUENCE (SIZE (1..maxNrOfDPCHs)) OF UL-Code-InformationModify-ModifyItem-RL-ReconfPrepTDD
UL-Code-InformationModify-ModifyList-RL-ReconfPrepTDD ::= SEQUENCE (SIZE (1..240)) OF UL-Code-InformationModify-ModifyItem-RL-ReconfPrepTDD

UL-Code-InformationModify-ModifyItem-RL-ReconfPrepTDD ::= SEQUENCE {
	dPCH-ID									DPCH-ID,
	tdd-ChannelisationCode					TDD-ChannelisationCode		OPTIONAL,
--	iE-Extensions							ProtocolExtensionContainer { { UL-Code-InformationModify-ModifyItem-RL-ReconfPrepTDD-ExtIEs} }		OPTIONAL,
	iE-Extensions							ProtocolExtensionContainer OPTIONAL,
	...
}

--UL-Code-InformationModify-ModifyItem-RL-ReconfPrepTDD-ExtIEs NBAP-PROTOCOL-EXTENSION ::= {
--	...
--}

--UL-TimeslotLCR-InformationModify-ModifyList-RL-ReconfPrepTDD ::= SEQUENCE (SIZE (1..maxNrOfULTSLCRs)) OF UL-Timeslot-LCR-InformationModify-ModifyItem-RL-ReconfPrepTDD
	-- Applicable to 1.28Mcps TDD only
UL-TimeslotLCR-InformationModify-ModifyList-RL-ReconfPrepTDD ::= SEQUENCE (SIZE (1..6)) OF UL-Timeslot-LCR-InformationModify-ModifyItem-RL-ReconfPrepTDD
	-- Applicable to 1.28Mcps TDD only

UL-Timeslot-LCR-InformationModify-ModifyItem-RL-ReconfPrepTDD ::= SEQUENCE {
	timeSlotLCR								TimeSlotLCR,
	midambleShiftLCR						MidambleShiftLCR	OPTIONAL,
	tFCI-Presence							TFCI-Presence		OPTIONAL,
	uL-Code-InformationModify-ModifyList-RL-ReconfPrepTDDLCR				UL-Code-InformationModify-ModifyList-RL-ReconfPrepTDDLCR		OPTIONAL,
--	iE-Extensions							ProtocolExtensionContainer { { UL-Timeslot-LCR-InformationModify-ModifyItem-RL-ReconfPrepTDD-ExtIEs} }		OPTIONAL,
	iE-Extensions							ProtocolExtensionContainer OPTIONAL,
	...
}

--UL-Timeslot-LCR-InformationModify-ModifyItem-RL-ReconfPrepTDD-ExtIEs NBAP-PROTOCOL-EXTENSION ::= {
--	...
--}

--UL-Code-InformationModify-ModifyList-RL-ReconfPrepTDDLCR ::= SEQUENCE (SIZE (1..maxNrOfDPCHLCRs)) OF UL-Code-InformationModify-ModifyItem-RL-ReconfPrepTDDLCR
UL-Code-InformationModify-ModifyList-RL-ReconfPrepTDDLCR ::= SEQUENCE (SIZE (1..240)) OF UL-Code-InformationModify-ModifyItem-RL-ReconfPrepTDDLCR

UL-Code-InformationModify-ModifyItem-RL-ReconfPrepTDDLCR ::= SEQUENCE {
	dPCH-ID									DPCH-ID,
	tdd-ChannelisationCodeLCR				TDD-ChannelisationCodeLCR		OPTIONAL,
--	iE-Extensions							ProtocolExtensionContainer { { UL-Code-InformationModify-ModifyItem-RL-ReconfPrepTDDLCR-ExtIEs} }		OPTIONAL,
	iE-Extensions							ProtocolExtensionContainer OPTIONAL,
	...
}

--UL-Code-InformationModify-ModifyItem-RL-ReconfPrepTDDLCR-ExtIEs NBAP-PROTOCOL-EXTENSION ::= {
--{ ID id-UL-DPCH-TimeSlotFormat-LCR-ModifyItem-RL-ReconfPrepTDD  CRITICALITY	reject	 EXTENSION TDD-UL-DPCH-TimeSlotFormat-LCR   PRESENCE  optional},

--	...
--}

--UL-DPCH-InformationModify-DeleteList-RL-ReconfPrepTDD ::= ProtocolIE-Single-Container {{ UL-DPCH-InformationModify-DeleteListIEs-RL-ReconfPrepTDD }}
UL-DPCH-InformationModify-DeleteList-RL-ReconfPrepTDD ::= ProtocolIE-Single-Container

--UL-DPCH-InformationModify-DeleteListIEs-RL-ReconfPrepTDD NBAP-PROTOCOL-IES ::= {
--	{ ID id-UL-DPCH-InformationModify-DeleteListIE-RL-ReconfPrepTDD   CRITICALITY reject		TYPE UL-DPCH-InformationModify-DeleteListIE-RL-ReconfPrepTDD		PRESENCE mandatory }
--}

--UL-DPCH-InformationModify-DeleteListIE-RL-ReconfPrepTDD ::= SEQUENCE (SIZE (1..maxNrOfDPCHs)) OF UL-DPCH-InformationModify-DeleteItem-RL-ReconfPrepTDD
UL-DPCH-InformationModify-DeleteListIE-RL-ReconfPrepTDD ::= SEQUENCE (SIZE (1..240)) OF UL-DPCH-InformationModify-DeleteItem-RL-ReconfPrepTDD

UL-DPCH-InformationModify-DeleteItem-RL-ReconfPrepTDD ::= SEQUENCE {
	dPCH-ID										DPCH-ID,
--	iE-Extensions								ProtocolExtensionContainer { { UL-DPCH-InformationModify-DeleteItem-RL-ReconfPrepTDD-ExtIEs} }		OPTIONAL,
	iE-Extensions								ProtocolExtensionContainer OPTIONAL,
	...
}

--UL-DPCH-InformationModify-DeleteItem-RL-ReconfPrepTDD-ExtIEs  NBAP-PROTOCOL-EXTENSION ::= {
--	...
--}

--UL-CCTrCH-InformationDeleteList-RL-ReconfPrepTDD ::= SEQUENCE (SIZE (1..maxNrOfCCTrCHs)) OF UL-CCTrCH-InformationDeleteItem-RL-ReconfPrepTDD
UL-CCTrCH-InformationDeleteList-RL-ReconfPrepTDD ::= SEQUENCE (SIZE (1..16)) OF UL-CCTrCH-InformationDeleteItem-RL-ReconfPrepTDD

UL-CCTrCH-InformationDeleteItem-RL-ReconfPrepTDD ::= SEQUENCE {
	cCTrCH-ID									CCTrCH-ID,
--	iE-Extensions								ProtocolExtensionContainer { { UL-CCTrCH-InformationDeleteItem-RL-ReconfPrepTDD-ExtIEs} }		OPTIONAL,
	iE-Extensions								ProtocolExtensionContainer OPTIONAL,
	...
}

--UL-CCTrCH-InformationDeleteItem-RL-ReconfPrepTDD-ExtIEs  NBAP-PROTOCOL-EXTENSION ::= {
--	...
--}

--DL-CCTrCH-InformationAddList-RL-ReconfPrepTDD ::= SEQUENCE (SIZE (1..maxNrOfCCTrCHs)) OF DL-CCTrCH-InformationAddItem-RL-ReconfPrepTDD
DL-CCTrCH-InformationAddList-RL-ReconfPrepTDD ::= SEQUENCE (SIZE (1..16)) OF DL-CCTrCH-InformationAddItem-RL-ReconfPrepTDD

DL-CCTrCH-InformationAddItem-RL-ReconfPrepTDD ::= SEQUENCE {
	cCTrCH-ID										CCTrCH-ID,
	tFCS											TFCS,
	tFCI-Coding										TFCI-Coding,
	punctureLimit									PunctureLimit,
	cCTrCH-TPCList									CCTrCH-TPCAddList-RL-ReconfPrepTDD				OPTIONAL,
	dl-DPCH-InformationList							DL-DPCH-InformationAddList-RL-ReconfPrepTDD 	OPTIONAL,
	-- This DPCH Information is the for the first RL repetition, DPCH information for RL repetitions 2 and on, should be defined in MultipleRL-DL-DPCH-InformationAddList-RL-ReconfPrepTDD
--	iE-Extensions									ProtocolExtensionContainer { { DL-CCTrCH-InformationAddItem-RL-ReconfPrepTDD-ExtIEs} }			OPTIONAL,
	iE-Extensions									ProtocolExtensionContainer OPTIONAL,
	...
}

--DL-CCTrCH-InformationAddItem-RL-ReconfPrepTDD-ExtIEs  NBAP-PROTOCOL-EXTENSION ::= {
--	{ ID id-DL-DPCH-LCR-InformationAddList-RL-ReconfPrepTDD				CRITICALITY reject	EXTENSION DL-DPCH-LCR-InformationAddList-RL-ReconfPrepTDD		PRESENCE optional }|
	-- Applicable to 1.28Mcps TDD only
-- This DPCH Information is the for the first RL repetition, DPCH information for RL repetitions 2 and on, should be defined in MultipleRL-DL-DPCH-InformationAddList-RL-ReconfPrepTDD
--	{ ID id-CCTrCH-Initial-DL-Power-RL-ReconfPrepTDD					CRITICALITY ignore	EXTENSION DL-Power	PRESENCE optional	}|
-- This DL Power inforrmation is the for the first RL repetition, DL power information for RL repetitions 2 and on, should be defined in MultipleRL-DL-DPCH-InformationAddList-RL-ReconfPrepTDD
--	{ ID id-TDD-TPC-DownlinkStepSize-InformationAdd-RL-ReconfPrepTDD	CRITICALITY reject	EXTENSION  TDD-TPC-DownlinkStepSize	 PRESENCE optional}|
-- This DL step size is the for the first RL repetition, DL step size information for RL repetitions 2 and on, should be defined in MultipleRL-DL-DPCH-InformationAddList-RL-ReconfPrepTDD
--	{ ID id-CCTrCH-Maximum-DL-Power-InformationAdd-RL-ReconfPrepTDD		CRITICALITY ignore	EXTENSION DL-Power	PRESENCE optional	}|
-- This DL Power inforrmation is the for the first RL repetition, DL power information for RL repetitions 2 and on, should be defined in MultipleRL-DL-DPCH-InformationAddList-RL-ReconfPrepTDD
--	{ ID id-CCTrCH-Minimum-DL-Power-InformationAdd-RL-ReconfPrepTDD		CRITICALITY ignore	EXTENSION DL-Power	PRESENCE optional	}|
-- This DL Power inforrmation is the for the first RL repetition, DL power information for RL repetitions 2 and on, should be defined in MultipleRL-DL-DPCH-InformationAddList-RL-ReconfPrepTDD
--	{ ID id-RL-ID														CRITICALITY ignore	EXTENSION RL-ID	PRESENCE optional	}|
-- This is the RL ID for the first RL repetition
--	{ ID id-multipleRL-ul-DPCH-InformationList							CRITICALITY reject	EXTENSION MultipleRL-DL-DPCH-InformationAddList-RL-ReconfPrepTDD	PRESENCE optional	},
-- This DPCH Information is the for the 2nd and beyond RL repetition,
--	...
--}

--MultipleRL-DL-DPCH-InformationAddList-RL-ReconfPrepTDD ::= SEQUENCE (SIZE (1..maxNrOfRLs-1)) OF MultipleRL-DL-DPCH-InformationAddListIE-RL-ReconfPrepTDD
MultipleRL-DL-DPCH-InformationAddList-RL-ReconfPrepTDD ::= SEQUENCE (SIZE (1..15)) OF MultipleRL-DL-DPCH-InformationAddListIE-RL-ReconfPrepTDD
--Includes the 2nd through the max number of radio link information repetitions.

MultipleRL-DL-DPCH-InformationAddListIE-RL-ReconfPrepTDD ::= SEQUENCE {
	dl-DPCH-InformationList										DL-DPCH-InformationAddList-RL-ReconfPrepTDD	OPTIONAL,
	dl-DPCH-InformationListLCR									DL-DPCH-LCR-InformationAddList-RL-ReconfPrepTDD	OPTIONAL,
	cCTrCH-Initial-DL-Power										DL-Power							OPTIONAL,
	tDD-TPC-DownlinkStepSize									TDD-TPC-DownlinkStepSize			OPTIONAL,
	cCTrCH-Maximum-DL-Power-InformationAdd-RL-ReconfPrepTDD		DL-Power							OPTIONAL,
	cCTrCH-Minimum-DL-Power-InformationAdd-RL-ReconfPrepTDD		DL-Power							OPTIONAL,
	rL-ID														RL-ID		OPTIONAL,
--	iE-Extensions								ProtocolExtensionContainer { { MultipleRL-DL-DPCH-InformationAddListIE-RL-ReconfPrepTDD-ExtIEs} }		OPTIONAL,
	iE-Extensions								ProtocolExtensionContainer OPTIONAL,
	...
}

--MultipleRL-DL-DPCH-InformationAddListIE-RL-ReconfPrepTDD-ExtIEs  NBAP-PROTOCOL-EXTENSION ::= {
--	...
--}

--CCTrCH-TPCAddList-RL-ReconfPrepTDD ::= SEQUENCE (SIZE (1..maxNrOfCCTrCHs)) OF CCTrCH-TPCAddItem-RL-ReconfPrepTDD
		-- Applicable to 3.84Mcps TDD only
CCTrCH-TPCAddList-RL-ReconfPrepTDD ::= SEQUENCE (SIZE (1..16)) OF CCTrCH-TPCAddItem-RL-ReconfPrepTDD
		-- Applicable to 3.84Mcps TDD only

CCTrCH-TPCAddItem-RL-ReconfPrepTDD	 ::= SEQUENCE {
	cCTrCH-ID								CCTrCH-ID,
--	iE-Extensions							ProtocolExtensionContainer { { CCTrCH-TPCAddItem-RL-ReconfPrepTDD-ExtIEs} }		OPTIONAL,
	iE-Extensions							ProtocolExtensionContainer OPTIONAL,
	...
}

--CCTrCH-TPCAddItem-RL-ReconfPrepTDD-ExtIEs  NBAP-PROTOCOL-EXTENSION ::= {
--	...
--}

--DL-DPCH-InformationAddList-RL-ReconfPrepTDD ::= ProtocolIE-Single-Container {{ DL-DPCH-InformationAddListIEs-RL-ReconfPrepTDD }}
DL-DPCH-InformationAddList-RL-ReconfPrepTDD ::= ProtocolIE-Single-Container

--DL-DPCH-InformationAddListIEs-RL-ReconfPrepTDD NBAP-PROTOCOL-IES ::= {
--	{ ID id-DL-DPCH-InformationAddListIE-RL-ReconfPrepTDD   CRITICALITY reject		TYPE DL-DPCH-InformationAddItem-RL-ReconfPrepTDD		PRESENCE mandatory }
--}

DL-DPCH-InformationAddItem-RL-ReconfPrepTDD ::= SEQUENCE {
	repetitionPeriod						RepetitionPeriod,
	repetitionLength						RepetitionLength,
	tdd-DPCHOffset							TDD-DPCHOffset,
	dL-Timeslot-Information					DL-Timeslot-Information,
--	iE-Extensions							ProtocolExtensionContainer { { DL-DPCH-InformationAddItem-RL-ReconfPrepTDD-ExtIEs} }		OPTIONAL,
	iE-Extensions							ProtocolExtensionContainer OPTIONAL,
	...
}

--DL-DPCH-InformationAddItem-RL-ReconfPrepTDD-ExtIEs  NBAP-PROTOCOL-EXTENSION ::= {
--	...
--}

DL-DPCH-LCR-InformationAddList-RL-ReconfPrepTDD ::= SEQUENCE {
	repetitionPeriod						RepetitionPeriod,
	repetitionLength						RepetitionLength,
	tdd-DPCHOffset							TDD-DPCHOffset,
	dL-Timeslot-InformationLCR				DL-TimeslotLCR-Information,
--	iE-Extensions							ProtocolExtensionContainer { { DL-DPCH-LCR-InformationAddItem-RL-ReconfPrepTDD-ExtIEs} }		OPTIONAL,
	iE-Extensions							ProtocolExtensionContainer OPTIONAL,
	...
}

--DL-DPCH-LCR-InformationAddItem-RL-ReconfPrepTDD-ExtIEs  NBAP-PROTOCOL-EXTENSION ::= {
--	...
--}

--DL-CCTrCH-InformationModifyList-RL-ReconfPrepTDD ::= SEQUENCE (SIZE (1..maxNrOfCCTrCHs)) OF DL-CCTrCH-InformationModifyItem-RL-ReconfPrepTDD
DL-CCTrCH-InformationModifyList-RL-ReconfPrepTDD ::= SEQUENCE (SIZE (1..16)) OF DL-CCTrCH-InformationModifyItem-RL-ReconfPrepTDD

DL-CCTrCH-InformationModifyItem-RL-ReconfPrepTDD ::= SEQUENCE {
	cCTrCH-ID										CCTrCH-ID,
	tFCS											TFCS											OPTIONAL,
	tFCI-Coding										TFCI-Coding										OPTIONAL,
	punctureLimit									PunctureLimit 									OPTIONAL,
	cCTrCH-TPCList									CCTrCH-TPCModifyList-RL-ReconfPrepTDD			OPTIONAL,
	dl-DPCH-InformationAddList						DL-DPCH-InformationModify-AddList-RL-ReconfPrepTDD 	OPTIONAL,
-- This DPCH Information is the for the first RL repetition, DPCH information for RL repetitions 2 and on, should be defined in MultipleRL-DL-DPCH-InformationModifyList-RL-ReconfPrepTDD
	dl-DPCH-InformationModifyList					DL-DPCH-InformationModify-ModifyList-RL-ReconfPrepTDD 	OPTIONAL,
-- This DPCH Information is the for the first RL repetition, DPCH information for RL repetitions 2 and on, should be defined in MultipleRL-DL-DPCH-InformationModifyList-RL-ReconfPrepTDD
	dl-DPCH-InformationDeleteList					DL-DPCH-InformationModify-DeleteList-RL-ReconfPrepTDD 	OPTIONAL,
-- This DPCH Information is the for the first RL repetition, DPCH information for RL repetitions 2 and on, should be defined in MultipleRL-DL-DPCH-InformationModifyList-RL-ReconfPrepTDD
--	iE-Extensions									ProtocolExtensionContainer { { DL-CCTrCH-InformationModifyItem-RL-ReconfPrepTDD-ExtIEs} }			OPTIONAL,
	iE-Extensions									ProtocolExtensionContainer OPTIONAL,
	...
}

--DL-CCTrCH-InformationModifyItem-RL-ReconfPrepTDD-ExtIEs  NBAP-PROTOCOL-EXTENSION ::= {
--	{ ID id-DL-DPCH-LCR-InformationModify-AddList-RL-ReconfPrepTDD CRITICALITY reject		EXTENSION 	DL-DPCH-LCR-InformationModify-AddList-RL-ReconfPrepTDD		PRESENCE optional }|
  -- Applicable to 1.28Mcps TDD only
-- This DPCH Information is the for the first RL repetition, DPCH information for RL repetitions 2 and on, should be defined in MultipleRL-DL-DPCH-InformationModifyList-RL-ReconfPrepTDD
--	{ ID id-TDD-TPC-DownlinkStepSize-InformationModify-RL-ReconfPrepTDD	CRITICALITY reject	EXTENSION TDD-TPC-DownlinkStepSize	PRESENCE optional}|
-- This Step Size Information is the for the first RL repetition, step size information for RL repetitions 2 and on, should be defined in MultipleRL-DL-DPCH-InformationModifyList-RL-ReconfPrepTDD
--	{ ID id-CCTrCH-Maximum-DL-Power-InformationModify-RL-ReconfPrepTDD		CRITICALITY ignore	EXTENSION DL-Power		PRESENCE optional	}|
-- This power Information is the for the first RL repetition, power information for RL repetitions 2 and on, should be defined in MultipleRL-DL-DPCH-InformationModifyList-RL-ReconfPrepTDD
--	{ ID id-CCTrCH-Minimum-DL-Power-InformationModify-RL-ReconfPrepTDD		CRITICALITY ignore	EXTENSION DL-Power		PRESENCE optional	}|
-- This power Information is the for the first RL repetition, power information for RL repetitions 2 and on, should be defined in MultipleRL-DL-DPCH-InformationModifyList-RL-ReconfPrepTDD
--	{ ID id-RL-ID		CRITICALITY ignore		EXTENSION		RL-ID		PRESENCE optional	}|
-- This is the RL ID for the first RL repetition
--	{ ID id-multipleRL-dl-DPCH-InformationModifyList	CRITICALITY reject		EXTENSION		MultipleRL-DL-DPCH-InformationModifyList-RL-ReconfPrepTDD	PRESENCE optional	},
-- This DPCH Information is the for the 2nd and beyond RL repetitions,
--	...
--}

--MultipleRL-DL-DPCH-InformationModifyList-RL-ReconfPrepTDD ::= SEQUENCE (SIZE (1..maxNrOfRLs-1)) OF MultipleRL-DL-DPCH-InformationModifyListIE-RL-ReconfPrepTDD
MultipleRL-DL-DPCH-InformationModifyList-RL-ReconfPrepTDD ::= SEQUENCE (SIZE (1..15)) OF MultipleRL-DL-DPCH-InformationModifyListIE-RL-ReconfPrepTDD
--Includes the 2nd through the max number of radio link information repetitions.

MultipleRL-DL-DPCH-InformationModifyListIE-RL-ReconfPrepTDD ::= SEQUENCE {
	dl-DPCH-InformationAddList										DL-DPCH-InformationModify-AddList-RL-ReconfPrepTDD			OPTIONAL,
	dl-DPCH-InformationModifyList									DL-DPCH-InformationModify-ModifyList-RL-ReconfPrepTDD		OPTIONAL,
	dl-DPCH-InformationDeleteList									DL-DPCH-InformationModify-DeleteList-RL-ReconfPrepTDD		OPTIONAL,
	dl-DPCH-InformationAddListLCR									DL-DPCH-LCR-InformationModify-AddList-RL-ReconfPrepTDD	OPTIONAL,
	tDD-TPC-DownlinkStepSize-InformationModify-RL-ReconfPrepTDD		TDD-TPC-DownlinkStepSize											OPTIONAL,
	cCTrCH-Maximum-DL-Power-InformationModify-RL-ReconfPrepTDD		DL-Power									OPTIONAL,
	cCTrCH-Minimum-DL-Power-InformationModify-RL-ReconfPrepTDD		DL-Power									OPTIONAL,
	rL-ID															RL-ID		OPTIONAL,
--	iE-Extensions													ProtocolExtensionContainer { { MultipleRL-DL-DPCH-InformationModifyListIE-RL-ReconfPrepTDD-ExtIEs} }		OPTIONAL,
	iE-Extensions													ProtocolExtensionContainer OPTIONAL,
...
} 

--MultipleRL-DL-DPCH-InformationModifyListIE-RL-ReconfPrepTDD-ExtIEs  NBAP-PROTOCOL-EXTENSION ::= {
--	...
--}

--CCTrCH-TPCModifyList-RL-ReconfPrepTDD ::= SEQUENCE (SIZE (1..maxNrOfCCTrCHs)) OF CCTrCH-TPCModifyItem-RL-ReconfPrepTDD
CCTrCH-TPCModifyList-RL-ReconfPrepTDD ::= SEQUENCE (SIZE (1..16)) OF CCTrCH-TPCModifyItem-RL-ReconfPrepTDD

CCTrCH-TPCModifyItem-RL-ReconfPrepTDD	 ::= SEQUENCE {
	cCTrCH-ID								CCTrCH-ID,
--	iE-Extensions							ProtocolExtensionContainer { { CCTrCH-TPCModifyItem-RL-ReconfPrepTDD-ExtIEs} }		OPTIONAL,
	iE-Extensions							ProtocolExtensionContainer OPTIONAL,
	...
}

--CCTrCH-TPCModifyItem-RL-ReconfPrepTDD-ExtIEs  NBAP-PROTOCOL-EXTENSION ::= {
--	...
--}

--DL-DPCH-InformationModify-AddList-RL-ReconfPrepTDD ::= ProtocolIE-Single-Container {{ DL-DPCH-InformationModify-AddListIEs-RL-ReconfPrepTDD }}	
DL-DPCH-InformationModify-AddList-RL-ReconfPrepTDD ::= ProtocolIE-Single-Container 	
-- Applicable to 3.84Mcps TDD only

--DL-DPCH-InformationModify-AddListIEs-RL-ReconfPrepTDD NBAP-PROTOCOL-IES ::= {
--	{ ID id-DL-DPCH-InformationModify-AddListIE-RL-ReconfPrepTDD   CRITICALITY reject		TYPE DL-DPCH-InformationModify-AddItem-RL-ReconfPrepTDD		PRESENCE mandatory }
--}

DL-DPCH-InformationModify-AddItem-RL-ReconfPrepTDD ::= SEQUENCE {
	repetitionPeriod						RepetitionPeriod,
	repetitionLength						RepetitionLength,
	tdd-DPCHOffset							TDD-DPCHOffset,
	dL-Timeslot-Information					DL-Timeslot-Information,
--	iE-Extensions							ProtocolExtensionContainer { { DL-DPCH-InformationModify-AddItem-RL-ReconfPrepTDD-ExtIEs} }		OPTIONAL,
	iE-Extensions							ProtocolExtensionContainer OPTIONAL,
	...
}

--DL-DPCH-InformationModify-AddItem-RL-ReconfPrepTDD-ExtIEs  NBAP-PROTOCOL-EXTENSION ::= {
--	...
--}

DL-DPCH-LCR-InformationModify-AddList-RL-ReconfPrepTDD ::= SEQUENCE {
	repetitionPeriod						RepetitionPeriod,
	repetitionLength						RepetitionLength,
	tdd-DPCHOffset							TDD-DPCHOffset,
	dL-Timeslot-InformationLCR				DL-TimeslotLCR-Information,
--	iE-Extensions							ProtocolExtensionContainer { { DL-DPCH-LCR-InformationModify-AddItem-RL-ReconfPrepTDD-ExtIEs} }		OPTIONAL,
	iE-Extensions							ProtocolExtensionContainer OPTIONAL,
	...
}

--DL-DPCH-LCR-InformationModify-AddItem-RL-ReconfPrepTDD-ExtIEs  NBAP-PROTOCOL-EXTENSION ::= {
--	...
--}

--DL-DPCH-InformationModify-ModifyList-RL-ReconfPrepTDD ::= ProtocolIE-Single-Container {{ DL-DPCH-InformationModify-ModifyListIEs-RL-ReconfPrepTDD }}
DL-DPCH-InformationModify-ModifyList-RL-ReconfPrepTDD ::= ProtocolIE-Single-Container

--DL-DPCH-InformationModify-ModifyListIEs-RL-ReconfPrepTDD NBAP-PROTOCOL-IES ::= {
--	{ ID id-DL-DPCH-InformationModify-ModifyListIE-RL-ReconfPrepTDD   CRITICALITY reject		TYPE DL-DPCH-InformationModify-ModifyItem-RL-ReconfPrepTDD		PRESENCE mandatory }
--}

DL-DPCH-InformationModify-ModifyItem-RL-ReconfPrepTDD ::= SEQUENCE {
	repetitionPeriod						RepetitionPeriod			OPTIONAL,
	repetitionLength						RepetitionLength			OPTIONAL,
	tdd-DPCHOffset							TDD-DPCHOffset				OPTIONAL,
	dL-Timeslot-InformationAddModify-ModifyList-RL-ReconfPrepTDD		DL-Timeslot-InformationModify-ModifyList-RL-ReconfPrepTDD			OPTIONAL,
--	iE-Extensions							ProtocolExtensionContainer { { DL-DPCH-InformationModify-ModifyItem-RL-ReconfPrepTDD-ExtIEs} }		OPTIONAL,
	iE-Extensions							ProtocolExtensionContainer OPTIONAL,
	...
}

--DL-DPCH-InformationModify-ModifyItem-RL-ReconfPrepTDD-ExtIEs  NBAP-PROTOCOL-EXTENSION ::= {
--	{ ID id-DL-Timeslot-LCR-InformationModify-ModifyList-RL-ReconfPrepTDD   CRITICALITY reject			EXTENSION		 DL-Timeslot-LCR-InformationModify-ModifyList-RL-ReconfPrepTDD		PRESENCE optional },
--	...
--}

--DL-Timeslot-InformationModify-ModifyList-RL-ReconfPrepTDD ::= SEQUENCE (SIZE (1..maxNrOfDLTSs)) OF DL-Timeslot-InformationModify-ModifyItem-RL-ReconfPrepTDD
DL-Timeslot-InformationModify-ModifyList-RL-ReconfPrepTDD ::= SEQUENCE (SIZE (1..15)) OF DL-Timeslot-InformationModify-ModifyItem-RL-ReconfPrepTDD

DL-Timeslot-InformationModify-ModifyItem-RL-ReconfPrepTDD	 ::= SEQUENCE {
	timeSlot								TimeSlot,
	midambleShiftAndBurstType				MidambleShiftAndBurstType			OPTIONAL,
	tFCI-Presence							TFCI-Presence			OPTIONAL,
	dL-Code-InformationModify-ModifyList-RL-ReconfPrepTDD				DL-Code-InformationModify-ModifyList-RL-ReconfPrepTDD			OPTIONAL,
--	iE-Extensions							ProtocolExtensionContainer { { DL-Timeslot-InformationModify-ModifyItem-RL-ReconfPrepTDD-ExtIEs} }		OPTIONAL,
	iE-Extensions							ProtocolExtensionContainer OPTIONAL,
	...
}

--DL-Timeslot-InformationModify-ModifyItem-RL-ReconfPrepTDD-ExtIEs NBAP-PROTOCOL-EXTENSION ::= {
--	{ ID id-Maximum-DL-Power-Modify-LCR-InformationModify-RL-ReconfPrepTDD	CRITICALITY ignore EXTENSION DL-Power		PRESENCE optional	}|
	-- Applicable to 1.28Mcps TDD only
--	{ ID id-Minimum-DL-Power-Modify-LCR-InformationModify-RL-ReconfPrepTDD	CRITICALITY ignore	EXTENSION DL-Power		PRESENCE optional	},
	-- Applicable to 1.28Mcps TDD only
--	...
--}
--DL-Code-InformationModify-ModifyList-RL-ReconfPrepTDD ::= SEQUENCE (SIZE (0..maxNrOfDPCHs)) OF DL-Code-InformationModify-ModifyItem-RL-ReconfPrepTDD
DL-Code-InformationModify-ModifyList-RL-ReconfPrepTDD ::= SEQUENCE (SIZE (0..240)) OF DL-Code-InformationModify-ModifyItem-RL-ReconfPrepTDD

DL-Code-InformationModify-ModifyItem-RL-ReconfPrepTDD	 ::= SEQUENCE {
	dPCH-ID									DPCH-ID,
	tdd-ChannelisationCode					TDD-ChannelisationCode		OPTIONAL,
--	iE-Extensions							ProtocolExtensionContainer { { DL-Code-InformationModify-ModifyItem-RL-ReconfPrepTDD-ExtIEs} }		OPTIONAL,
	iE-Extensions							ProtocolExtensionContainer OPTIONAL,
	...
}

--DL-Code-InformationModify-ModifyItem-RL-ReconfPrepTDD-ExtIEs NBAP-PROTOCOL-EXTENSION ::= {
--	...
--}

--DL-Timeslot-LCR-InformationModify-ModifyList-RL-ReconfPrepTDD ::= SEQUENCE (SIZE (1..maxNrOfDLTSLCRs)) OF DL-Timeslot-LCR-InformationModify-ModifyItem-RL-ReconfPrepTDD
DL-Timeslot-LCR-InformationModify-ModifyList-RL-ReconfPrepTDD ::= SEQUENCE (SIZE (1..240)) OF DL-Timeslot-LCR-InformationModify-ModifyItem-RL-ReconfPrepTDD

DL-Timeslot-LCR-InformationModify-ModifyItem-RL-ReconfPrepTDD	 ::= SEQUENCE {
	timeSlotLCR								TimeSlotLCR,
	midambleShiftLCR						MidambleShiftLCR		OPTIONAL,
	tFCI-Presence							TFCI-Presence			OPTIONAL,
	dL-Code-LCR-InformationModify-ModifyList-RL-ReconfPrepTDD				DL-Code-LCR-InformationModify-ModifyList-RL-ReconfPrepTDD			OPTIONAL,
--	iE-Extensions							ProtocolExtensionContainer { { DL-Timeslot-LCR-InformationModify-ModifyItem-RL-ReconfPrepTDD-ExtIEs} }		OPTIONAL,
	iE-Extensions							ProtocolExtensionContainer OPTIONAL,
	...
}

--DL-Timeslot-LCR-InformationModify-ModifyItem-RL-ReconfPrepTDD-ExtIEs NBAP-PROTOCOL-EXTENSION ::= {
--	...
--}
--DL-Code-LCR-InformationModify-ModifyList-RL-ReconfPrepTDD ::= SEQUENCE (SIZE (1..maxNrOfDPCHLCRs)) OF DL-Code-LCR-InformationModify-ModifyItem-RL-ReconfPrepTDD
DL-Code-LCR-InformationModify-ModifyList-RL-ReconfPrepTDD ::= SEQUENCE (SIZE (1..240)) OF DL-Code-LCR-InformationModify-ModifyItem-RL-ReconfPrepTDD

DL-Code-LCR-InformationModify-ModifyItem-RL-ReconfPrepTDD	 ::= SEQUENCE {
	dPCH-ID									DPCH-ID,
	tdd-ChannelisationCodeLCR				TDD-ChannelisationCodeLCR		OPTIONAL,
	iE-Extensions							ProtocolExtensionContainer OPTIONAL,
	...
}

--DL-Code-LCR-InformationModify-ModifyItem-RL-ReconfPrepTDD-ExtIEs NBAP-PROTOCOL-EXTENSION ::= {
--	{ ID id-DL-DPCH-TimeSlotFormat-LCR-ModifyItem-RL-ReconfPrepTDD	 CRITICALITY	reject	 EXTENSION TDD-DL-DPCH-TimeSlotFormat-LCR   PRESENCE  optional},
--	...
--}

--DL-DPCH-InformationModify-DeleteList-RL-ReconfPrepTDD ::= ProtocolIE-Single-Container {{ DL-DPCH-InformationModify-DeleteListIEs-RL-ReconfPrepTDD }}
DL-DPCH-InformationModify-DeleteList-RL-ReconfPrepTDD ::= ProtocolIE-Single-Container

--DL-DPCH-InformationModify-DeleteListIEs-RL-ReconfPrepTDD NBAP-PROTOCOL-IES ::= {
--	{ ID id-DL-DPCH-InformationModify-DeleteListIE-RL-ReconfPrepTDD   CRITICALITY reject		TYPE DL-DPCH-InformationModify-DeleteListIE-RL-ReconfPrepTDD		PRESENCE mandatory }
--}

--DL-DPCH-InformationModify-DeleteListIE-RL-ReconfPrepTDD ::= SEQUENCE (SIZE (1..maxNrOfDPCHs)) OF DL-DPCH-InformationModify-DeleteItem-RL-ReconfPrepTDD
DL-DPCH-InformationModify-DeleteListIE-RL-ReconfPrepTDD ::= SEQUENCE (SIZE (1..240)) OF DL-DPCH-InformationModify-DeleteItem-RL-ReconfPrepTDD

DL-DPCH-InformationModify-DeleteItem-RL-ReconfPrepTDD ::= SEQUENCE {
	dPCH-ID										DPCH-ID,
--	iE-Extensions								ProtocolExtensionContainer { { DL-DPCH-InformationModify-DeleteItem-RL-ReconfPrepTDD-ExtIEs} }		OPTIONAL,
	iE-Extensions								ProtocolExtensionContainer OPTIONAL,
	...
}

--DL-DPCH-InformationModify-DeleteItem-RL-ReconfPrepTDD-ExtIEs  NBAP-PROTOCOL-EXTENSION ::= {
--	...
--}

--DL-CCTrCH-InformationDeleteList-RL-ReconfPrepTDD ::= SEQUENCE (SIZE (1..maxNrOfCCTrCHs)) OF DL-CCTrCH-InformationDeleteItem-RL-ReconfPrepTDD
DL-CCTrCH-InformationDeleteList-RL-ReconfPrepTDD ::= SEQUENCE (SIZE (1..16)) OF DL-CCTrCH-InformationDeleteItem-RL-ReconfPrepTDD

DL-CCTrCH-InformationDeleteItem-RL-ReconfPrepTDD ::= SEQUENCE {
	cCTrCH-ID										CCTrCH-ID,
--	iE-Extensions									ProtocolExtensionContainer { { DL-CCTrCH-InformationDeleteItem-RL-ReconfPrepTDD-ExtIEs} }			OPTIONAL,
	iE-Extensions									ProtocolExtensionContainer OPTIONAL,
	...
}

--DL-CCTrCH-InformationDeleteItem-RL-ReconfPrepTDD-ExtIEs  NBAP-PROTOCOL-EXTENSION ::= {
--	...
--}

--DCH-DeleteList-RL-ReconfPrepTDD ::= SEQUENCE (SIZE (1..maxNrOfDCHs)) OF DCH-DeleteItem-RL-ReconfPrepTDD
DCH-DeleteList-RL-ReconfPrepTDD ::= SEQUENCE (SIZE (1..128)) OF DCH-DeleteItem-RL-ReconfPrepTDD

DCH-DeleteItem-RL-ReconfPrepTDD ::= SEQUENCE {
	dCH-ID										DCH-ID,
--	iE-Extensions								ProtocolExtensionContainer { { DCH-DeleteItem-RL-ReconfPrepTDD-ExtIEs} }		OPTIONAL,
	iE-Extensions								ProtocolExtensionContainer OPTIONAL,
	...
}

--DCH-DeleteItem-RL-ReconfPrepTDD-ExtIEs  NBAP-PROTOCOL-EXTENSION ::= {
--	...
--}

--DSCH-Information-ModifyList-RL-ReconfPrepTDD ::= SEQUENCE (SIZE (1..maxNrOfDSCHs)) OF DSCH-Information-ModifyItem-RL-ReconfPrepTDD
DSCH-Information-ModifyList-RL-ReconfPrepTDD ::= SEQUENCE (SIZE (1..32)) OF DSCH-Information-ModifyItem-RL-ReconfPrepTDD

DSCH-Information-ModifyItem-RL-ReconfPrepTDD ::= SEQUENCE {
	dSCH-ID										DSCH-ID,
	cCTrCH-ID									CCTrCH-ID				OPTIONAL,
	-- DL CCTrCH in which the DSCH is mapped
	transportFormatSet							TransportFormatSet		OPTIONAL,
	allocationRetentionPriority					AllocationRetentionPriority	OPTIONAL,
	frameHandlingPriority						FrameHandlingPriority	OPTIONAL,
	toAWS										ToAWS					OPTIONAL,
	toAWE										ToAWE					OPTIONAL,
	transportBearerRequestIndicator				TransportBearerRequestIndicator,
--	iE-Extensions								ProtocolExtensionContainer { { DSCH-Information-ModifyItem-RL-ReconfPrepTDD-ExtIEs} }		OPTIONAL,
	iE-Extensions								ProtocolExtensionContainer OPTIONAL,
	...
 }

--DSCH-Information-ModifyItem-RL-ReconfPrepTDD-ExtIEs  NBAP-PROTOCOL-EXTENSION ::= {
--	{ ID id-bindingID					CRITICALITY ignore	EXTENSION BindingID		PRESENCE 	optional	}|
	-- Shall be ignored if bearer establishment with ALCAP.
--	{ ID id-transportlayeraddress		CRITICALITY ignore	EXTENSION TransportLayerAddress	PRESENCE 	optional	},
	-- Shall be ignored if bearer establishment with ALCAP.
--	...
--}

--DSCH-Information-DeleteList-RL-ReconfPrepTDD ::= SEQUENCE (SIZE (1..maxNrOfDSCHs)) OF DSCH-Information-DeleteItem-RL-ReconfPrepTDD
DSCH-Information-DeleteList-RL-ReconfPrepTDD ::= SEQUENCE (SIZE (1..32)) OF DSCH-Information-DeleteItem-RL-ReconfPrepTDD

DSCH-Information-DeleteItem-RL-ReconfPrepTDD ::= SEQUENCE {
	dSCH-ID										DSCH-ID,
--	iE-Extensions								ProtocolExtensionContainer { { DSCH-Information-DeleteItem-RL-ReconfPrepTDD-ExtIEs} }		OPTIONAL,
	iE-Extensions								ProtocolExtensionContainer OPTIONAL,
	...
}

--DSCH-Information-DeleteItem-RL-ReconfPrepTDD-ExtIEs  NBAP-PROTOCOL-EXTENSION ::= {
--	...
--}

--USCH-Information-ModifyList-RL-ReconfPrepTDD ::= SEQUENCE (SIZE (1..maxNrOfUSCHs)) OF USCH-Information-ModifyItem-RL-ReconfPrepTDD
USCH-Information-ModifyList-RL-ReconfPrepTDD ::= SEQUENCE (SIZE (1..32)) OF USCH-Information-ModifyItem-RL-ReconfPrepTDD

USCH-Information-ModifyItem-RL-ReconfPrepTDD ::= SEQUENCE {
 	uSCH-ID										USCH-ID,
 	transportFormatSet							TransportFormatSet			OPTIONAL,
	allocationRetentionPriority					AllocationRetentionPriority	OPTIONAL,
	cCTrCH-ID									CCTrCH-ID					OPTIONAL,	-- UL CCTrCH in which the USCH is mapped
	transportBearerRequestIndicator				TransportBearerRequestIndicator,
--	iE-Extensions								ProtocolExtensionContainer { { USCH-Information-ModifyItem-RL-ReconfPrepTDD-ExtIEs} }		OPTIONAL,
	iE-Extensions								ProtocolExtensionContainer OPTIONAL,
	...
}

--USCH-Information-ModifyItem-RL-ReconfPrepTDD-ExtIEs  NBAP-PROTOCOL-EXTENSION ::= {
--	{ ID id-bindingID						CRITICALITY	ignore		EXTENSION BindingID			PRESENCE optional	}|
	-- Shall be ignored if bearer establishment with ALCAP.
--	{ ID id-transportlayeraddress			CRITICALITY	ignore		EXTENSION TransportLayerAddress	PRESENCE optional	}|
	-- Shall be ignored if bearer establishment with ALCAP.
--	{ ID id-TnlQos							CRITICALITY	ignore		EXTENSION	TnlQos		PRESENCE optional	},
--	...
--}

--USCH-Information-DeleteList-RL-ReconfPrepTDD ::= SEQUENCE (SIZE (1..maxNrOfUSCHs)) OF USCH-Information-DeleteItem-RL-ReconfPrepTDD
USCH-Information-DeleteList-RL-ReconfPrepTDD ::= SEQUENCE (SIZE (1..32)) OF USCH-Information-DeleteItem-RL-ReconfPrepTDD

USCH-Information-DeleteItem-RL-ReconfPrepTDD ::= SEQUENCE {
	uSCH-ID										USCH-ID,
--	iE-Extensions								ProtocolExtensionContainer { { USCH-Information-DeleteItem-RL-ReconfPrepTDD-ExtIEs} }		OPTIONAL,
	iE-Extensions								ProtocolExtensionContainer OPTIONAL,
	...

}

--USCH-Information-DeleteItem-RL-ReconfPrepTDD-ExtIEs  NBAP-PROTOCOL-EXTENSION ::= {
--	...
--}

--MultipleRL-Information-RL-ReconfPrepTDD ::= SEQUENCE (SIZE (1..maxNrOfRLs-1)) OF RL-Information-RL-ReconfPrepTDD
MultipleRL-Information-RL-ReconfPrepTDD ::= SEQUENCE (SIZE (1..15)) OF RL-Information-RL-ReconfPrepTDD
--Includes the 2nd through the max number of radio link information repetitions.

RL-Information-RL-ReconfPrepTDD ::= SEQUENCE {
	rL-ID										RL-ID,
	maxDL-Power									DL-Power			OPTIONAL,
	minDL-Power									DL-Power			OPTIONAL,
--	iE-Extensions								ProtocolExtensionContainer { { RL-Information-RL-ReconfPrepTDD-ExtIEs} }		OPTIONAL,
	iE-Extensions								ProtocolExtensionContainer OPTIONAL,
	...
}

--RL-Information-RL-ReconfPrepTDD-ExtIEs  NBAP-PROTOCOL-EXTENSION ::= {
--	{ ID id-InitDL-Power								CRITICALITY ignore	EXTENSION DL-Power				PRESENCE optional	}|
--	{ ID id-RL-Specific-DCH-Info						CRITICALITY ignore	EXTENSION RL-Specific-DCH-Info			PRESENCE optional	}|
--	{ ID id-UL-Synchronisation-Parameters-LCR			CRITICALITY ignore	EXTENSION UL-Synchronisation-Parameters-LCR	PRESENCE optional	}|
	-- Mandatory for 1.28Mcps TDD, Not Applicable to 3.84Mcps TDD
--	{ ID id-TimeslotISCP-LCR-InfoList-RL-ReconfPrepTDD	CRITICALITY ignore	EXTENSION DL-TimeslotISCPInfoLCR			PRESENCE optional	},
	-- Applicable to 1.28Mcps TDD only
--	...
--}


-- **************************************************************
--
-- RADIO LINK RECONFIGURATION READY
--
-- **************************************************************

--RadioLinkReconfigurationReady ::= SEQUENCE {
--	protocolIEs				ProtocolIE-Container	{{RadioLinkReconfigurationReady-IEs}},
--	protocolExtensions		ProtocolExtensionContainer	{{RadioLinkReconfigurationReady-Extensions}}		OPTIONAL,
--	...
--}
RadioLinkReconfigurationReady ::= SEQUENCE {
	protocolIEs				ProtocolIE-Container,
	protocolExtensions		ProtocolExtensionContainer OPTIONAL,
	...
}
--RadioLinkReconfigurationReady-IEs NBAP-PROTOCOL-IES ::= {
--	{ ID id-CRNC-CommunicationContextID					CRITICALITY ignore	TYPE CRNC-CommunicationContextID				PRESENCE mandatory }|
--	{ ID id-RL-InformationResponseList-RL-ReconfReady	CRITICALITY ignore	TYPE RL-InformationResponseList-RL-ReconfReady	PRESENCE optional }|
--	{ ID id-CriticalityDiagnostics						CRITICALITY ignore	TYPE CriticalityDiagnostics				PRESENCE optional },
--	...
--}

--RadioLinkReconfigurationReady-Extensions NBAP-PROTOCOL-EXTENSION ::= {
--	{ ID id-TargetCommunicationControlPortID	CRITICALITY ignore		EXTENSION CommunicationControlPortID		PRESENCE optional }|
--	{ ID id-HSDSCH-FDD-Information-Response		CRITICALITY ignore		EXTENSION HSDSCH-FDD-Information-Response		PRESENCE optional }|
	-- FDD only
--	{ ID id-HSDSCH-TDD-Information-Response		CRITICALITY ignore		EXTENSION HSDSCH-TDD-Information-Response		PRESENCE optional },
	-- TDD only
--	...
--}

--RL-InformationResponseList-RL-ReconfReady	 ::= SEQUENCE (SIZE (1..maxNrOfRLs)) OF ProtocolIE-Single-Container {{ RL-InformationResponseItemIE-RL-ReconfReady}}
RL-InformationResponseList-RL-ReconfReady	 ::= SEQUENCE (SIZE (1..15)) OF ProtocolIE-Single-Container

--RL-InformationResponseItemIE-RL-ReconfReady NBAP-PROTOCOL-IES ::= {
--	{ ID id-RL-InformationResponseItem-RL-ReconfReady	CRITICALITY ignore	TYPE RL-InformationResponseItem-RL-ReconfReady	PRESENCE mandatory }
--}

RL-InformationResponseItem-RL-ReconfReady ::= SEQUENCE {
	rL-ID											RL-ID,
	dCH-InformationResponseList-RL-ReconfReady		DCH-InformationResponseList-RL-ReconfReady	OPTIONAL,
	dSCH-InformationResponseList-RL-ReconfReady		DSCH-InformationResponseList-RL-ReconfReady	OPTIONAL, -- TDD only
	uSCH-InformationResponseList-RL-ReconfReady		USCH-InformationResponseList-RL-ReconfReady	OPTIONAL, -- TDD only
	not-Used-tFCI2-BearerInformationResponse		NULL										OPTIONAL,
--	iE-Extensions									ProtocolExtensionContainer { { RL-InformationResponseItem-RL-ReconfReady-ExtIEs} }		OPTIONAL,
	iE-Extensions									ProtocolExtensionContainer OPTIONAL,
	...
}

--RL-InformationResponseItem-RL-ReconfReady-ExtIEs  NBAP-PROTOCOL-EXTENSION ::= {
--	{ ID id-DL-PowerBalancing-UpdatedIndicator			CRITICALITY ignore	EXTENSION DL-PowerBalancing-UpdatedIndicator				PRESENCE optional }|
--	{ ID id-E-DCH-RL-Set-ID								CRITICALITY ignore	EXTENSION RL-Set-ID							PRESENCE optional }|
--	{ ID id-E-DCH-FDD-DL-Control-Channel-Information	CRITICALITY ignore	EXTENSION E-DCH-FDD-DL-Control-Channel-Information		PRESENCE optional }|
--	{ ID id-E-DCH-FDD-Information-Response				CRITICALITY ignore	EXTENSION E-DCH-FDD-Information-Response				PRESENCE optional },
--	...
--}

--DCH-InformationResponseList-RL-ReconfReady::= ProtocolIE-Single-Container {{ DCH-InformationResponseListIEs-RL-ReconfReady }}
DCH-InformationResponseList-RL-ReconfReady::= ProtocolIE-Single-Container

--DCH-InformationResponseListIEs-RL-ReconfReady NBAP-PROTOCOL-IES ::= {
--	{ ID id-DCH-InformationResponse   CRITICALITY ignore	TYPE DCH-InformationResponse	PRESENCE mandatory }
--}

--DSCH-InformationResponseList-RL-ReconfReady::= ProtocolIE-Single-Container {{ DSCH-InformationResponseListIEs-RL-ReconfReady }}
DSCH-InformationResponseList-RL-ReconfReady::= ProtocolIE-Single-Container

--DSCH-InformationResponseListIEs-RL-ReconfReady NBAP-PROTOCOL-IES ::= {
--	{ ID id-DSCH-InformationResponse   CRITICALITY ignore	TYPE DSCH-InformationResponse	PRESENCE mandatory }
--}

--USCH-InformationResponseList-RL-ReconfReady::= ProtocolIE-Single-Container {{ USCH-InformationResponseListIEs-RL-ReconfReady }}
USCH-InformationResponseList-RL-ReconfReady::= ProtocolIE-Single-Container

--USCH-InformationResponseListIEs-RL-ReconfReady NBAP-PROTOCOL-IES ::= {
--	{ ID id-USCH-InformationResponse   CRITICALITY ignore	TYPE USCH-InformationResponse		PRESENCE mandatory }
--}

-- **************************************************************
--
-- RADIO LINK RECONFIGURATION FAILURE
--
-- **************************************************************

--RadioLinkReconfigurationFailure ::= SEQUENCE {
--	protocolIEs				ProtocolIE-Container	{{RadioLinkReconfigurationFailure-IEs}},
--	protocolExtensions		ProtocolExtensionContainer	{{RadioLinkReconfigurationFailure-Extensions}}		OPTIONAL,
--	...
--}

RadioLinkReconfigurationFailure ::= SEQUENCE {
	protocolIEs				ProtocolIE-Container,
	protocolExtensions		ProtocolExtensionContainer OPTIONAL,
	...
}
--RadioLinkReconfigurationFailure-IEs NBAP-PROTOCOL-IES ::= {
--	{ ID id-CRNC-CommunicationContextID			CRITICALITY ignore	TYPE CRNC-CommunicationContextID		PRESENCE mandatory } |
--	{ ID id-CauseLevel-RL-ReconfFailure			CRITICALITY ignore	TYPE CauseLevel-RL-ReconfFailure		PRESENCE mandatory } |
--	{ ID id-CriticalityDiagnostics				CRITICALITY ignore	TYPE CriticalityDiagnostics			PRESENCE optional },
--	...
--}

--RadioLinkReconfigurationFailure-Extensions NBAP-PROTOCOL-EXTENSION ::= {
--	...
--}

CauseLevel-RL-ReconfFailure ::= CHOICE {
	generalCause		GeneralCauseList-RL-ReconfFailure,
	rLSpecificCause		RLSpecificCauseList-RL-ReconfFailure,
	...
}

GeneralCauseList-RL-ReconfFailure ::= SEQUENCE {
	cause										Cause,
--	iE-Extensions								ProtocolExtensionContainer { { GeneralCauseItem-RL-ReconfFailure-ExtIEs} }			OPTIONAL,
	iE-Extensions								ProtocolExtensionContainer OPTIONAL,
	...
 }

--GeneralCauseItem-RL-ReconfFailure-ExtIEs  NBAP-PROTOCOL-EXTENSION ::= {
--	...
--}

RLSpecificCauseList-RL-ReconfFailure ::= SEQUENCE {
	rL-ReconfigurationFailureList-RL-ReconfFailure		RL-ReconfigurationFailureList-RL-ReconfFailure		OPTIONAL,
--	iE-Extensions										ProtocolExtensionContainer { { RLSpecificCauseItem-RL-ReconfFailure-ExtIEs} }			OPTIONAL,
	iE-Extensions										ProtocolExtensionContainer OPTIONAL,
	...
 }

--RLSpecificCauseItem-RL-ReconfFailure-ExtIEs  NBAP-PROTOCOL-EXTENSION ::= {
--	...
--}

--RL-ReconfigurationFailureList-RL-ReconfFailure ::= SEQUENCE (SIZE (1..maxNrOfRLs)) OF ProtocolIE-Single-Container {{ RL-ReconfigurationFailureItemIE-RL-ReconfFailure}}
RL-ReconfigurationFailureList-RL-ReconfFailure ::= SEQUENCE (SIZE (1..15)) OF ProtocolIE-Single-Container

--RL-ReconfigurationFailureItemIE-RL-ReconfFailure NBAP-PROTOCOL-IES ::= {
--	{ ID id-RL-ReconfigurationFailureItem-RL-ReconfFailure	CRITICALITY ignore	TYPE RL-ReconfigurationFailureItem-RL-ReconfFailure	PRESENCE mandatory}
--}

RL-ReconfigurationFailureItem-RL-ReconfFailure ::= SEQUENCE {
 	rL-ID										RL-ID,
	cause										Cause,
--	iE-Extensions								ProtocolExtensionContainer { { RL-ReconfigurationFailureItem-RL-ReconfFailure-ExtIEs} }			OPTIONAL,
	iE-Extensions								ProtocolExtensionContainer OPTIONAL,
	...
 }

--RL-ReconfigurationFailureItem-RL-ReconfFailure-ExtIEs  NBAP-PROTOCOL-EXTENSION ::= {
--	...
--}

-- **************************************************************
--
-- RADIO LINK RECONFIGURATION COMMIT
--
-- **************************************************************

--RadioLinkReconfigurationCommit ::= SEQUENCE {
--	protocolIEs				ProtocolIE-Container	{{RadioLinkReconfigurationCommit-IEs}},
--	protocolExtensions		ProtocolExtensionContainer	{{RadioLinkReconfigurationCommit-Extensions}}		OPTIONAL,
--	...
--}
RadioLinkReconfigurationCommit ::= SEQUENCE {
	protocolIEs				ProtocolIE-Container,
	protocolExtensions		ProtocolExtensionContainer OPTIONAL,
	...
}
--RadioLinkReconfigurationCommit-IEs NBAP-PROTOCOL-IES ::= {
--	{ ID	id-NodeB-CommunicationContextID			CRITICALITY ignore	TYPE NodeB-CommunicationContextID	PRESENCE mandatory } |
--	{ ID	id-CFN									CRITICALITY ignore	TYPE CFN					PRESENCE mandatory }|
--	{ ID 	id-Active-Pattern-Sequence-Information	CRITICALITY ignore	TYPE Active-Pattern-Sequence-Information	PRESENCE optional },
	-- FDD only
--	...
--}

--RadioLinkReconfigurationCommit-Extensions NBAP-PROTOCOL-EXTENSION ::= {
--	...
--}

-- **************************************************************
--
-- RADIO LINK RECONFIGURATION CANCEL
--
-- **************************************************************

--RadioLinkReconfigurationCancel ::= SEQUENCE {
--	protocolIEs				ProtocolIE-Container	{{RadioLinkReconfigurationCancel-IEs}},
--	protocolExtensions		ProtocolExtensionContainer	{{RadioLinkReconfigurationCancel-Extensions}}		OPTIONAL,
--	...
--}
RadioLinkReconfigurationCancel ::= SEQUENCE {
	protocolIEs				ProtocolIE-Container,
	protocolExtensions		ProtocolExtensionContainer OPTIONAL,
	...
}
--RadioLinkReconfigurationCancel-IEs NBAP-PROTOCOL-IES ::= {
--	{ ID	id-NodeB-CommunicationContextID			CRITICALITY 	ignore		TYPE	NodeB-CommunicationContextID			PRESENCE	mandatory	},
--	...
--}

--RadioLinkReconfigurationCancel-Extensions NBAP-PROTOCOL-EXTENSION ::= {
--	...
--}

-- **************************************************************
--
-- RADIO LINK RECONFIGURATION REQUEST FDD
--
-- **************************************************************
--RadioLinkReconfigurationRequestFDD ::= SEQUENCE {
--	protocolIEs				ProtocolIE-Container	{{RadioLinkReconfigurationRequestFDD-IEs}},
--	protocolExtensions		ProtocolExtensionContainer	{{RadioLinkReconfigurationRequestFDD-Extensions}}		OPTIONAL,
--	...
--}
RadioLinkReconfigurationRequestFDD ::= SEQUENCE {
	protocolIEs				ProtocolIE-Container,
	protocolExtensions		ProtocolExtensionContainer	OPTIONAL,
	...
}

--RadioLinkReconfigurationRequestFDD-IEs NBAP-PROTOCOL-IES ::= {
--	{ ID id-NodeB-CommunicationContextID					CRITICALITY reject	TYPE NodeB-CommunicationContextID					PRESENCE mandatory }|
--	{ ID id-UL-DPCH-Information-RL-ReconfRqstFDD			CRITICALITY reject	TYPE UL-DPCH-Information-RL-ReconfRqstFDD			PRESENCE optional }|
--	{ ID id-DL-DPCH-Information-RL-ReconfRqstFDD			CRITICALITY reject	TYPE DL-DPCH-Information-RL-ReconfRqstFDD			PRESENCE optional }|
--	{ ID id-FDD-DCHs-to-Modify								CRITICALITY reject	TYPE FDD-DCHs-to-Modify					PRESENCE optional }|
--	{ ID id-DCHs-to-Add-FDD									CRITICALITY reject	TYPE DCH-FDD-Information					PRESENCE optional }|
--	{ ID id-DCH-DeleteList-RL-ReconfRqstFDD					CRITICALITY reject	TYPE DCH-DeleteList-RL-ReconfRqstFDD				PRESENCE optional }|
--	{ ID id-RL-InformationList-RL-ReconfRqstFDD				CRITICALITY reject	TYPE RL-InformationList-RL-ReconfRqstFDD			PRESENCE optional }|
--	{ ID id-Transmission-Gap-Pattern-Sequence-Information	CRITICALITY reject	TYPE Transmission-Gap-Pattern-Sequence-Information	 PRESENCE optional },
--	...
--}

--RadioLinkReconfigurationRequestFDD-Extensions NBAP-PROTOCOL-EXTENSION ::= {
--	{ ID id-SignallingBearerRequestIndicator			CRITICALITY reject	EXTENSION SignallingBearerRequestIndicator			PRESENCE optional }|
--	{ ID id-HSDSCH-FDD-Information						CRITICALITY reject	EXTENSION HSDSCH-FDD-Information				PRESENCE optional }|
--	{ ID id-HSDSCH-Information-to-Modify-Unsynchronised	CRITICALITY reject	EXTENSION HSDSCH-Information-to-Modify-Unsynchronised		PRESENCE optional }|
--	{ ID id-HSDSCH-MACdFlows-to-Add						CRITICALITY reject	EXTENSION HSDSCH-MACdFlows-Information				PRESENCE optional }|
--	{ ID id-HSDSCH-MACdFlows-to-Delete					CRITICALITY reject	EXTENSION HSDSCH-MACdFlows-to-Delete				PRESENCE optional }|
--	{ ID id-HSDSCH-RNTI									CRITICALITY reject	EXTENSION HSDSCH-RNTI				PRESENCE conditional }|
	-- The IE shall be present if HS-PDSCH RL ID IE is present.
--	{ ID id-HSPDSCH-RL-ID								CRITICALITY reject	EXTENSION RL-ID						PRESENCE optional }|
--	{ ID id-E-DPCH-Information-RL-ReconfRqstFDD			CRITICALITY reject	EXTENSION E-DPCH-Information-RL-ReconfRqstFDD		PRESENCE optional }|
--	{ ID id-E-DCH-FDD-Information						CRITICALITY reject	EXTENSION E-DCH-FDD-Information				PRESENCE optional }|
--	{ ID id-E-DCH-FDD-Information-to-Modify				CRITICALITY reject	EXTENSION E-DCH-FDD-Information-to-Modify			PRESENCE optional }|
--	{ ID id-E-DCH-MACdFlows-to-Add						CRITICALITY reject	EXTENSION E-DCH-MACdFlows-Information				PRESENCE optional }|
--	{ ID id-E-DCH-MACdFlows-to-Delete					CRITICALITY reject	EXTENSION E-DCH-MACdFlows-to-Delete				PRESENCE optional }|
--	{ ID id-Serving-E-DCH-RL-ID							CRITICALITY reject	EXTENSION Serving-E-DCH-RL-ID				PRESENCE optional },
--	...
--}


UL-DPCH-Information-RL-ReconfRqstFDD ::= SEQUENCE {
	ul-TFCS											TFCS			OPTIONAL,
--	iE-Extensions									ProtocolExtensionContainer { { UL-DPCH-Information-RL-ReconfRqstFDD-ExtIEs} }		OPTIONAL,
	iE-Extensions									ProtocolExtensionContainer OPTIONAL,
	...
}

--UL-DPCH-Information-RL-ReconfRqstFDD-ExtIEs NBAP-PROTOCOL-EXTENSION ::= {
--	{ ID id-UL-DPDCH-Indicator-For-E-DCH-Operation	CRITICALITY reject	EXTENSION UL-DPDCH-Indicator-For-E-DCH-Operation			PRESENCE conditional },
	-- The IE shall be present if E-DPCH Information IE is present
--	...
--}

DL-DPCH-Information-RL-ReconfRqstFDD ::= SEQUENCE {
	dl-TFCS											TFCS									OPTIONAL,
 	tFCI-SignallingMode								TFCI-SignallingMode						OPTIONAL,
	limitedPowerIncrease							LimitedPowerIncrease					OPTIONAL,
--	iE-Extensions									ProtocolExtensionContainer { { DL-DPCH-Information-RL-ReconfRqstFDD-ExtIEs} }		OPTIONAL,
	iE-Extensions									ProtocolExtensionContainer OPTIONAL,
	...
 }

--DL-DPCH-Information-RL-ReconfRqstFDD-ExtIEs NBAP-PROTOCOL-EXTENSION ::= {
--	...
--}

--DCH-DeleteList-RL-ReconfRqstFDD ::= SEQUENCE (SIZE (1..maxNrOfDCHs)) OF DCH-DeleteItem-RL-ReconfRqstFDD
DCH-DeleteList-RL-ReconfRqstFDD ::= SEQUENCE (SIZE (1..128)) OF DCH-DeleteItem-RL-ReconfRqstFDD

DCH-DeleteItem-RL-ReconfRqstFDD ::= SEQUENCE {
	dCH-ID											DCH-ID,
--	iE-Extensions									ProtocolExtensionContainer { { DCH-DeleteItem-RL-ReconfRqstFDD-ExtIEs} }			OPTIONAL,
	iE-Extensions									ProtocolExtensionContainer OPTIONAL,
	...

}

--DCH-DeleteItem-RL-ReconfRqstFDD-ExtIEs  NBAP-PROTOCOL-EXTENSION ::= {
--	...
--}

--RL-InformationList-RL-ReconfRqstFDD ::= SEQUENCE (SIZE (1..maxNrOfRLs)) OF ProtocolIE-Single-Container {{ RL-InformationItemIE-RL-ReconfRqstFDD}}
RL-InformationList-RL-ReconfRqstFDD ::= SEQUENCE (SIZE (1..16)) OF ProtocolIE-Single-Container

--RL-InformationItemIE-RL-ReconfRqstFDD NBAP-PROTOCOL-IES ::= {
--	{ ID	id-RL-InformationItem-RL-ReconfRqstFDD				CRITICALITY		reject			TYPE	RL-InformationItem-RL-ReconfRqstFDD			PRESENCE	mandatory}
--}

RL-InformationItem-RL-ReconfRqstFDD ::= SEQUENCE {
	rL-ID										RL-ID,
	maxDL-Power									DL-Power		OPTIONAL,
	minDL-Power									DL-Power		OPTIONAL,
	dl-CodeInformation							FDD-DL-CodeInformation		OPTIONAL,
-- The IE shall be present if the Transmission Gap Pattern Sequence Information IE is included and the indicated Downlink Compressed Mode method for at least one of the included Transmission Gap Pattern Sequence is set to "SF/2".
--	iE-Extensions								ProtocolExtensionContainer { { RL-InformationItem-RL-ReconfRqstFDD-ExtIEs} }			OPTIONAL,
	iE-Extensions								ProtocolExtensionContainer OPTIONAL,
	...
}

--RL-InformationItem-RL-ReconfRqstFDD-ExtIEs  NBAP-PROTOCOL-EXTENSION ::= {
--	{ ID id-DLReferencePower			CRITICALITY ignore		EXTENSION DL-Power							PRESENCE optional }|
--	{ ID id-RL-Specific-DCH-Info		CRITICALITY ignore		EXTENSION RL-Specific-DCH-Info				PRESENCE optional }|
--	{ ID id-E-DCH-RL-Indication			CRITICALITY reject		EXTENSION E-DCH-RL-Indication				PRESENCE optional }|
--	{ ID id-RL-Specific-E-DCH-Info		CRITICALITY ignore	EXTENSION RL-Specific-E-DCH-Info					PRESENCE optional },
--	...
--}

E-DPCH-Information-RL-ReconfRqstFDD ::= SEQUENCE {
	e-TFCS-Information					E-TFCS-Information														OPTIONAL,
	e-DPCCH-PO						E-DPCCH-PO																					OPTIONAL,
--	iE-Extensions					ProtocolExtensionContainer { { E-DPCH-Information-RL-ReconfRqstFDD-ExtIEs} }		OPTIONAL,
	iE-Extensions					ProtocolExtensionContainer OPTIONAL,
	...
}

--E-DPCH-Information-RL-ReconfRqstFDD-ExtIEs NBAP-PROTOCOL-EXTENSION ::= {
--	...
--}

-- **************************************************************
--
-- RADIO LINK RECONFIGURATION REQUEST TDD
--
-- **************************************************************

--RadioLinkReconfigurationRequestTDD ::= SEQUENCE {
--	protocolIEs				ProtocolIE-Container	{{RadioLinkReconfigurationRequestTDD-IEs}},
--	protocolExtensions		ProtocolExtensionContainer	{{RadioLinkReconfigurationRequestTDD-Extensions}}		OPTIONAL,
--	...
--}
RadioLinkReconfigurationRequestTDD ::= SEQUENCE {
	protocolIEs				ProtocolIE-Container,
	protocolExtensions		ProtocolExtensionContainer OPTIONAL,
	...
}

--RadioLinkReconfigurationRequestTDD-IEs NBAP-PROTOCOL-IES ::= {
--	{ ID id-NodeB-CommunicationContextID						CRITICALITY reject	TYPE NodeB-CommunicationContextID				PRESENCE mandatory }|
--	{ ID id-UL-CCTrCH-InformationModifyList-RL-ReconfRqstTDD	CRITICALITY notify	TYPE UL-CCTrCH-InformationModifyList-RL-ReconfRqstTDD		PRESENCE optional } |
--	{ ID id-UL-CCTrCH-InformationDeleteList-RL-ReconfRqstTDD	CRITICALITY notify	TYPE UL-CCTrCH-InformationDeleteList-RL-ReconfRqstTDD		PRESENCE optional } |
--	{ ID id-DL-CCTrCH-InformationModifyList-RL-ReconfRqstTDD	CRITICALITY notify	TYPE DL-CCTrCH-InformationModifyList-RL-ReconfRqstTDD		PRESENCE optional } |
--	{ ID id-DL-CCTrCH-InformationDeleteList-RL-ReconfRqstTDD	CRITICALITY notify	TYPE DL-CCTrCH-InformationDeleteList-RL-ReconfRqstTDD		PRESENCE optional } |
--	{ ID id-TDD-DCHs-to-Modify									CRITICALITY reject	TYPE TDD-DCHs-to-Modify					PRESENCE optional }|
--	{ ID	id-DCHs-to-Add-TDD									CRITICALITY reject	TYPE DCH-TDD-Information					PRESENCE optional }|
--	{ ID id-DCH-DeleteList-RL-ReconfRqstTDD						CRITICALITY reject	TYPE DCH-DeleteList-RL-ReconfRqstTDD			PRESENCE optional }|
--	{ ID id-RL-Information-RL-ReconfRqstTDD						CRITICALITY reject	TYPE RL-Information-RL-ReconfRqstTDD			PRESENCE optional },
-- This RL-Information-RL-ReconfRqstTDD is the first RL information repetition in the RL-Information List. Repetition 2 and on, should be defined in Multiple-RL-Information-RL-ReconfRqstTDD,
--	...
--}

--RadioLinkReconfigurationRequestTDD-Extensions NBAP-PROTOCOL-EXTENSION ::= {
--	{ ID id-SignallingBearerRequestIndicator			CRITICALITY reject	EXTENSION SignallingBearerRequestIndicator	PRESENCE optional }|
--	{ ID id-multiple-RL-Information-RL-ReconfRqstTDD				CRITICALITY reject	EXTENSION Multiple-RL-Information-RL-ReconfRqstTDD		PRESENCE optional }|
--Includes the 2nd through the max number of radio link information repetitions.
--	{ ID id-HSDSCH-TDD-Information						CRITICALITY reject	EXTENSION HSDSCH-TDD-Information			PRESENCE optional }|
--	{ ID id-HSDSCH-Information-to-Modify-Unsynchronised	CRITICALITY reject	EXTENSION HSDSCH-Information-to-Modify-Unsynchronised		PRESENCE optional }|
--	{ ID id-HSDSCH-MACdFlows-to-Add						CRITICALITY reject	EXTENSION HSDSCH-MACdFlows-Information			PRESENCE optional }|
--	{ ID id-HSDSCH-MACdFlows-to-Delete					CRITICALITY reject	EXTENSION HSDSCH-MACdFlows-to-Delete			PRESENCE optional }|
--	{ ID id-HSDSCH-RNTI									CRITICALITY reject	EXTENSION HSDSCH-RNTI			PRESENCE conditional }|
	-- The IE shall be present if HS-PDSCH RL ID IE is present.
--	{ ID id-HSPDSCH-RL-ID								CRITICALITY reject	EXTENSION RL-ID					PRESENCE optional },
--	...
--}

--UL-CCTrCH-InformationModifyList-RL-ReconfRqstTDD ::= SEQUENCE (SIZE (1..maxNrOfCCTrCHs)) OF ProtocolIE-Single-Container {{ UL-CCTrCH-InformationModifyItemIE-RL-ReconfRqstTDD}}
UL-CCTrCH-InformationModifyList-RL-ReconfRqstTDD ::= SEQUENCE (SIZE (1..16)) OF ProtocolIE-Single-Container

--UL-CCTrCH-InformationModifyItemIE-RL-ReconfRqstTDD NBAP-PROTOCOL-IES ::= {
--	{ ID	id-UL-CCTrCH-InformationModifyItem-RL-ReconfRqstTDD	CRITICALITY notify	TYPE UL-CCTrCH-InformationModifyItem-RL-ReconfRqstTDD		PRESENCE mandatory}
--}

UL-CCTrCH-InformationModifyItem-RL-ReconfRqstTDD ::= SEQUENCE {
	cCTrCH-ID										CCTrCH-ID,
	tFCS											TFCS			OPTIONAL,
	punctureLimit									PunctureLimit	OPTIONAL,
--	iE-Extensions									ProtocolExtensionContainer { { UL-CCTrCH-InformationModifyItem-RL-ReconfRqstTDD-ExtIEs} }			OPTIONAL,
	iE-Extensions									ProtocolExtensionContainer OPTIONAL,
	...
}

--UL-CCTrCH-InformationModifyItem-RL-ReconfRqstTDD-ExtIEs  NBAP-PROTOCOL-EXTENSION ::= {
--{ ID id-UL-SIRTarget        CRITICALITY reject      EXTENSION       UL-SIR      PRESENCE	optional   },
    -- Applicable to 1.28Mcps TDD only
--	...
--}

--UL-CCTrCH-InformationDeleteList-RL-ReconfRqstTDD ::= SEQUENCE (SIZE (1..maxNrOfCCTrCHs)) OF ProtocolIE-Single-Container {{ UL-CCTrCH-InformationDeleteItemIE-RL-ReconfRqstTDD}}
UL-CCTrCH-InformationDeleteList-RL-ReconfRqstTDD ::= SEQUENCE (SIZE (1..16)) OF ProtocolIE-Single-Container

--UL-CCTrCH-InformationDeleteItemIE-RL-ReconfRqstTDD NBAP-PROTOCOL-IES ::= {
--	{ ID	id-UL-CCTrCH-InformationDeleteItem-RL-ReconfRqstTDD			CRITICALITY		notify			TYPE 	UL-CCTrCH-InformationDeleteItem-RL-ReconfRqstTDD		PRESENCE	mandatory}
--}

UL-CCTrCH-InformationDeleteItem-RL-ReconfRqstTDD ::= SEQUENCE {
	cCTrCH-ID										CCTrCH-ID,
--	iE-Extensions									ProtocolExtensionContainer { { UL-CCTrCH-InformationDeleteItem-RL-ReconfRqstTDD-ExtIEs} }			OPTIONAL,
	iE-Extensions									ProtocolExtensionContainer OPTIONAL,
	...
}

--UL-CCTrCH-InformationDeleteItem-RL-ReconfRqstTDD-ExtIEs  NBAP-PROTOCOL-EXTENSION ::= {
--	...
--}

--DL-CCTrCH-InformationModifyList-RL-ReconfRqstTDD ::= SEQUENCE (SIZE (1..maxNrOfCCTrCHs)) OF ProtocolIE-Single-Container {{ DL-CCTrCH-InformationModifyItemIE-RL-ReconfRqstTDD}}
DL-CCTrCH-InformationModifyList-RL-ReconfRqstTDD ::= SEQUENCE (SIZE (1..16)) OF ProtocolIE-Single-Container

--DL-CCTrCH-InformationModifyItemIE-RL-ReconfRqstTDD NBAP-PROTOCOL-IES ::= {
--	{ ID	id-DL-CCTrCH-InformationModifyItem-RL-ReconfRqstTDD			CRITICALITY		notify			TYPE 	DL-CCTrCH-InformationModifyItem-RL-ReconfRqstTDD		PRESENCE	mandatory}
--}

DL-CCTrCH-InformationModifyItem-RL-ReconfRqstTDD ::= SEQUENCE {
	cCTrCH-ID										CCTrCH-ID,
	tFCS											TFCS			OPTIONAL,
	punctureLimit									PunctureLimit	OPTIONAL,
--	iE-Extensions									ProtocolExtensionContainer { { DL-CCTrCH-InformationModifyItem-RL-ReconfRqstTDD-ExtIEs} }			OPTIONAL,
	iE-Extensions									ProtocolExtensionContainer OPTIONAL,
	...
}

--DL-CCTrCH-InformationModifyItem-RL-ReconfRqstTDD-ExtIEs  NBAP-PROTOCOL-EXTENSION ::= {
--	{ ID id-DL-DPCH-LCR-InformationModify-ModifyList-RL-ReconfRqstTDD	CRITICALITY ignore	EXTENSION  DL-DPCH-LCR-InformationModify-ModifyList-RL-ReconfRqstTDD		PRESENCE optional }|
	-- Applicable to 1.28Mcps TDD only
-- This DPCH LCR Information is the for the first RL repetition, DPCH LCR information for RL repetitions 2 and on, should be defined in MultipleRL-DL-CCTrCH-InformationModifyList-RL-ReconfRqstTDD.
--	{ ID id-CCTrCH-Maximum-DL-Power-InformationModify-RL-ReconfRqstTDD	CRITICALITY ignore	EXTENSION DL-Power		PRESENCE optional	}|
-- This power Information is the for the first RL repetition, power information for RL repetitions 2 and on, should be defined in MultipleRL-DL-CCTrCH-InformationModifyList-RL-ReconfRqstTDD.
--	{ ID id-CCTrCH-Minimum-DL-Power-InformationModify-RL-ReconfRqstTDD	CRITICALITY ignore	EXTENSION DL-Power		PRESENCE optional	}|
-- This power Information is the for the first RL repetition, power information for RL repetitions 2 and on, should be defined in MultipleRL-DL-CCTrCH-InformationModifyList-RL-ReconfRqstTDD.
--	{ ID id-RL-ID														CRITICALITY ignore	EXTENSION	RL-ID		PRESENCE optional	}|
-- This is the RL ID for the first RL repetition.
--	{ ID id-multipleRL-dl-CCTrCH-InformationModifyList-RL-ReconfRqstTDD	CRITICALITY reject	EXTENSION	MultipleRL-DL-CCTrCH-InformationModifyList-RL-ReconfRqstTDD	PRESENCE optional	},
-- This CCTrCH Information is the for the 2nd and beyond RL repetitions.
--	...
--}

--MultipleRL-DL-CCTrCH-InformationModifyList-RL-ReconfRqstTDD ::= SEQUENCE (SIZE (1..maxNrOfRLs-1)) OF  MultipleRL-DL-CCTrCH-InformationModifyListIE-RL-ReconfRqstTDD
MultipleRL-DL-CCTrCH-InformationModifyList-RL-ReconfRqstTDD ::= SEQUENCE (SIZE (1..15)) OF  MultipleRL-DL-CCTrCH-InformationModifyListIE-RL-ReconfRqstTDD
--Includes the 2nd through the max number of radio link information repetitions.

MultipleRL-DL-CCTrCH-InformationModifyListIE-RL-ReconfRqstTDD ::= SEQUENCE {
	dl-DPCH-LCR-InformationModifyList								DL-DPCH-LCR-InformationModify-ModifyList-RL-ReconfRqstTDD	OPTIONAL,
	cCTrCH-Maximum-DL-Power-InformationModify-RL-ReconfRqstTDD		DL-Power										OPTIONAL,
	cCTrCH-Minimum-DL-Power-InformationModify-RL-ReconfRqstTDD		DL-Power										OPTIONAL,
	rL-ID															RL-ID											OPTIONAL,
...
}


DL-DPCH-LCR-InformationModify-ModifyList-RL-ReconfRqstTDD ::= SEQUENCE {	
	dL-Timeslot-LCR-InformationModify-ModifyList-RL-ReconfRqstTDD		DL-Timeslot-LCR-InformationModify-ModifyList-RL-ReconfRqstTDD		OPTIONAL,
--	iE-Extensions							ProtocolExtensionContainer { { DL-DPCH-LCR-InformationModify-ModifyList-RL-ReconfRqstTDD-ExtIEs} }		OPTIONAL,
	iE-Extensions							ProtocolExtensionContainer OPTIONAL,
	...
}

--DL-DPCH-LCR-InformationModify-ModifyList-RL-ReconfRqstTDD-ExtIEs  NBAP-PROTOCOL-EXTENSION ::= {
--	...
--}

--DL-Timeslot-LCR-InformationModify-ModifyList-RL-ReconfRqstTDD	::= SEQUENCE (SIZE (1..maxNrOfDLTSLCRs)) OF DL-Timeslot-LCR-InformationModify-ModifyItem-RL-ReconfRqstTDD	
DL-Timeslot-LCR-InformationModify-ModifyList-RL-ReconfRqstTDD	::= SEQUENCE (SIZE (1..6)) OF DL-Timeslot-LCR-InformationModify-ModifyItem-RL-ReconfRqstTDD	

DL-Timeslot-LCR-InformationModify-ModifyItem-RL-ReconfRqstTDD	 ::= SEQUENCE {
	timeSlotLCR								TimeSlotLCR,
	maxPowerLCR								DL-Power	OPTIONAL,
	minPowerLCR								DL-Power	OPTIONAL,
--	iE-Extensions							ProtocolExtensionContainer { { DL-Timeslot-LCR-InformationModify-ModifyItem-RL-ReconfRqstTDD-ExtIEs} }		OPTIONAL,
	iE-Extensions							ProtocolExtensionContainer OPTIONAL,
	...
}

--DL-Timeslot-LCR-InformationModify-ModifyItem-RL-ReconfRqstTDD-ExtIEs  NBAP-PROTOCOL-EXTENSION ::= {
--	...
--}

--DL-CCTrCH-InformationDeleteList-RL-ReconfRqstTDD ::= SEQUENCE (SIZE (1..maxNrOfCCTrCHs)) OF ProtocolIE-Single-Container {{ DL-CCTrCH-InformationDeleteItemIE-RL-ReconfRqstTDD}}
DL-CCTrCH-InformationDeleteList-RL-ReconfRqstTDD ::= SEQUENCE (SIZE (1..16)) OF ProtocolIE-Single-Container

--DL-CCTrCH-InformationDeleteItemIE-RL-ReconfRqstTDD NBAP-PROTOCOL-IES ::= {
--	{ ID	id-DL-CCTrCH-InformationDeleteItem-RL-ReconfRqstTDD		CRITICALITY notify	TYPE DL-CCTrCH-InformationDeleteItem-RL-ReconfRqstTDD		PRESENCE	mandatory}
--}

DL-CCTrCH-InformationDeleteItem-RL-ReconfRqstTDD ::= SEQUENCE {
	cCTrCH-ID										CCTrCH-ID,
--	iE-Extensions									ProtocolExtensionContainer { { DL-CCTrCH-InformationDeleteItem-RL-ReconfRqstTDD-ExtIEs} }			OPTIONAL,
	iE-Extensions									ProtocolExtensionContainer OPTIONAL,
	...
}

--DL-CCTrCH-InformationDeleteItem-RL-ReconfRqstTDD-ExtIEs  NBAP-PROTOCOL-EXTENSION ::= {
--	...
--}

--DCH-DeleteList-RL-ReconfRqstTDD ::= SEQUENCE (SIZE (1..maxNrOfDCHs)) OF DCH-DeleteItem-RL-ReconfRqstTDD
DCH-DeleteList-RL-ReconfRqstTDD ::= SEQUENCE (SIZE (1..128)) OF DCH-DeleteItem-RL-ReconfRqstTDD

DCH-DeleteItem-RL-ReconfRqstTDD ::= SEQUENCE {
	dCH-ID											DCH-ID,
--	iE-Extensions									ProtocolExtensionContainer { { DCH-DeleteItem-RL-ReconfRqstTDD-ExtIEs} }			OPTIONAL,
	iE-Extensions									ProtocolExtensionContainer OPTIONAL,
	...
}

--DCH-DeleteItem-RL-ReconfRqstTDD-ExtIEs  NBAP-PROTOCOL-EXTENSION ::= {
--	...
--}

--Multiple-RL-Information-RL-ReconfRqstTDD ::= SEQUENCE (SIZE (1..maxNrOfRLs-1)) OF RL-Information-RL-ReconfRqstTDD
Multiple-RL-Information-RL-ReconfRqstTDD ::= SEQUENCE (SIZE (1..15)) OF RL-Information-RL-ReconfRqstTDD
--Includes the 2nd through the max number of radio link information repetitions.

RL-Information-RL-ReconfRqstTDD ::= SEQUENCE {
	rL-ID										RL-ID,
	maxDL-Power									DL-Power		OPTIONAL,
	minDL-Power									DL-Power		OPTIONAL,
--	iE-Extensions								ProtocolExtensionContainer { { RL-InformationItem-RL-ReconfRqstTDD-ExtIEs} }			OPTIONAL,
	iE-Extensions								ProtocolExtensionContainer OPTIONAL,
	...
}

--RL-InformationItem-RL-ReconfRqstTDD-ExtIEs  NBAP-PROTOCOL-EXTENSION ::= {
--	{ ID id-RL-Specific-DCH-Info		CRITICALITY	ignore		EXTENSION 	RL-Specific-DCH-Info	PRESENCE 	optional	}|
--	{ ID id-UL-Synchronisation-Parameters-LCR			CRITICALITY	ignore		EXTENSION 	UL-Synchronisation-Parameters-LCR		PRESENCE 	optional	},
	-- Mandatory for 1.28Mcps TDD, Not Applicable to 3.84Mcps TDD
--	...
--}

-- **************************************************************
--
-- RADIO LINK RECONFIGURATION RESPONSE
--
-- **************************************************************

--RadioLinkReconfigurationResponse ::= SEQUENCE {
--	protocolIEs				ProtocolIE-Container	{{RadioLinkReconfigurationResponse-IEs}},
--	protocolExtensions		ProtocolExtensionContainer	{{RadioLinkReconfigurationResponse-Extensions}}		OPTIONAL,
--	...
--}
RadioLinkReconfigurationResponse ::= SEQUENCE {
	protocolIEs				ProtocolIE-Container,
	protocolExtensions		ProtocolExtensionContainer OPTIONAL,
	...
}

--RadioLinkReconfigurationResponse-IEs NBAP-PROTOCOL-IES ::= {
--	{ ID	id-CRNC-CommunicationContextID					CRITICALITY	ignore		TYPE	CRNC-CommunicationContextID						PRESENCE	mandatory	} |
--	{ ID	id-RL-InformationResponseList-RL-ReconfRsp		CRITICALITY	ignore		TYPE	RL-InformationResponseList-RL-ReconfRsp			PRESENCE	optional	} |
--	{ ID	id-CriticalityDiagnostics						CRITICALITY	ignore		TYPE	CriticalityDiagnostics							PRESENCE	optional	},
--	...
--}

--RadioLinkReconfigurationResponse-Extensions NBAP-PROTOCOL-EXTENSION ::= {
--	{ ID id-TargetCommunicationControlPortID	CRITICALITY ignore		EXTENSION CommunicationControlPortID		PRESENCE optional }|
--	{ ID id-HSDSCH-FDD-Information-Response		CRITICALITY ignore		EXTENSION HSDSCH-FDD-Information-Response		PRESENCE optional }|
	-- FDD only
--	{ ID id-HSDSCH-TDD-Information-Response		CRITICALITY ignore		EXTENSION HSDSCH-TDD-Information-Response		PRESENCE optional },
	-- TDD only
	
--	...
--}

--RL-InformationResponseList-RL-ReconfRsp ::= SEQUENCE (SIZE (1..maxNrOfRLs)) OF ProtocolIE-Single-Container {{RL-InformationResponseItemIE-RL-ReconfRsp}}
RL-InformationResponseList-RL-ReconfRsp ::= SEQUENCE (SIZE (1..16)) OF ProtocolIE-Single-Container

--RL-InformationResponseItemIE-RL-ReconfRsp NBAP-PROTOCOL-IES ::= {
--	{ ID	id-RL-InformationResponseItem-RL-ReconfRsp			CRITICALITY		ignore			TYPE	RL-InformationResponseItem-RL-ReconfRsp			PRESENCE	mandatory}
--}

RL-InformationResponseItem-RL-ReconfRsp ::= SEQUENCE {
	rL-ID										RL-ID,
	dCH-InformationResponseList-RL-ReconfRsp	DCH-InformationResponseList-RL-ReconfRsp									OPTIONAL,
--	iE-Extensions								ProtocolExtensionContainer { { RL-InformationResponseItem-RL-ReconfRsp-ExtIEs} }		OPTIONAL,
	iE-Extensions								ProtocolExtensionContainer OPTIONAL,
	...
}

--RL-InformationResponseItem-RL-ReconfRsp-ExtIEs  NBAP-PROTOCOL-EXTENSION ::= {
--	{ ID id-DL-PowerBalancing-UpdatedIndicator			CRITICALITY ignore	EXTENSION DL-PowerBalancing-UpdatedIndicator				PRESENCE optional	}|
	-- FDD only
--	{ ID id-E-DCH-RL-Set-ID								CRITICALITY ignore	EXTENSION RL-Set-ID							PRESENCE optional }|
--	{ ID id-E-DCH-FDD-DL-Control-Channel-Information	CRITICALITY ignore	EXTENSION E-DCH-FDD-DL-Control-Channel-Information		PRESENCE optional }|
--	{ ID id-E-DCH-FDD-Information-Response				CRITICALITY ignore	EXTENSION E-DCH-FDD-Information-Response				PRESENCE optional },
--	...
--}

--DCH-InformationResponseList-RL-ReconfRsp::= ProtocolIE-Single-Container {{ DCH-InformationResponseListIEs-RL-ReconfRsp }}
DCH-InformationResponseList-RL-ReconfRsp::= ProtocolIE-Single-Container

--DCH-InformationResponseListIEs-RL-ReconfRsp NBAP-PROTOCOL-IES ::= {
--	{ ID id-DCH-InformationResponse   CRITICALITY ignore	TYPE DCH-InformationResponse	PRESENCE mandatory }
--}

-- **************************************************************
--
-- RADIO LINK DELETION REQUEST
--
-- **************************************************************

--RadioLinkDeletionRequest ::= SEQUENCE {
--	protocolIEs				ProtocolIE-Container	{{RadioLinkDeletionRequest-IEs}},
--	protocolExtensions		ProtocolExtensionContainer	{{RadioLinkDeletionRequest-Extensions}}		OPTIONAL,
--	...
--}
RadioLinkDeletionRequest ::= SEQUENCE {
	protocolIEs				ProtocolIE-Container,
	protocolExtensions		ProtocolExtensionContainer	OPTIONAL,
	...
}

--RadioLinkDeletionRequest-IEs NBAP-PROTOCOL-IES ::= {
--	{ ID	id-NodeB-CommunicationContextID					CRITICALITY reject	TYPE NodeB-CommunicationContextID				PRESENCE mandatory }|
--	{ ID	id-CRNC-CommunicationContextID					CRITICALITY reject	TYPE CRNC-CommunicationContextID				PRESENCE mandatory }|
--	{ ID	id-RL-informationList-RL-DeletionRqst			CRITICALITY notify	TYPE RL-informationList-RL-DeletionRqst		PRESENCE mandatory },
--	...
--}

--RadioLinkDeletionRequest-Extensions NBAP-PROTOCOL-EXTENSION ::= {
--	...
--}

--RL-informationList-RL-DeletionRqst ::= SEQUENCE (SIZE (1..maxNrOfRLs)) OF ProtocolIE-Single-Container {{RL-informationItemIE-RL-DeletionRqst}}
RL-informationList-RL-DeletionRqst ::= SEQUENCE (SIZE (1..16)) OF ProtocolIE-Single-Container

--RL-informationItemIE-RL-DeletionRqst NBAP-PROTOCOL-IES ::= {
--	{ ID	id-RL-informationItem-RL-DeletionRqst			CRITICALITY		notify			TYPE	RL-informationItem-RL-DeletionRqst				PRESENCE	mandatory}
--}

RL-informationItem-RL-DeletionRqst ::= SEQUENCE {
 	rL-ID										RL-ID,
--	iE-Extensions								ProtocolExtensionContainer { { RL-informationItem-RL-DeletionRqst-ExtIEs} }		OPTIONAL,
	iE-Extensions								ProtocolExtensionContainer OPTIONAL,
	...		
 }

--RL-informationItem-RL-DeletionRqst-ExtIEs  NBAP-PROTOCOL-EXTENSION ::= {
--	...
--}

-- **************************************************************
--
-- RADIO LINK DELETION RESPONSE
--
-- **************************************************************

--RadioLinkDeletionResponse ::= SEQUENCE {
--	protocolIEs				ProtocolIE-Container	{{RadioLinkDeletionResponse-IEs}},
--	protocolExtensions		ProtocolExtensionContainer	{{RadioLinkDeletionResponse-Extensions}}		OPTIONAL,
--	...
--}
RadioLinkDeletionResponse ::= SEQUENCE {
	protocolIEs				ProtocolIE-Container,
	protocolExtensions		ProtocolExtensionContainer	OPTIONAL,
	...
}

--RadioLinkDeletionResponse-IEs NBAP-PROTOCOL-IES ::= {
--	{ ID	id-CRNC-CommunicationContextID			CRITICALITY ignore	TYPE CRNC-CommunicationContextID				PRESENCE	mandatory	}|
--	{ ID	id-CriticalityDiagnostics				CRITICALITY ignore	TYPE CriticalityDiagnostics				PRESENCE	optional	},
--	...
--}

--RadioLinkDeletionResponse-Extensions NBAP-PROTOCOL-EXTENSION ::= {
--	...
--}


-- **************************************************************
--
-- DL POWER CONTROL REQUEST FDD
--
-- **************************************************************

--DL-PowerControlRequest ::= SEQUENCE {
--	protocolIEs				ProtocolIE-Container	{{DL-PowerControlRequest-IEs}},
--	protocolExtensions		ProtocolExtensionContainer	{{DL-PowerControlRequest-Extensions}}		OPTIONAL,
--	...
--}
DL-PowerControlRequest ::= SEQUENCE {
	protocolIEs				ProtocolIE-Container,
	protocolExtensions		ProtocolExtensionContainer	OPTIONAL,
	...
}
--DL-PowerControlRequest-IEs NBAP-PROTOCOL-IES ::= {
--	{ ID id-NodeB-CommunicationContextID		CRITICALITY	ignore	TYPE	NodeB-CommunicationContextID		PRESENCE	mandatory	} |
--	{ ID id-PowerAdjustmentType					CRITICALITY ignore	TYPE PowerAdjustmentType			PRESENCE mandatory} |
--	{ ID id-DLReferencePower					CRITICALITY ignore	TYPE DL-Power						PRESENCE conditional} |
	-- This IE shall be present if the Adjustment Type IE is set to 'Common'
--	{ ID id-InnerLoopDLPCStatus					CRITICALITY	ignore	TYPE InnerLoopDLPCStatus			PRESENCE	optional } |
--	{ ID id-DLReferencePowerList-DL-PC-Rqst		CRITICALITY ignore	TYPE DL-ReferencePowerInformationList-DL-PC-Rqst	PRESENCE conditional } |
	-- This IE shall be present if the Adjustment Type IE is set to 'Individual'
--	{ ID id-MaxAdjustmentStep					CRITICALITY ignore	TYPE MaxAdjustmentStep				PRESENCE conditional} |
	-- This IE shall be present if the Adjustment Type IE is set to 'Common' or 'Individual'
--	{ ID id-AdjustmentPeriod					CRITICALITY ignore	TYPE AdjustmentPeriod				PRESENCE conditional }|
	-- This IE shall be present if the Adjustment Type IE is set to 'Common' or 'Individual'
--	{ ID id-AdjustmentRatio						CRITICALITY ignore	TYPE ScaledAdjustmentRatio			PRESENCE conditional	},
	-- This IE shall be present if the Adjustment Type IE is set to 'Common' or 'Individual'
--	...
--}

--DL-PowerControlRequest-Extensions NBAP-PROTOCOL-EXTENSION ::= {
--	...
--}

--DL-ReferencePowerInformationList-DL-PC-Rqst ::= SEQUENCE (SIZE (1..maxNrOfRLs)) OF ProtocolIE-Single-Container {{DL-ReferencePowerInformationItemIE-DL-PC-Rqst }}
DL-ReferencePowerInformationList-DL-PC-Rqst ::= SEQUENCE (SIZE (1..16)) OF ProtocolIE-Single-Container

--DL-ReferencePowerInformationItemIE-DL-PC-Rqst NBAP-PROTOCOL-IES ::= {
--	{ ID id-DL-ReferencePowerInformationItem-DL-PC-Rqst		CRITICALITY		 ignore		TYPE 	DL-ReferencePowerInformationItem-DL-PC-Rqst		PRESENCE 	mandatory
--}
--}

DL-ReferencePowerInformationItem-DL-PC-Rqst ::= SEQUENCE {
	rL-ID									RL-ID,
	dl-ReferencePower						DL-Power,
--	iE-Extensions							ProtocolExtensionContainer { { DL-ReferencePowerInformationItem-DL-PC-Rqst-ExtIEs } }		OPTIONAL,
	iE-Extensions							ProtocolExtensionContainer OPTIONAL,
	...		
}

--DL-ReferencePowerInformationItem-DL-PC-Rqst-ExtIEs  NBAP-PROTOCOL-EXTENSION ::= {
--	...
--}

-- **************************************************************
--
-- DL POWER TIMESLOT CONTROL REQUEST TDD
--
-- **************************************************************

--DL-PowerTimeslotControlRequest ::= SEQUENCE {
--	protocolIEs				ProtocolIE-Container	{{DL-PowerTimeslotControlRequest-IEs}},
--	protocolExtensions		ProtocolExtensionContainer	{{DL-PowerTimeslotControlRequest-Extensions}}		OPTIONAL,
--	...
--}
DL-PowerTimeslotControlRequest ::= SEQUENCE {
	protocolIEs				ProtocolIE-Container,
	protocolExtensions		ProtocolExtensionContainer OPTIONAL,
	...
}
--DL-PowerTimeslotControlRequest-IEs NBAP-PROTOCOL-IES ::= {
--	{ ID id-NodeB-CommunicationContextID			CRITICALITY	ignore			TYPE	NodeB-CommunicationContextID				PRESENCE	mandatory	} |
--	{ ID id-TimeslotISCPInfo		CRITICALITY	ignore			TYPE	DL-TimeslotISCPInfo		PRESENCE optional },
	-- Mandatory for 3.84Mcps TDD, Not Applicable to 1.28Mcps TDD

--	...
--}

--DL-PowerTimeslotControlRequest-Extensions NBAP-PROTOCOL-EXTENSION ::= {
--	{ ID id-TimeslotISCPInfoList-LCR-DL-PC-RqstTDD		CRITICALITY	ignore			EXTENSION	DL-TimeslotISCPInfoLCR		PRESENCE optional }|
	-- Mandatory for 1.28Mcps TDD, Not Applicable to 3.84Mcps TDD
--	{ ID id-PrimCCPCH-RSCP-DL-PC-RqstTDD				CRITICALITY ignore			EXTENSION PrimaryCCPCH-RSCP		PRESENCE optional	}|
--	{ ID id-PrimaryCCPCH-RSCP-Delta						CRITICALITY	ignore			EXTENSION PrimaryCCPCH-RSCP-Delta	PRESENCE optional	},
--	...
--}

-- **************************************************************
--
-- DEDICATED MEASUREMENT INITIATION REQUEST
--
-- **************************************************************

--DedicatedMeasurementInitiationRequest ::= SEQUENCE {
--	protocolIEs				ProtocolIE-Container	{{DedicatedMeasurementInitiationRequest-IEs}},
--	protocolExtensions		ProtocolExtensionContainer	{{DedicatedMeasurementInitiationRequest-Extensions}}		OPTIONAL,
--	...
--}
DedicatedMeasurementInitiationRequest ::= SEQUENCE {
	protocolIEs				ProtocolIE-Container,
	protocolExtensions		ProtocolExtensionContainer	OPTIONAL,
	...
}
--DedicatedMeasurementInitiationRequest-IEs NBAP-PROTOCOL-IES ::= {
--	{ ID id-NodeB-CommunicationContextID			CRITICALITY reject	TYPE NodeB-CommunicationContextID			PRESENCE mandatory } |
--	{ ID id-MeasurementID							CRITICALITY reject	TYPE MeasurementID					PRESENCE mandatory } |
--	{ ID id-DedicatedMeasurementObjectType-DM-Rqst	CRITICALITY reject	TYPE DedicatedMeasurementObjectType-DM-Rqst			PRESENCE mandatory } |
--	{ ID id-DedicatedMeasurementType				CRITICALITY reject	TYPE DedicatedMeasurementType			PRESENCE mandatory } |
--	{ ID id-MeasurementFilterCoefficient			CRITICALITY reject	TYPE MeasurementFilterCoefficient			PRESENCE optional } |
--	{ ID id-ReportCharacteristics					CRITICALITY reject	TYPE ReportCharacteristics			PRESENCE mandatory } |
--	{ ID id-CFNReportingIndicator					CRITICALITY reject	TYPE FNReportingIndicator			PRESENCE mandatory } |
--	{ ID id-CFN										CRITICALITY reject	TYPE CFN							PRESENCE optional } ,
--	...
--}

--DedicatedMeasurementInitiationRequest-Extensions NBAP-PROTOCOL-EXTENSION ::= {
--	{ ID	id-NumberOfReportedCellPortions	CRITICALITY reject	EXTENSION NumberOfReportedCellPortions	PRESENCE conditional	}|
	-- The IE shall be present if the Dedicated Measurement Type IE is set to ”Best Cell Portions”, FDD only.
--	{ ID	id-MeasurementRecoveryBehavior				CRITICALITY ignore				EXTENSION	MeasurementRecoveryBehavior		PRESENCE optional
--	},
--	...
--}

DedicatedMeasurementObjectType-DM-Rqst ::= CHOICE {
	rL							RL-DM-Rqst,
	rLS							RL-Set-DM-Rqst, 		-- for FDD only
	all-RL						AllRL-DM-Rqst,
	all-RLS						AllRL-Set-DM-Rqst, 		-- for FDD only
	...
}

RL-DM-Rqst ::= SEQUENCE {
 	rL-InformationList					RL-InformationList-DM-Rqst,
--	iE-Extensions						ProtocolExtensionContainer { { RLItem-DM-Rqst-ExtIEs } }		OPTIONAL,
	iE-Extensions						ProtocolExtensionContainer OPTIONAL,
	...		
}

--RLItem-DM-Rqst-ExtIEs  NBAP-PROTOCOL-EXTENSION ::= {
--	...
--}

--RL-InformationList-DM-Rqst ::= SEQUENCE (SIZE (1..maxNrOfRLs)) OF ProtocolIE-Single-Container {{ RL-InformationItemIE-DM-Rqst }}
RL-InformationList-DM-Rqst ::= SEQUENCE (SIZE (1..16)) OF ProtocolIE-Single-Container

--RL-InformationItemIE-DM-Rqst NBAP-PROTOCOL-IES ::= {
--	{ ID id-RL-InformationItem-DM-Rqst   CRITICALITY reject	TYPE RL-InformationItem-DM-Rqst		PRESENCE mandatory }
--}

RL-InformationItem-DM-Rqst ::= SEQUENCE {
		rL-ID							RL-ID,	
		dPCH-ID							DPCH-ID				OPTIONAL, -- for TDD only
--		iE-Extensions					ProtocolExtensionContainer { { RL-InformationItem-DM-Rqst-ExtIEs } }		OPTIONAL,
		iE-Extensions					ProtocolExtensionContainer OPTIONAL,
		...		
	}

--RL-InformationItem-DM-Rqst-ExtIEs  NBAP-PROTOCOL-EXTENSION ::= {
--	{ ID id-PUSCH-Info-DM-Rqst		CRITICALITY reject				EXTENSION	PUSCH-Info-DM-Rqst		PRESENCE optional}|
	-- TDD only
--	{ ID id-HSSICH-Info-DM-Rqst		CRITICALITY reject				EXTENSION	HSSICH-Info-DM-Rqst		PRESENCE optional},
	-- TDD only
--	...
--}

--PUSCH-Info-DM-Rqst ::= SEQUENCE (SIZE (1..maxNrOfPUSCHs)) OF PUSCH-ID
PUSCH-Info-DM-Rqst ::= SEQUENCE (SIZE (1..256)) OF PUSCH-ID

--HSSICH-Info-DM-Rqst ::= SEQUENCE (SIZE (1..maxNrOfHSSICHs)) OF HS-SICH-ID
HSSICH-Info-DM-Rqst ::= SEQUENCE (SIZE (1..4)) OF HS-SICH-ID

RL-Set-DM-Rqst ::= SEQUENCE {
	rL-Set-InformationList-DM-Rqst			RL-Set-InformationList-DM-Rqst,
--	iE-Extensions							ProtocolExtensionContainer { { RL-SetItem-DM-Rqst-ExtIEs } }		OPTIONAL,
	iE-Extensions							ProtocolExtensionContainer OPTIONAL,
	...		
}

--RL-SetItem-DM-Rqst-ExtIEs  NBAP-PROTOCOL-EXTENSION ::= {
--	...
--}

--RL-Set-InformationList-DM-Rqst					::= SEQUENCE (SIZE(1..maxNrOfRLSets)) OF RL-Set-InformationItem-DM-Rqst
RL-Set-InformationList-DM-Rqst					::= SEQUENCE (SIZE(1..16)) OF RL-Set-InformationItem-DM-Rqst

RL-Set-InformationItem-DM-Rqst ::= SEQUENCE {
	rL-Set-ID						RL-Set-ID,
--	iE-Extensions					ProtocolExtensionContainer { { RL-Set-InformationItem-DM-Rqst-ExtIEs} } OPTIONAL,
	iE-Extensions					ProtocolExtensionContainer OPTIONAL,
	...
}

--RL-Set-InformationItem-DM-Rqst-ExtIEs NBAP-PROTOCOL-EXTENSION ::= {
--	...
--}

AllRL-DM-Rqst ::= NULL


AllRL-Set-DM-Rqst ::= NULL

-- **************************************************************
--
-- DEDICATED MEASUREMENT INITIATION RESPONSE
--
-- **************************************************************

--DedicatedMeasurementInitiationResponse ::= SEQUENCE {
--	protocolIEs				ProtocolIE-Container	{{DedicatedMeasurementInitiationResponse-IEs}},
--	protocolExtensions		ProtocolExtensionContainer	{{DedicatedMeasurementInitiationResponse-Extensions}}		OPTIONAL,
--	...
--}
DedicatedMeasurementInitiationResponse ::= SEQUENCE {
	protocolIEs				ProtocolIE-Container,
	protocolExtensions		ProtocolExtensionContainer	OPTIONAL,
	...
}

--DedicatedMeasurementInitiationResponse-IEs NBAP-PROTOCOL-IES ::= {
--	{ ID id-CRNC-CommunicationContextID				CRITICALITY ignore	TYPE CRNC-CommunicationContextID		PRESENCE mandatory } |
--	{ ID id-MeasurementID							CRITICALITY ignore	TYPE MeasurementID				PRESENCE mandatory } |
--	{ ID id-DedicatedMeasurementObjectType-DM-Rsp	CRITICALITY ignore	TYPE DedicatedMeasurementObjectType-DM-Rsp		PRESENCE optional } |
--	{ ID id-CriticalityDiagnostics					CRITICALITY ignore	TYPE CriticalityDiagnostics		PRESENCE optional },
--	...
--}

--DedicatedMeasurementInitiationResponse-Extensions NBAP-PROTOCOL-EXTENSION ::= {
--	{ ID	id-MeasurementRecoverySupportIndicator		CRITICALITY ignore		EXTENSION	MeasurementRecoverySupportIndicator		PRESENCE optional
--	},
--	...
--}

DedicatedMeasurementObjectType-DM-Rsp ::= CHOICE {
	rL							RL-DM-Rsp,
	rLS							RL-Set-DM-Rsp, 	-- for FDD only
	all-RL						RL-DM-Rsp,
	all-RLS						RL-Set-DM-Rsp, 	-- for FDD only
	...
}

RL-DM-Rsp ::= SEQUENCE {
	rL-InformationList-DM-Rsp			RL-InformationList-DM-Rsp,
--	iE-Extensions						ProtocolExtensionContainer { { RLItem-DM-Rsp-ExtIEs } }		OPTIONAL,
	iE-Extensions						ProtocolExtensionContainer OPTIONAL,
	...
}

--RLItem-DM-Rsp-ExtIEs  NBAP-PROTOCOL-EXTENSION ::= {
--	...
--}

--RL-InformationList-DM-Rsp ::= SEQUENCE (SIZE (1..maxNrOfRLs)) OF ProtocolIE-Single-Container {{ RL-InformationItemIE-DM-Rsp }}
RL-InformationList-DM-Rsp ::= SEQUENCE (SIZE (1..16)) OF ProtocolIE-Single-Container

--RL-InformationItemIE-DM-Rsp NBAP-PROTOCOL-IES ::= {
--	{ ID id-RL-InformationItem-DM-Rsp   CRITICALITY ignore	TYPE RL-InformationItem-DM-Rsp		PRESENCE mandatory }
--}

RL-InformationItem-DM-Rsp ::= SEQUENCE {
	rL-ID								RL-ID,
	dPCH-ID								DPCH-ID			OPTIONAL, 	-- for TDD only
	dedicatedMeasurementValue			DedicatedMeasurementValue,
	cFN									CFN				OPTIONAL,
--	iE-Extensions						ProtocolExtensionContainer { { RL-InformationItem-DM-Rsp-ExtIEs } }		OPTIONAL,
	iE-Extensions						ProtocolExtensionContainer OPTIONAL,
	...
}

--RL-InformationItem-DM-Rsp-ExtIEs  NBAP-PROTOCOL-EXTENSION ::= {
--	{ID id-PUSCH-Info-DM-Rsp		CRITICALITY reject				EXTENSION	PUSCH-Info-DM-Rsp		PRESENCE optional}|
	-- TDD only
	-- This PUSCH Information is the for the first PUSCH repetition, PUSCH information for PUSCH repetitions 2 and on, should be defined in Multiple-PUSCH-InfoList-DM-Rsp.
--	{ID id-HSSICH-Info-DM-Rsp		CRITICALITY reject				EXTENSION	HS-SICH-ID				PRESENCE optional}|
	-- TDD only
--	{ ID	id-multiple-DedicatedMeasurementValueList-TDD-DM-Rsp	CRITICALITY ignore	EXTENSION Multiple-DedicatedMeasurementValueList-TDD-DM-Rsp	PRESENCE optional	}|
	-- Applicable to 3.84Mcps TDD only. This list of dedicated measurement values is used for the 2nd and beyond measurements of a RL when multiple dedicated measurement values need to be reported.
--	{ ID	id-multiple-DedicatedMeasurementValueList-LCR-TDD-DM-Rsp	CRITICALITY ignore	EXTENSION Multiple-DedicatedMeasurementValueList-LCR-TDD-DM-Rsp	PRESENCE optional	}|
	-- Applicable to 1.28Mcps TDD only. This list of dedicated measurement values is used for the 2nd and beyond measurements of a RL when multiple dedicated measurement values need to be reported.
--	{ ID	id-multiple-PUSCH-InfoList-DM-Rsp	CRITICALITY ignore	EXTENSION Multiple-PUSCH-InfoList-DM-Rsp	PRESENCE optional	},
	-- TDD only, This PUSCH information is the for the 2nd and beyond PUSCH repetitions.
--	...
--}

--PUSCH-Info-DM-Rsp ::= SEQUENCE (SIZE (1..maxNrOfPUSCHs)) OF PUSCH-ID
PUSCH-Info-DM-Rsp ::= SEQUENCE (SIZE (1..256)) OF PUSCH-ID

--Multiple-PUSCH-InfoList-DM-Rsp ::= SEQUENCE (SIZE (1.. maxNrOfPUSCHs-1)) OF Multiple-PUSCH-InfoListIE-DM-Rsp
Multiple-PUSCH-InfoList-DM-Rsp ::= SEQUENCE (SIZE (1.. 255)) OF Multiple-PUSCH-InfoListIE-DM-Rsp
-- Includes the 2nd through the max number of PUSCH information repetitions.

Multiple-PUSCH-InfoListIE-DM-Rsp ::= SEQUENCE {
	pUSCH-ID								PUSCH-ID														OPTIONAL,
	dedicatedMeasurementValue				DedicatedMeasurementValue										OPTIONAL,
--	iE-Extensions							ProtocolExtensionContainer { { Multiple-PUSCH-InfoListIE-DM-Rsp-ExtIEs} }		OPTIONAL,
	iE-Extensions							ProtocolExtensionContainer OPTIONAL,
	...
}

--Multiple-PUSCH-InfoListIE-DM-Rsp-ExtIEs NBAP-PROTOCOL-EXTENSION ::= {
--	...
--}

RL-Set-DM-Rsp ::= SEQUENCE {
	rL-Set-InformationList-DM-Rsp		RL-Set-InformationList-DM-Rsp,
--	iE-Extensions						ProtocolExtensionContainer { { RL-SetItem-DM-Rsp-ExtIEs } }		OPTIONAL,
	iE-Extensions						ProtocolExtensionContainer OPTIONAL,
	...
}

--RL-SetItem-DM-Rsp-ExtIEs  NBAP-PROTOCOL-EXTENSION ::= {
--	...
--}

--RL-Set-InformationList-DM-Rsp ::= SEQUENCE (SIZE (1..maxNrOfRLSets)) OF ProtocolIE-Single-Container {{ RL-Set-InformationItemIE-DM-Rsp }}
RL-Set-InformationList-DM-Rsp ::= SEQUENCE (SIZE (1..16)) OF ProtocolIE-Single-Container 

--RL-Set-InformationItemIE-DM-Rsp NBAP-PROTOCOL-IES ::= {
--	{ ID id-RL-Set-InformationItem-DM-Rsp		CRITICALITY ignore		TYPE 	RL-Set-InformationItem-DM-Rsp	PRESENCE mandatory}
--}

RL-Set-InformationItem-DM-Rsp ::= SEQUENCE {
	rL-Set-ID						RL-Set-ID,
	dedicatedMeasurementValue		DedicatedMeasurementValue,
	cFN								CFN					OPTIONAL,
--	iE-Extensions					ProtocolExtensionContainer { { RL-Set-InformationItem-DM-Rsp-ExtIEs} } OPTIONAL,
	iE-Extensions					ProtocolExtensionContainer OPTIONAL,
	...
}

--RL-Set-InformationItem-DM-Rsp-ExtIEs NBAP-PROTOCOL-EXTENSION ::= {
--	...
--}

--Multiple-DedicatedMeasurementValueList-TDD-DM-Rsp ::= SEQUENCE (SIZE (1.. maxNrOfDPCHsPerRL-1)) OF Multiple-DedicatedMeasurementValueItem-TDD-DM-Rsp
Multiple-DedicatedMeasurementValueList-TDD-DM-Rsp ::= SEQUENCE (SIZE (1.. 239)) OF Multiple-DedicatedMeasurementValueItem-TDD-DM-Rsp

Multiple-DedicatedMeasurementValueItem-TDD-DM-Rsp ::= SEQUENCE {
	dPCH-ID								DPCH-ID, 
	dedicatedMeasurementValue			DedicatedMeasurementValue,
--	iE-Extensions						ProtocolExtensionContainer { { Multiple-DedicatedMeasurementValueItem-TDD-DM-Rsp-ExtIEs} }		OPTIONAL,
	iE-Extensions						ProtocolExtensionContainer OPTIONAL,
	...
}

--Multiple-DedicatedMeasurementValueItem-TDD-DM-Rsp-ExtIEs NBAP-PROTOCOL-EXTENSION ::= {
--	...
--}
--Multiple-DedicatedMeasurementValueList-LCR-TDD-DM-Rsp ::= SEQUENCE (SIZE (1.. maxNrOfDPCHsLCRPerRL-1)) OF Multiple-DedicatedMeasurementValueItem-LCR-TDD-DM-Rsp
Multiple-DedicatedMeasurementValueList-LCR-TDD-DM-Rsp ::= SEQUENCE (SIZE (1.. 95)) OF Multiple-DedicatedMeasurementValueItem-LCR-TDD-DM-Rsp

Multiple-DedicatedMeasurementValueItem-LCR-TDD-DM-Rsp ::= SEQUENCE {
	dPCH-ID								DPCH-ID, 
	dedicatedMeasurementValue			DedicatedMeasurementValue,
--	iE-Extensions						ProtocolExtensionContainer { { Multiple-DedicatedMeasurementValueItem-LCR-TDD-DM-Rsp-ExtIEs} }		OPTIONAL,
	iE-Extensions						ProtocolExtensionContainer OPTIONAL,
	...
}

--Multiple-DedicatedMeasurementValueItem-LCR-TDD-DM-Rsp-ExtIEs NBAP-PROTOCOL-EXTENSION ::= {
--	...
--}


-- **************************************************************
--
-- DEDICATED MEASUREMENT INITIATION FAILURE
--
-- **************************************************************
--DedicatedMeasurementInitiationFailure ::= SEQUENCE {
--	protocolIEs				ProtocolIE-Container	{{DedicatedMeasurementInitiationFailure-IEs}},
--	protocolExtensions		ProtocolExtensionContainer	{{DedicatedMeasurementInitiationFailure-Extensions}}		OPTIONAL,
--	...
--}
DedicatedMeasurementInitiationFailure ::= SEQUENCE {
	protocolIEs				ProtocolIE-Container,
	protocolExtensions		ProtocolExtensionContainer OPTIONAL,
	...
}

--DedicatedMeasurementInitiationFailure-IEs NBAP-PROTOCOL-IES ::= {
--	{ ID	id-CRNC-CommunicationContextID			CRITICALITY		ignore			TYPE	CRNC-CommunicationContextID		PRESENCE	mandatory	} |
--	{ ID	id-MeasurementID						CRITICALITY		ignore			TYPE	MeasurementID				PRESENCE	mandatory	} |
--	{ ID	id-Cause								CRITICALITY		ignore			TYPE	Cause				PRESENCE	mandatory	} |
--	{ ID	id-CriticalityDiagnostics				CRITICALITY		ignore			TYPE	CriticalityDiagnostics				PRESENCE	optional	},
--	...
--}

--DedicatedMeasurementInitiationFailure-Extensions NBAP-PROTOCOL-EXTENSION ::= {
--	...
--}

-- **************************************************************
--
-- DEDICATED MEASUREMENT REPORT
--
-- **************************************************************

--DedicatedMeasurementReport ::= SEQUENCE {
--	protocolIEs				ProtocolIE-Container	{{DedicatedMeasurementReport-IEs}},
--	protocolExtensions		ProtocolExtensionContainer	{{DedicatedMeasurementReport-Extensions}}		OPTIONAL,
--	...
--}
DedicatedMeasurementReport ::= SEQUENCE {
	protocolIEs				ProtocolIE-Container,
	protocolExtensions		ProtocolExtensionContainer	OPTIONAL,
	...
}
--DedicatedMeasurementReport-IEs NBAP-PROTOCOL-IES ::= {
--	{ ID id-CRNC-CommunicationContextID				CRITICALITY ignore	TYPE CRNC-CommunicationContextID		PRESENCE	mandatory	} |
--	{ ID id-MeasurementID							CRITICALITY ignore	TYPE MeasurementID				PRESENCE	mandatory	} |
--	{ ID id-DedicatedMeasurementObjectType-DM-Rprt	CRITICALITY ignore	TYPE DedicatedMeasurementObjectType-DM-Rprt		PRESENCE	mandatory	} ,
--	...
--}

--DedicatedMeasurementReport-Extensions NBAP-PROTOCOL-EXTENSION ::= {
--	{ ID	id-MeasurementRecoveryReportingIndicator		CRITICALITY ignore		EXTENSION	MeasurementRecoveryReportingIndicator		PRESENCE optional
--	},
--	...
--}

DedicatedMeasurementObjectType-DM-Rprt ::= CHOICE {
 	rL									RL-DM-Rprt,
	rLS									RL-Set-DM-Rprt, 		-- for FDD only
 	all-RL								RL-DM-Rprt,
	all-RLS								RL-Set-DM-Rprt, 		-- for FDD only
	...
}

RL-DM-Rprt ::= SEQUENCE {
	rL-InformationList-DM-Rprt			RL-InformationList-DM-Rprt,
--	iE-Extensions						ProtocolExtensionContainer { { RLItem-DM-Rprt-ExtIEs } }		OPTIONAL,
	iE-Extensions						ProtocolExtensionContainer OPTIONAL,
	...
}

--RLItem-DM-Rprt-ExtIEs  NBAP-PROTOCOL-EXTENSION ::= {
--	...
--}

--RL-InformationList-DM-Rprt ::= SEQUENCE (SIZE (1..maxNrOfRLs)) OF ProtocolIE-Single-Container {{ RL-InformationItemIE-DM-Rprt }}
RL-InformationList-DM-Rprt ::= SEQUENCE (SIZE (1..16)) OF ProtocolIE-Single-Container

--RL-InformationItemIE-DM-Rprt NBAP-PROTOCOL-IES ::= {
--	{ ID id-RL-InformationItem-DM-Rprt   CRITICALITY ignore	TYPE RL-InformationItem-DM-Rprt		PRESENCE mandatory }
--}

RL-InformationItem-DM-Rprt ::= SEQUENCE {
	rL-ID							RL-ID,
	dPCH-ID							DPCH-ID		OPTIONAL, 		-- for TDD only
	dedicatedMeasurementValueInformation	DedicatedMeasurementValueInformation,
--	iE-Extensions					ProtocolExtensionContainer { { RL-InformationItem-DM-Rprt-ExtIEs } }		OPTIONAL,
	iE-Extensions					ProtocolExtensionContainer OPTIONAL,
	...
}

--RL-InformationItem-DM-Rprt-ExtIEs  NBAP-PROTOCOL-EXTENSION ::= {
--	{ID id-PUSCH-Info-DM-Rprt		CRITICALITY reject				EXTENSION	PUSCH-Info-DM-Rprt		PRESENCE optional}|
	-- TDD only
	-- This PUSCH Information is the for the first PUSCH repetition, PUSCH information for PUSCH repetitions 2 and on, should be defined in Multiple-PUSCH-InfoList-DM-Rprt.
--	{ID id-HSSICH-Info-DM-Rprt		CRITICALITY reject				EXTENSION	HS-SICH-ID				PRESENCE optional}|
	-- TDD only
--	{ ID	id-multiple-PUSCH-InfoList-DM-Rprt	CRITICALITY ignore	EXTENSION Multiple-PUSCH-InfoList-DM-Rprt		PRESENCE optional	},
	-- TDD only, This PUSCH information is the for the 2nd and beyond PUSCH repetitions.
--	...
--}

--PUSCH-Info-DM-Rprt ::= SEQUENCE (SIZE (0..maxNrOfPUSCHs)) OF PUSCH-ID
PUSCH-Info-DM-Rprt ::= SEQUENCE (SIZE (0..256)) OF PUSCH-ID

--Multiple-PUSCH-InfoList-DM-Rprt ::= SEQUENCE (SIZE (1.. maxNrOfPUSCHs-1)) OF Multiple-PUSCH-InfoListIE-DM-Rprt
Multiple-PUSCH-InfoList-DM-Rprt ::= SEQUENCE (SIZE (1.. 255)) OF Multiple-PUSCH-InfoListIE-DM-Rprt
-- Includes the 2nd through the max number of PUSCH information repetitions.

Multiple-PUSCH-InfoListIE-DM-Rprt ::= SEQUENCE {
	pUSCH-ID								PUSCH-ID														OPTIONAL,
	dedicatedMeasurementValue				DedicatedMeasurementValue										OPTIONAL,
--	iE-Extensions							ProtocolExtensionContainer { { Multiple-PUSCH-InfoListIE-DM-Rprt-ExtIEs} }		OPTIONAL,
	iE-Extensions							ProtocolExtensionContainer OPTIONAL,
	...
}

--Multiple-PUSCH-InfoListIE-DM-Rprt-ExtIEs NBAP-PROTOCOL-EXTENSION ::= {
--	...
--}

RL-Set-DM-Rprt ::= SEQUENCE {
	rL-Set-InformationList-DM-Rprt		RL-Set-InformationList-DM-Rprt,
--	iE-Extensions						ProtocolExtensionContainer { { RL-SetItem-DM-Rprt-ExtIEs } }		OPTIONAL,
	iE-Extensions						ProtocolExtensionContainer OPTIONAL,
	...
}

--RL-SetItem-DM-Rprt-ExtIEs  NBAP-PROTOCOL-EXTENSION ::= {
--	...
--}

--RL-Set-InformationList-DM-Rprt ::= SEQUENCE (SIZE (1..maxNrOfRLSets)) OF ProtocolIE-Single-Container {{ RL-Set-InformationItemIE-DM-Rprt }}
RL-Set-InformationList-DM-Rprt ::= SEQUENCE (SIZE (1..16)) OF ProtocolIE-Single-Container

--RL-Set-InformationItemIE-DM-Rprt NBAP-PROTOCOL-IES ::= {
--	{ ID id-RL-Set-InformationItem-DM-Rprt	CRITICALITY ignore	TYPE RL-Set-InformationItem-DM-Rprt		PRESENCE mandatory	}
--}

RL-Set-InformationItem-DM-Rprt ::= SEQUENCE {
	rL-Set-ID						RL-Set-ID,
	dedicatedMeasurementValueInformation	DedicatedMeasurementValueInformation,
--	iE-Extensions					ProtocolExtensionContainer { { RL-Set-InformationItem-DM-Rprt-ExtIEs} } OPTIONAL,
	iE-Extensions					ProtocolExtensionContainer OPTIONAL,
	...
}

--RL-Set-InformationItem-DM-Rprt-ExtIEs NBAP-PROTOCOL-EXTENSION ::= {
--	...
--}

-- **************************************************************
--
-- DEDICATED MEASUREMENT TERMINATION REQUEST
--
-- **************************************************************

--DedicatedMeasurementTerminationRequest ::= SEQUENCE {
--	protocolIEs				ProtocolIE-Container	{{DedicatedMeasurementTerminationRequest-IEs}},
--	protocolExtensions		ProtocolExtensionContainer	{{DedicatedMeasurementTerminationRequest-Extensions}}		OPTIONAL,
--	...
--}
DedicatedMeasurementTerminationRequest ::= SEQUENCE {
	protocolIEs				ProtocolIE-Container,
	protocolExtensions		ProtocolExtensionContainer	OPTIONAL,
	...
}

--DedicatedMeasurementTerminationRequest-IEs NBAP-PROTOCOL-IES ::= {
--	{ ID	id-NodeB-CommunicationContextID			CRITICALITY		ignore			TYPE	NodeB-CommunicationContextID		PRESENCE	mandatory	} |
--	{ ID	id-MeasurementID						CRITICALITY		ignore			TYPE	MeasurementID				PRESENCE	mandatory	},
--	...
--}

--DedicatedMeasurementTerminationRequest-Extensions NBAP-PROTOCOL-EXTENSION ::= {
--	...
--}

-- **************************************************************
--
-- DEDICATED MEASUREMENT FAILURE INDICATION
--
-- **************************************************************

--DedicatedMeasurementFailureIndication ::= SEQUENCE {
--	protocolIEs				ProtocolIE-Container	{{DedicatedMeasurementFailureIndication-IEs}},
--	protocolExtensions		ProtocolExtensionContainer	{{DedicatedMeasurementFailureIndication-Extensions}}		OPTIONAL,
--	...
--}
DedicatedMeasurementFailureIndication ::= SEQUENCE {
	protocolIEs				ProtocolIE-Container,
	protocolExtensions		ProtocolExtensionContainer	OPTIONAL,
	...
}

--DedicatedMeasurementFailureIndication-IEs NBAP-PROTOCOL-IES ::= {
--	{ ID	id-CRNC-CommunicationContextID		CRITICALITY		ignore		TYPE	CRNC-CommunicationContextID		PRESENCE	mandatory	} |
--	{ ID	id-MeasurementID					CRITICALITY		ignore		TYPE	MeasurementID		PRESENCE	mandatory	} |
--	{ ID	id-Cause							CRITICALITY		ignore		TYPE	Cause				PRESENCE	mandatory	},
--	...
--}

--DedicatedMeasurementFailureIndication-Extensions NBAP-PROTOCOL-EXTENSION ::= {
--	...
--}

-- **************************************************************
--
-- RADIO LINK FAILURE INDICATION
--
-- **************************************************************

--RadioLinkFailureIndication ::= SEQUENCE {
--	protocolIEs				ProtocolIE-Container	{{RadioLinkFailureIndication-IEs}},
--	protocolExtensions		ProtocolExtensionContainer	{{RadioLinkFailureIndication-Extensions}}		OPTIONAL,
--	...
--}
RadioLinkFailureIndication ::= SEQUENCE {
	protocolIEs				ProtocolIE-Container,
	protocolExtensions		ProtocolExtensionContainer	OPTIONAL,
	...
}
--RadioLinkFailureIndication-IEs NBAP-PROTOCOL-IES ::= {
--	{ ID	id-CRNC-CommunicationContextID				CRITICALITY ignore			TYPE CRNC-CommunicationContextID			PRESENCE	mandatory	} |
--	{ ID	id-Reporting-Object-RL-FailureInd			CRITICALITY ignore			TYPE Reporting-Object-RL-FailureInd		PRESENCE	mandatory	} ,
--	...
--}

--RadioLinkFailureIndication-Extensions NBAP-PROTOCOL-EXTENSION ::= {
--	...
--}

Reporting-Object-RL-FailureInd ::= CHOICE {
	rL						RL-RL-FailureInd,
	rL-Set					RL-Set-RL-FailureInd, --FDD only
	...,
	cCTrCH					CCTrCH-RL-FailureInd --TDD only
}

RL-RL-FailureInd ::= SEQUENCE {
	rL-InformationList-RL-FailureInd		RL-InformationList-RL-FailureInd,
--	iE-Extensions							ProtocolExtensionContainer { { RLItem-RL-FailureInd-ExtIEs } }		OPTIONAL,
	iE-Extensions							ProtocolExtensionContainer OPTIONAL,
	...
 }

--RLItem-RL-FailureInd-ExtIEs NBAP-PROTOCOL-EXTENSION ::= {
--	...
--}

--RL-InformationList-RL-FailureInd ::= SEQUENCE (SIZE (1..maxNrOfRLs)) OF ProtocolIE-Single-Container {{ RL-InformationItemIE-RL-FailureInd}}
RL-InformationList-RL-FailureInd ::= SEQUENCE (SIZE (1..16)) OF ProtocolIE-Single-Container

--RL-InformationItemIE-RL-FailureInd NBAP-PROTOCOL-IES ::= {
 --	{ ID	id-RL-InformationItem-RL-FailureInd			CRITICALITY		ignore			TYPE	RL-InformationItem-RL-FailureInd			PRESENCE	mandatory}
 --}

RL-InformationItem-RL-FailureInd ::= SEQUENCE {
 	rL-ID										RL-ID,
 	cause										Cause,
--	iE-Extensions								ProtocolExtensionContainer { { RL-InformationItem-RL-FailureInd-ExtIEs } }		OPTIONAL,
	iE-Extensions								ProtocolExtensionContainer OPTIONAL,
	...
 }

--RL-InformationItem-RL-FailureInd-ExtIEs NBAP-PROTOCOL-EXTENSION ::= {
--	...
--}

RL-Set-RL-FailureInd ::= SEQUENCE {
	rL-Set-InformationList-RL-FailureInd	RL-Set-InformationList-RL-FailureInd,
--	iE-Extensions							ProtocolExtensionContainer { { RL-SetItem-RL-FailureInd-ExtIEs } }		OPTIONAL,
	iE-Extensions							ProtocolExtensionContainer OPTIONAL,
	...
 }

--RL-SetItem-RL-FailureInd-ExtIEs NBAP-PROTOCOL-EXTENSION ::= {
--	...
--}

--RL-Set-InformationList-RL-FailureInd ::= SEQUENCE (SIZE (1..maxNrOfRLSets)) OF ProtocolIE-Single-Container {{ RL-Set-InformationItemIE-RL-FailureInd }}
RL-Set-InformationList-RL-FailureInd ::= SEQUENCE (SIZE (1..16)) OF ProtocolIE-Single-Container

--RL-Set-InformationItemIE-RL-FailureInd NBAP-PROTOCOL-IES ::= {
--	{ ID id-RL-Set-InformationItem-RL-FailureInd	CRITICALITY ignore		TYPE RL-Set-InformationItem-RL-FailureInd		PRESENCE mandatory	}
--}

RL-Set-InformationItem-RL-FailureInd ::= SEQUENCE {
 	rL-Set-ID				RL-Set-ID,
 	cause					Cause,
--	iE-Extensions			ProtocolExtensionContainer { { RL-Set-InformationItem-RL-FailureInd-ExtIEs} } OPTIONAL,
	iE-Extensions			ProtocolExtensionContainer OPTIONAL,
	...
}

--RL-Set-InformationItem-RL-FailureInd-ExtIEs NBAP-PROTOCOL-EXTENSION ::= {
--	...
--}

CCTrCH-RL-FailureInd ::= SEQUENCE {
	rL-ID										RL-ID,
	cCTrCH-InformationList-RL-FailureInd		CCTrCH-InformationList-RL-FailureInd,
--	iE-Extensions							ProtocolExtensionContainer { { CCTrCHItem-RL-FailureInd-ExtIEs } }		OPTIONAL,
	iE-Extensions							ProtocolExtensionContainer OPTIONAL,
	...
 }

--CCTrCHItem-RL-FailureInd-ExtIEs NBAP-PROTOCOL-EXTENSION ::= {
--	...
--}

--CCTrCH-InformationList-RL-FailureInd ::= SEQUENCE (SIZE (1..maxNrOfCCTrCHs)) OF ProtocolIE-Single-Container {{ CCTrCH-InformationItemIE-RL-FailureInd}}
CCTrCH-InformationList-RL-FailureInd ::= SEQUENCE (SIZE (1..16)) OF ProtocolIE-Single-Container 

--CCTrCH-InformationItemIE-RL-FailureInd NBAP-PROTOCOL-IES ::= {
--	{ ID	id-CCTrCH-InformationItem-RL-FailureInd			CRITICALITY		ignore			TYPE	CCTrCH-InformationItem-RL-FailureInd			PRESENCE	mandatory}
-- }

CCTrCH-InformationItem-RL-FailureInd ::= SEQUENCE {
 	cCTrCH-ID									CCTrCH-ID,
	cause										Cause,
--	iE-Extensions								ProtocolExtensionContainer { { CCTrCH-InformationItem-RL-FailureInd-ExtIEs } }		OPTIONAL,
	iE-Extensions								ProtocolExtensionContainer OPTIONAL,
	...
 }

--CCTrCH-InformationItem-RL-FailureInd-ExtIEs NBAP-PROTOCOL-EXTENSION ::= {
--	...
--}

-- **************************************************************
--
-- RADIO LINK PREEMPTION REQUIRED INDICATION
--
-- **************************************************************
--RadioLinkPreemptionRequiredIndication ::= SEQUENCE {
--	protocolIEs                     ProtocolIE-Container       {{RadioLinkPreemptionRequiredIndication-IEs}},
--	protocolExtensions              ProtocolExtensionContainer {{RadioLinkPreemptionRequiredIndication-Extensions}}                   OPTIONAL,
--	...
--}
RadioLinkPreemptionRequiredIndication ::= SEQUENCE {
	protocolIEs                     ProtocolIE-Container,
	protocolExtensions              ProtocolExtensionContainer OPTIONAL,
	...
}

--RadioLinkPreemptionRequiredIndication-IEs NBAP-PROTOCOL-IES ::= {
--	{ ID	id-CRNC-CommunicationContextID					CRITICALITY		ignore			TYPE	CRNC-CommunicationContextID				PRESENCE	mandatory		} |
--	{ ID id-RL-InformationList-RL-PreemptRequiredInd	CRITICALITY ignore	TYPE RL-InformationList-RL-PreemptRequiredInd		PRESENCE optional	},
--	...
--}

--RadioLinkPreemptionRequiredIndication-Extensions NBAP-PROTOCOL-EXTENSION ::= {
--	...
--}

--RL-InformationList-RL-PreemptRequiredInd			::= SEQUENCE (SIZE (1..maxNrOfRLs)) OF ProtocolIE-Single-Container { {RL-InformationItemIE-RL-PreemptRequiredInd}}
RL-InformationList-RL-PreemptRequiredInd			::= SEQUENCE (SIZE (1..16)) OF ProtocolIE-Single-Container

--RL-InformationItemIE-RL-PreemptRequiredInd NBAP-PROTOCOL-IES ::= {
--	{ ID id-RL-InformationItem-RL-PreemptRequiredInd		CRITICALITY ignore	TYPE RL-InformationItem-RL-PreemptRequiredInd		PRESENCE mandatory	},
--	...
--}

RL-InformationItem-RL-PreemptRequiredInd::= SEQUENCE {
	rL-ID						RL-ID,
--	iE-Extensions				ProtocolExtensionContainer { {RL-InformationItem-RL-PreemptRequiredInd-ExtIEs} } OPTIONAL,
	iE-Extensions				ProtocolExtensionContainer OPTIONAL,
	...
}

--RL-InformationItem-RL-PreemptRequiredInd-ExtIEs NBAP-PROTOCOL-EXTENSION ::= {
--	...
--}

-- **************************************************************
--
-- RADIO LINK RESTORE INDICATION
--
-- **************************************************************

--RadioLinkRestoreIndication ::= SEQUENCE {
--	protocolIEs				ProtocolIE-Container	{{RadioLinkRestoreIndication-IEs}},
--	protocolExtensions		ProtocolExtensionContainer	{{RadioLinkRestoreIndication-Extensions}}		OPTIONAL,
--	...
--}
RadioLinkRestoreIndication ::= SEQUENCE {
	protocolIEs				ProtocolIE-Container,
	protocolExtensions		ProtocolExtensionContainer	OPTIONAL,
	...
}
--RadioLinkRestoreIndication-IEs NBAP-PROTOCOL-IES ::= {
--	{ ID	id-CRNC-CommunicationContextID			CRITICALITY ignore	TYPE CRNC-CommunicationContextID		PRESENCE	mandatory	} |
--	{ ID	id-Reporting-Object-RL-RestoreInd		CRITICALITY ignore	TYPE Reporting-Object-RL-RestoreInd		PRESENCE	mandatory	},
--	...
--}

--RadioLinkRestoreIndication-Extensions NBAP-PROTOCOL-EXTENSION ::= {
--	...
--}

Reporting-Object-RL-RestoreInd ::= CHOICE {
	rL						RL-RL-RestoreInd, --TDD only
	rL-Set					RL-Set-RL-RestoreInd, --FDD only
	...,
	cCTrCH					CCTrCH-RL-RestoreInd --TDD only
}

RL-RL-RestoreInd ::= SEQUENCE {
	rL-InformationList-RL-RestoreInd		RL-InformationList-RL-RestoreInd,
--	iE-Extensions							ProtocolExtensionContainer { { RLItem-RL-RestoreInd-ExtIEs } }		OPTIONAL,
	iE-Extensions							ProtocolExtensionContainer OPTIONAL,
	...
 }

--RLItem-RL-RestoreInd-ExtIEs NBAP-PROTOCOL-EXTENSION ::= {
--	...
--}

--RL-InformationList-RL-RestoreInd ::= SEQUENCE (SIZE (1..maxNrOfRLs)) OF ProtocolIE-Single-Container {{RL-InformationItemIE-RL-RestoreInd}}
RL-InformationList-RL-RestoreInd ::= SEQUENCE (SIZE (1..16)) OF ProtocolIE-Single-Container

--RL-InformationItemIE-RL-RestoreInd NBAP-PROTOCOL-IES ::= {
--	{ ID	id-RL-InformationItem-RL-RestoreInd		CRITICALITY ignore		TYPE	RL-InformationItem-RL-RestoreInd			PRESENCE	mandatory}
-- }

RL-InformationItem-RL-RestoreInd ::= SEQUENCE {
 	rL-ID									RL-ID,
--	iE-Extensions							ProtocolExtensionContainer { { RL-InformationItem-RL-RestoreInd-ExtIEs } }		OPTIONAL,
	iE-Extensions							ProtocolExtensionContainer OPTIONAL,
	...
 }

--RL-InformationItem-RL-RestoreInd-ExtIEs NBAP-PROTOCOL-EXTENSION ::= {
--	...
--}

RL-Set-RL-RestoreInd ::= SEQUENCE {
	rL-Set-InformationList-RL-RestoreInd	RL-Set-InformationList-RL-RestoreInd,
--	iE-Extensions							ProtocolExtensionContainer { { RL-SetItem-RL-RestoreInd-ExtIEs } }		OPTIONAL,
	iE-Extensions							ProtocolExtensionContainer OPTIONAL,
	...
 }

--RL-SetItem-RL-RestoreInd-ExtIEs NBAP-PROTOCOL-EXTENSION ::= {
--	...
--}

--RL-Set-InformationList-RL-RestoreInd ::= SEQUENCE (SIZE (1..maxNrOfRLSets)) OF ProtocolIE-Single-Container {{ RL-Set-InformationItemIE-RL-RestoreInd }}
RL-Set-InformationList-RL-RestoreInd ::= SEQUENCE (SIZE (1..16)) OF ProtocolIE-Single-Container

--RL-Set-InformationItemIE-RL-RestoreInd NBAP-PROTOCOL-IES ::= {
 --	{ ID id-RL-Set-InformationItem-RL-RestoreInd	CRITICALITY ignore		TYPE RL-Set-InformationItem-RL-RestoreInd	PRESENCE mandatory	}
 --}

RL-Set-InformationItem-RL-RestoreInd ::= SEQUENCE {
 	rL-Set-ID				RL-Set-ID,
-- 	iE-Extensions			ProtocolExtensionContainer { { RL-Set-InformationItem-RL-RestoreInd-ExtIEs} } OPTIONAL,
	iE-Extensions			ProtocolExtensionContainer OPTIONAL,
	...
}

--RL-Set-InformationItem-RL-RestoreInd-ExtIEs NBAP-PROTOCOL-EXTENSION ::= {
--	...
--}

CCTrCH-RL-RestoreInd ::= SEQUENCE {
	rL-ID										RL-ID,
	cCTrCH-InformationList-RL-RestoreInd		CCTrCH-InformationList-RL-RestoreInd,
--	iE-Extensions							ProtocolExtensionContainer { { CCTrCHItem-RL-RestoreInd-ExtIEs } }		OPTIONAL,
	iE-Extensions							ProtocolExtensionContainer OPTIONAL,
	...
 }

--CCTrCHItem-RL-RestoreInd-ExtIEs NBAP-PROTOCOL-EXTENSION ::= {
--	...
--}

--CCTrCH-InformationList-RL-RestoreInd ::= SEQUENCE (SIZE (1..maxNrOfCCTrCHs)) OF ProtocolIE-Single-Container {{ CCTrCH-InformationItemIE-RL-RestoreInd}}
CCTrCH-InformationList-RL-RestoreInd ::= SEQUENCE (SIZE (1..16)) OF ProtocolIE-Single-Container

--CCTrCH-InformationItemIE-RL-RestoreInd NBAP-PROTOCOL-IES ::= {
--	{ ID id-CCTrCH-InformationItem-RL-RestoreInd	CRITICALITY ignore	TYPE CCTrCH-InformationItem-RL-RestoreInd		PRESENCE	mandatory }
--}

CCTrCH-InformationItem-RL-RestoreInd ::= SEQUENCE {
	cCTrCH-ID										CCTrCH-ID,
--	iE-Extensions								ProtocolExtensionContainer { { CCTrCH-InformationItem-RL-RestoreInd-ExtIEs } }		OPTIONAL,
	iE-Extensions								ProtocolExtensionContainer OPTIONAL,
	...
 }

--CCTrCH-InformationItem-RL-RestoreInd-ExtIEs NBAP-PROTOCOL-EXTENSION ::= {
--	...
--}

-- **************************************************************
--
-- COMPRESSED MODE COMMAND FDD
--
-- **************************************************************

--CompressedModeCommand ::= SEQUENCE {
--	protocolIEs				ProtocolIE-Container	{{CompressedModeCommand-IEs}},
--	protocolExtensions		ProtocolExtensionContainer	{{CompressedModeCommand-Extensions}}                   OPTIONAL,
--	...
--}
CompressedModeCommand ::= SEQUENCE {
	protocolIEs				ProtocolIE-Container,
	protocolExtensions		ProtocolExtensionContainer OPTIONAL,
	...
}

--CompressedModeCommand-IEs NBAP-PROTOCOL-IES ::= {
--	{ ID 	id-NodeB-CommunicationContextID			CRITICALITY 		ignore		TYPE 	NodeB-CommunicationContextID				PRESENCE 	mandatory	} |
--	{ ID 	id-Active-Pattern-Sequence-Information	CRITICALITY 		ignore		TYPE 	Active-Pattern-Sequence-Information		PRESENCE mandatory },
--	...
--}

--CompressedModeCommand-Extensions NBAP-PROTOCOL-EXTENSION ::= {
--	...
--}


-- **************************************************************
--
-- ERROR INDICATION
--
-- **************************************************************

--ErrorIndication ::= SEQUENCE {
--	protocolIEs				ProtocolIE-Container	{{ErrorIndication-IEs}},
--	protocolExtensions		ProtocolExtensionContainer	{{ErrorIndication-Extensions}}		OPTIONAL,
--	...
--}
ErrorIndication ::= SEQUENCE {
	protocolIEs				ProtocolIE-Container,
	protocolExtensions		ProtocolExtensionContainer	OPTIONAL,
	...
}

--ErrorIndication-IEs NBAP-PROTOCOL-IES ::= {
--	{ ID	id-CRNC-CommunicationContextID		CRITICALITY		ignore			TYPE 	CRNC-CommunicationContextID			PRESENCE	optional	} |
--	{ ID	id-NodeB-CommunicationContextID		CRITICALITY		ignore			TYPE 	NodeB-CommunicationContextID		PRESENCE	optional	} |
--	{ ID	id-Cause							CRITICALITY		ignore			TYPE	Cause				PRESENCE	optional	} |
--	{ ID	id-CriticalityDiagnostics			CRITICALITY		ignore			TYPE	CriticalityDiagnostics			PRESENCE	optional	},
--	...
--}

--ErrorIndication-Extensions NBAP-PROTOCOL-EXTENSION ::= {
--	...
--}

-- **************************************************************
--
-- PRIVATE MESSAGE
--
-- **************************************************************

--PrivateMessage ::= SEQUENCE {
--	privateIEs		PrivateIE-Container	{{PrivateMessage-IEs}},
--	...
--}
PrivateMessage ::= SEQUENCE {
	privateIEs		PrivateIE-Container,
	...
}

--PrivateMessage-IEs NBAP-PRIVATE-IES ::= {
--	...
--}
-- **************************************************************
--
-- PHYSICAL SHARED CHANNEL RECONFIGURATION REQUEST FDD
--
-- **************************************************************

--PhysicalSharedChannelReconfigurationRequestFDD ::= SEQUENCE {
--	protocolIEs			ProtocolIE-Container  {{PhysicalSharedChannelReconfigurationRequestFDD-IEs}},
--	protocolExtensions    ProtocolExtensionContainer {{PhysicalSharedChannelReconfigurationRequestFDD-Extensions}}    OPTIONAL,
--	...
--}
PhysicalSharedChannelReconfigurationRequestFDD ::= SEQUENCE {
	protocolIEs			ProtocolIE-Container,
	protocolExtensions    ProtocolExtensionContainer OPTIONAL,
	...
}
--PhysicalSharedChannelReconfigurationRequestFDD-IEs NBAP-PROTOCOL-IES ::= {
--	{ ID id-C-ID											CRITICALITY reject	TYPE C-ID							PRESENCE mandatory }|
--	{ ID id-ConfigurationGenerationID						CRITICALITY reject	TYPE ConfigurationGenerationID					PRESENCE mandatory }|
--	{ ID id-SFN												CRITICALITY reject	TYPE SFN							PRESENCE optional }|
--	{ ID id-HS-PDSCH-HS-SCCH-E-AGCH-E-RGCH-E-HICH-MaxPower-PSCH-ReconfRqst		CRITICALITY reject	TYPE MaximumTransmissionPower					PRESENCE optional }|
--	{ ID id-HS-PDSCH-HS-SCCH-ScramblingCode-PSCH-ReconfRqst	CRITICALITY reject	TYPE DL-ScramblingCode					PRESENCE optional }|
--	{ ID id-HS-PDSCH-FDD-Code-Information-PSCH-ReconfRqst	CRITICALITY reject	TYPE HS-PDSCH-FDD-Code-Information					PRESENCE optional }|
--	{ ID id-HS-SCCH-FDD-Code-Information-PSCH-ReconfRqst	CRITICALITY reject	TYPE HS-SCCH-FDD-Code-Information					PRESENCE optional },
--	...
--}

--PhysicalSharedChannelReconfigurationRequestFDD-Extensions NBAP-PROTOCOL-EXTENSION ::= {
--	{ ID id-E-AGCH-And-E-RGCH-E-HICH-FDD-Scrambling-Code		CRITICALITY reject	EXTENSION DL-ScramblingCode										PRESENCE optional }|
--	{ ID id-E-AGCH-FDD-Code-Information							CRITICALITY reject	EXTENSION E-AGCH-FDD-Code-Information								PRESENCE optional }|
--	{ ID id-E-RGCH-E-HICH-FDD-Code-Information					CRITICALITY reject	EXTENSION E-RGCH-E-HICH-FDD-Code-Information					PRESENCE optional }|
--	{ID id-HSDPA-And-EDCH-CellPortion-Information-PSCH-ReconfRqst	CRITICALITY reject	EXTENSION HSDPA-And-EDCH-CellPortion-InformationList-PSCH-ReconfRqst		PRESENCE optional }|
--	{ID id-Maximum-Target-ReceivedTotalWideBandPower				CRITICALITY reject	EXTENSION Maximum-Target-ReceivedTotalWideBandPower PRESENCE optional }|
--	{ID id-Reference-ReceivedTotalWideBandPower				CRITICALITY ignore	EXTENSION Reference-ReceivedTotalWideBandPower PRESENCE optional }|
--	{ID id-Target-NonServing-EDCH-To-Total-EDCH-Power-Ratio		CRITICALITY	reject	EXTENSION Target-NonServing-EDCH-To-Total-EDCH-Power-Ratio		PRESENCE optional },
--	...
--}


--HSDPA-And-EDCH-CellPortion-Information-PSCH-ReconfRqst ::= ProtocolIE-Single-Container {{ HSDPA-And-EDCH-CellPortion-InformationListIE-PSCH-ReconfRqst }}
HSDPA-And-EDCH-CellPortion-Information-PSCH-ReconfRqst ::= ProtocolIE-Single-Container

--HSDPA-And-EDCH-CellPortion-InformationListIE-PSCH-ReconfRqst NBAP-PROTOCOL-IES ::= {
--	{ ID id-HSDPA-And-EDCH-CellPortion-InformationList-PSCH-ReconfRqst	CRITICALITY reject	TYPE HSDPA-And-EDCH-CellPortion-InformationItem-PSCH-ReconfRqst		PRESENCE mandatory }
--}

--HSDPA-And-EDCH-CellPortion-InformationList-PSCH-ReconfRqst ::= SEQUENCE (SIZE (1..maxNrOfCellPortionsPerCell)) OF HSDPA-And-EDCH-CellPortion-InformationItem-PSCH-ReconfRqst
HSDPA-And-EDCH-CellPortion-InformationList-PSCH-ReconfRqst ::= SEQUENCE (SIZE (1..64)) OF HSDPA-And-EDCH-CellPortion-InformationItem-PSCH-ReconfRqst

HSDPA-And-EDCH-CellPortion-InformationItem-PSCH-ReconfRqst::= SEQUENCE {
	cellPortionID														CellPortionID,
	hS-PDSCH-HS-SCCH-ScramblingCode-PSCH-ReconfRqst						DL-ScramblingCode				OPTIONAL,
	hS-PDSCH-FDD-Code-Information-PSCH-ReconfRqst						HS-PDSCH-FDD-Code-Information		OPTIONAL,
	hS-SCCH-FDD-Code-Information-PSCH-ReconfRqst						HS-SCCH-FDD-Code-Information		OPTIONAL,
	hS-PDSCH-HS-SCCH-E-AGCH-E-RGCH-E-HICH-MaxPower-PSCH-ReconfRqst		MaximumTransmissionPower		OPTIONAL,
--	iE-Extensions														ProtocolExtensionContainer { { HSDPA-And-EDCH-CellPortion-InformationItem-PSCH-ReconfRqst-ExtIEs} }	OPTIONAL,
	iE-Extensions														ProtocolExtensionContainer OPTIONAL,
	...
}

--HSDPA-And-EDCH-CellPortion-InformationItem-PSCH-ReconfRqst-ExtIEs NBAP-PROTOCOL-EXTENSION ::= {
--...
--}

-- **************************************************************
--
-- PHYSICAL SHARED CHANNEL RECONFIGURATION REQUEST TDD
--
-- **************************************************************

--PhysicalSharedChannelReconfigurationRequestTDD ::= SEQUENCE {
--	protocolIEs			ProtocolIE-Container  {{PhysicalSharedChannelReconfigurationRequestTDD-IEs}},
--	protocolExtensions    ProtocolExtensionContainer {{PhysicalSharedChannelReconfigurationRequestTDD-Extensions}}    OPTIONAL,
--	...
--}
PhysicalSharedChannelReconfigurationRequestTDD ::= SEQUENCE {
	protocolIEs			ProtocolIE-Container,
	protocolExtensions    ProtocolExtensionContainer OPTIONAL,
	...
}
--PhysicalSharedChannelReconfigurationRequestTDD-IEs NBAP-PROTOCOL-IES ::= {
--	{ ID id-C-ID									CRITICALITY reject	TYPE C-ID						PRESENCE mandatory }|
--	{ ID id-SFN										CRITICALITY reject	TYPE SFN						PRESENCE optional }|
--	{ ID id-PDSCHSets-AddList-PSCH-ReconfRqst		CRITICALITY reject	TYPE PDSCHSets-AddList-PSCH-ReconfRqst		PRESENCE optional }|
--	{ ID id-PDSCHSets-ModifyList-PSCH-ReconfRqst	CRITICALITY reject	TYPE PDSCHSets-ModifyList-PSCH-ReconfRqst		PRESENCE optional }|
--	{ ID id-PDSCHSets-DeleteList-PSCH-ReconfRqst	CRITICALITY reject	TYPE PDSCHSets-DeleteList-PSCH-ReconfRqst		PRESENCE optional }|
--	{ ID id-PUSCHSets-AddList-PSCH-ReconfRqst		CRITICALITY reject	TYPE PUSCHSets-AddList-PSCH-ReconfRqst		PRESENCE optional }|
--	{ ID id-PUSCHSets-ModifyList-PSCH-ReconfRqst	CRITICALITY reject	TYPE PUSCHSets-ModifyList-PSCH-ReconfRqst		PRESENCE optional }|
--	{ ID id-PUSCHSets-DeleteList-PSCH-ReconfRqst	CRITICALITY reject	TYPE PUSCHSets-DeleteList-PSCH-ReconfRqst		PRESENCE optional },
--	...
--}

--PhysicalSharedChannelReconfigurationRequestTDD-Extensions NBAP-PROTOCOL-EXTENSION ::= {
--	{ ID id-HS-PDSCH-TDD-Information-PSCH-ReconfRqst			CRITICALITY reject	EXTENSION HS-PDSCH-TDD-Information-PSCH-ReconfRqst			PRESENCE optional } |
--	{ ID id-Add-To-HS-SCCH-Resource-Pool-PSCH-ReconfRqst		CRITICALITY reject	EXTENSION Add-To-HS-SCCH-Resource-Pool-PSCH-ReconfRqst			PRESENCE optional } |
--	{ ID id-Modify-HS-SCCH-Resource-Pool-PSCH-ReconfRqst		CRITICALITY reject	EXTENSION Modify-HS-SCCH-Resource-Pool-PSCH-ReconfRqst			PRESENCE optional } |
--	{ ID id-Delete-From-HS-SCCH-Resource-Pool-PSCH-ReconfRqst	CRITICALITY reject	EXTENSION Delete-From-HS-SCCH-Resource-Pool-PSCH-ReconfRqst		PRESENCE optional } |
--	{ ID id-ConfigurationGenerationID						CRITICALITY reject	EXTENSION ConfigurationGenerationID				PRESENCE optional },
--	...
--}

--PDSCHSets-AddList-PSCH-ReconfRqst ::= SEQUENCE (SIZE (1..maxNrOfPDSCHSets)) OF PDSCHSets-AddItem-PSCH-ReconfRqst
PDSCHSets-AddList-PSCH-ReconfRqst ::= SEQUENCE (SIZE (1..256)) OF PDSCHSets-AddItem-PSCH-ReconfRqst

PDSCHSets-AddItem-PSCH-ReconfRqst	 ::= SEQUENCE {
	pDSCHSet-ID									PDSCHSet-ID,
	pDSCH-InformationList						PDSCH-Information-AddList-PSCH-ReconfRqst 	OPTIONAL,	-- Mandatory for 3.84Mcps TDD. Not Applicable to 1.28Mcps TDD
--	iE-Extensions								ProtocolExtensionContainer { {PDSCHSets-AddItem-PSCH-ReconfRqst-ExtIEs} }		OPTIONAL,
	iE-Extensions								ProtocolExtensionContainer OPTIONAL,
	...
}

--PDSCHSets-AddItem-PSCH-ReconfRqst-ExtIEs  NBAP-PROTOCOL-EXTENSION ::= {
--	{ID id-PDSCH-AddInformation-LCR-PSCH-ReconfRqst 	CRITICALITY	reject		EXTENSION 	PDSCH-AddInformation-LCR-AddItem-PSCH-ReconfRqst			PRESENCE	optional},
 -- Mandatory for 1.28Mcps TDD. Not Applicable to 3.84Mcps TDD
--	...
--}

--PDSCH-Information-AddList-PSCH-ReconfRqst ::= ProtocolIE-Single-Container {{ PDSCH-Information-AddListIEs-PSCH-ReconfRqst }}
PDSCH-Information-AddList-PSCH-ReconfRqst ::= ProtocolIE-Single-Container
-- Mandatory for 3.84Mcps TDD, Not Applicable to 1.28Mcps TDD

--PDSCH-Information-AddListIEs-PSCH-ReconfRqst	NBAP-PROTOCOL-IES ::= { 
--	{ID id-PDSCH-Information-AddListIE-PSCH-ReconfRqst 	CRITICALITY	reject		TYPE 	PDSCH-Information-AddItem-PSCH-ReconfRqst			PRESENCE	mandatory}
--}

PDSCH-Information-AddItem-PSCH-ReconfRqst ::= SEQUENCE {
	repetitionPeriod						RepetitionPeriod,
	repetitionLength						RepetitionLength,
	tdd-PhysicalChannelOffset				TDD-PhysicalChannelOffset,
	dL-Timeslot-InformationAddList-PSCH-ReconfRqst				DL-Timeslot-InformationAddList-PSCH-ReconfRqst,
--	iE-Extensions							ProtocolExtensionContainer { {PDSCH-Information-AddItem-PSCH-ReconfRqst-ExtIEs} }		OPTIONAL,
	iE-Extensions							ProtocolExtensionContainer OPTIONAL,
	...
	}

--PDSCH-Information-AddItem-PSCH-ReconfRqst-ExtIEs  NBAP-PROTOCOL-EXTENSION ::= {
--	...
--}

--DL-Timeslot-InformationAddList-PSCH-ReconfRqst ::= SEQUENCE (SIZE (1.. maxNrOfDLTSs)) OF DL-Timeslot-InformationAddItem-PSCH-ReconfRqst
DL-Timeslot-InformationAddList-PSCH-ReconfRqst ::= SEQUENCE (SIZE (1.. 15)) OF DL-Timeslot-InformationAddItem-PSCH-ReconfRqst

DL-Timeslot-InformationAddItem-PSCH-ReconfRqst ::= SEQUENCE {
	timeSlot								TimeSlot,
	midambleShiftAndBurstType				MidambleShiftAndBurstType,
	tFCI-Presence							TFCI-Presence,
	dL-Code-InformationAddList-PSCH-ReconfRqst				DL-Code-InformationAddList-PSCH-ReconfRqst,
--	iE-Extensions							ProtocolExtensionContainer { { DL-Timeslot-InformationAddItem-PSCH-ReconfRqst-ExtIEs} }		OPTIONAL,
	iE-Extensions							ProtocolExtensionContainer OPTIONAL,
	...
}

--DL-Timeslot-InformationAddItem-PSCH-ReconfRqst-ExtIEs NBAP-PROTOCOL-EXTENSION ::= {
--	...
--}

--DL-Code-InformationAddList-PSCH-ReconfRqst ::= SEQUENCE (SIZE (1..maxNrOfPDSCHs)) OF DL-Code-InformationAddItem-PSCH-ReconfRqst
DL-Code-InformationAddList-PSCH-ReconfRqst ::= SEQUENCE (SIZE (1..256)) OF DL-Code-InformationAddItem-PSCH-ReconfRqst

DL-Code-InformationAddItem-PSCH-ReconfRqst ::= SEQUENCE {
	pDSCH-ID								PDSCH-ID,
	tdd-ChannelisationCode					TDD-ChannelisationCode,
--	iE-Extensions							ProtocolExtensionContainer { { DL-Code-InformationAddItem-PSCH-ReconfRqst-ExtIEs} }		OPTIONAL,
	iE-Extensions							ProtocolExtensionContainer OPTIONAL,
	...
}

--DL-Code-InformationAddItem-PSCH-ReconfRqst-ExtIEs NBAP-PROTOCOL-EXTENSION ::= {
--	...
--}

PDSCH-AddInformation-LCR-AddItem-PSCH-ReconfRqst ::= SEQUENCE {
	repetitionPeriod						RepetitionPeriod,
	repetitionLength						RepetitionLength,
	tdd-PhysicalChannelOffset				TDD-PhysicalChannelOffset,
	dL-Timeslot-InformationAddList-LCR-PSCH-ReconfRqst				DL-Timeslot-InformationAddList-LCR-PSCH-ReconfRqst,
--	iE-Extensions								ProtocolExtensionContainer { {PDSCH-AddInformation-LCR-AddItem-PSCH-ReconfRqst-ExtIEs} }		OPTIONAL,
	iE-Extensions								ProtocolExtensionContainer OPTIONAL,
	...
	}

--PDSCH-AddInformation-LCR-AddItem-PSCH-ReconfRqst-ExtIEs  NBAP-PROTOCOL-EXTENSION ::= {
--{ID	id-Tstd-indicator			CRITICALITY	reject		EXTENSION 	TSTD-Indicator		PRESENCE 	optional	},
	-- Applicable to 1.28Mcps TDD only
--	...
--}

--DL-Timeslot-InformationAddList-LCR-PSCH-ReconfRqst ::= SEQUENCE (SIZE (1.. maxNrOfDLTSLCRs)) OF DL-Timeslot-InformationAddItem-LCR-PSCH-ReconfRqst
DL-Timeslot-InformationAddList-LCR-PSCH-ReconfRqst ::= SEQUENCE (SIZE (1.. 6)) OF DL-Timeslot-InformationAddItem-LCR-PSCH-ReconfRqst

DL-Timeslot-InformationAddItem-LCR-PSCH-ReconfRqst ::= SEQUENCE {
	timeSlotLCR								TimeSlotLCR,
	midambleShiftLCR						MidambleShiftLCR,
	tFCI-Presence							TFCI-Presence,
	dL-Code-InformationAddList-LCR-PSCH-ReconfRqst				DL-Code-InformationAddList-LCR-PSCH-ReconfRqst,
--	iE-Extensions							ProtocolExtensionContainer { { DL-Timeslot-InformationAddItem-LCR-PSCH-ReconfRqst-ExtIEs} }		OPTIONAL,
	iE-Extensions							ProtocolExtensionContainer OPTIONAL,
	...
}

--DL-Timeslot-InformationAddItem-LCR-PSCH-ReconfRqst-ExtIEs NBAP-PROTOCOL-EXTENSION ::= {
--	...
--}

--DL-Code-InformationAddList-LCR-PSCH-ReconfRqst ::= SEQUENCE (SIZE (1..maxNrOfPDSCHs)) OF DL-Code-InformationAddItem-LCR-PSCH-ReconfRqst
DL-Code-InformationAddList-LCR-PSCH-ReconfRqst ::= SEQUENCE (SIZE (1..256)) OF DL-Code-InformationAddItem-LCR-PSCH-ReconfRqst

DL-Code-InformationAddItem-LCR-PSCH-ReconfRqst ::= SEQUENCE {
	pDSCH-ID								PDSCH-ID,
	tdd-ChannelisationCodeLCR				TDD-ChannelisationCodeLCR,
--	iE-Extensions							ProtocolExtensionContainer { { DL-Code-InformationAddItem-LCR-PSCH-ReconfRqst-ExtIEs} }		OPTIONAL,
	iE-Extensions							ProtocolExtensionContainer OPTIONAL,
	...
}

--DL-Code-InformationAddItem-LCR-PSCH-ReconfRqst-ExtIEs NBAP-PROTOCOL-EXTENSION ::= {
--	...
--}

--PDSCHSets-ModifyList-PSCH-ReconfRqst ::= SEQUENCE (SIZE (1..maxNrOfPDSCHSets)) OF PDSCHSets-ModifyItem-PSCH-ReconfRqst
PDSCHSets-ModifyList-PSCH-ReconfRqst ::= SEQUENCE (SIZE (1..256)) OF PDSCHSets-ModifyItem-PSCH-ReconfRqst

PDSCHSets-ModifyItem-PSCH-ReconfRqst	 ::= SEQUENCE {
	pDSCHSet-ID									PDSCHSet-ID,
	pDSCH-InformationList						PDSCH-Information-ModifyList-PSCH-ReconfRqst,
--	iE-Extensions								ProtocolExtensionContainer { {PDSCHSets-ModifyItem-PSCH-ReconfRqst-ExtIEs} }		OPTIONAL,
	iE-Extensions								ProtocolExtensionContainer OPTIONAL,
	...
}

--PDSCHSets-ModifyItem-PSCH-ReconfRqst-ExtIEs  NBAP-PROTOCOL-EXTENSION ::= {
--	...
--}

--PDSCH-Information-ModifyList-PSCH-ReconfRqst ::= ProtocolIE-Single-Container {{ PDSCH-Information-ModifyListIEs-PSCH-ReconfRqst }}
PDSCH-Information-ModifyList-PSCH-ReconfRqst ::= ProtocolIE-Single-Container

--PDSCH-Information-ModifyListIEs-PSCH-ReconfRqst NBAP-PROTOCOL-IES ::= {
--	{ID id-PDSCH-Information-ModifyListIE-PSCH-ReconfRqst	CRITICALITY reject	TYPE PDSCH-Information-ModifyItem-PSCH-ReconfRqst			PRESENCE	optional}|
--	{ID id-PDSCH-ModifyInformation-LCR-PSCH-ReconfRqst		CRITICALITY reject	TYPE PDSCH-ModifyInformation-LCR-ModifyItem-PSCH-ReconfRqst			PRESENCE	optional}
--
--}

PDSCH-Information-ModifyItem-PSCH-ReconfRqst ::= SEQUENCE {
	repetitionPeriod									RepetitionPeriod								OPTIONAL,
	repetitionLength									RepetitionLength								OPTIONAL,
	tdd-PhysicalChannelOffset							TDD-PhysicalChannelOffset						OPTIONAL,
	dL-Timeslot-InformationModifyList-PSCH-ReconfRqst	DL-Timeslot-InformationModifyList-PSCH-ReconfRqst		OPTIONAL,
--	iE-Extensions								ProtocolExtensionContainer { {PDSCH-Information-ModifyItem-PSCH-ReconfRqst-ExtIEs} }		OPTIONAL,
	iE-Extensions								ProtocolExtensionContainer OPTIONAL,
	...
	}

--PDSCH-Information-ModifyItem-PSCH-ReconfRqst-ExtIEs  NBAP-PROTOCOL-EXTENSION ::= {
--	...
--}

--DL-Timeslot-InformationModifyList-PSCH-ReconfRqst ::= SEQUENCE (SIZE (1.. maxNrOfDLTSs)) OF DL-Timeslot-InformationModifyItem-PSCH-ReconfRqst
DL-Timeslot-InformationModifyList-PSCH-ReconfRqst ::= SEQUENCE (SIZE (1.. 15)) OF DL-Timeslot-InformationModifyItem-PSCH-ReconfRqst

DL-Timeslot-InformationModifyItem-PSCH-ReconfRqst ::= SEQUENCE {
	timeSlot								TimeSlot,
	midambleShiftAndBurstType				MidambleShiftAndBurstType	OPTIONAL,
	tFCI-Presence							TFCI-Presence	OPTIONAL,
	dL-Code-InformationModifyList-PSCH-ReconfRqst				DL-Code-InformationModifyList-PSCH-ReconfRqst		OPTIONAL,
--	iE-Extensions							ProtocolExtensionContainer { { DL-Timeslot-InformationModifyItem-PSCH-ReconfRqst-ExtIEs} }		OPTIONAL,
	iE-Extensions							ProtocolExtensionContainer OPTIONAL,
	...
}

--DL-Timeslot-InformationModifyItem-PSCH-ReconfRqst-ExtIEs NBAP-PROTOCOL-EXTENSION ::= {
--	...
--}

--DL-Code-InformationModifyList-PSCH-ReconfRqst ::= SEQUENCE (SIZE (1..maxNrOfPDSCHs)) OF DL-Code-InformationModifyItem-PSCH-ReconfRqst
DL-Code-InformationModifyList-PSCH-ReconfRqst ::= SEQUENCE (SIZE (1..256)) OF DL-Code-InformationModifyItem-PSCH-ReconfRqst

DL-Code-InformationModifyItem-PSCH-ReconfRqst ::= SEQUENCE {
	pDSCH-ID								PDSCH-ID,
	tdd-ChannelisationCode					TDD-ChannelisationCode,
--	iE-Extensions							ProtocolExtensionContainer { { DL-Code-InformationModifyItem-PSCH-ReconfRqst-ExtIEs} }		OPTIONAL,
	iE-Extensions							ProtocolExtensionContainer OPTIONAL,
	...
}

--DL-Code-InformationModifyItem-PSCH-ReconfRqst-ExtIEs NBAP-PROTOCOL-EXTENSION ::= {
--	...
--}

PDSCH-ModifyInformation-LCR-ModifyItem-PSCH-ReconfRqst ::= SEQUENCE {
	repetitionPeriod											RepetitionPeriod							OPTIONAL,
	repetitionLength											RepetitionLength							OPTIONAL,
	tdd-PhysicalChannelOffset									TDD-PhysicalChannelOffset					OPTIONAL,
	dL-Timeslot-LCR-InformationModifyList-PSCH-ReconfRqst		DL-Timeslot-LCR-InformationModifyList-PSCH-ReconfRqst		OPTIONAL,
--	iE-Extensions								ProtocolExtensionContainer { {PDSCH-ModifyInformation-LCR-ModifyListIE-PSCH-ReconfRqst-ExtIEs} }		OPTIONAL,
	iE-Extensions								ProtocolExtensionContainer OPTIONAL,
	...
	}

--PDSCH-ModifyInformation-LCR-ModifyListIE-PSCH-ReconfRqst-ExtIEs NBAP-PROTOCOL-EXTENSION ::= {
--	...
--}

--DL-Timeslot-LCR-InformationModifyList-PSCH-ReconfRqst ::= SEQUENCE (SIZE (1.. maxNrOfDLTSLCRs)) OF DL-Timeslot-LCR-InformationModifyItem-PSCH-ReconfRqst
DL-Timeslot-LCR-InformationModifyList-PSCH-ReconfRqst ::= SEQUENCE (SIZE (1.. 6)) OF DL-Timeslot-LCR-InformationModifyItem-PSCH-ReconfRqst

DL-Timeslot-LCR-InformationModifyItem-PSCH-ReconfRqst ::= SEQUENCE {
	timeSlotLCR												TimeSlotLCR,
	midambleShiftLCR										MidambleShiftLCR	OPTIONAL,
	tFCI-Presence											TFCI-Presence	OPTIONAL,
	dL-Code-LCR-InformationModifyList-PSCH-ReconfRqst		DL-Code-LCR-InformationModifyList-PSCH-ReconfRqst		OPTIONAL,
--	iE-Extensions							ProtocolExtensionContainer { { DL-Timeslot-LCR-InformationModifyItem-PSCH-ReconfRqst-ExtIEs} }		OPTIONAL,
	iE-Extensions							ProtocolExtensionContainer OPTIONAL,
	...
}

--DL-Timeslot-LCR-InformationModifyItem-PSCH-ReconfRqst-ExtIEs NBAP-PROTOCOL-EXTENSION ::= {
--	...
--}

--DL-Code-LCR-InformationModifyList-PSCH-ReconfRqst ::= SEQUENCE (SIZE (1..maxNrOfPDSCHs)) OF DL-Code-LCR-InformationModifyItem-PSCH-ReconfRqst
DL-Code-LCR-InformationModifyList-PSCH-ReconfRqst ::= SEQUENCE (SIZE (1..256)) OF DL-Code-LCR-InformationModifyItem-PSCH-ReconfRqst

DL-Code-LCR-InformationModifyItem-PSCH-ReconfRqst ::= SEQUENCE {
	pDSCH-ID								PDSCH-ID,
	tdd-ChannelisationCodeLCR				TDD-ChannelisationCodeLCR,
--	iE-Extensions							ProtocolExtensionContainer { { DL-Code-LCR-InformationModifyItem-PSCH-ReconfRqst-ExtIEs} }		OPTIONAL,
	iE-Extensions							ProtocolExtensionContainer OPTIONAL,
	...
}

--DL-Code-LCR-InformationModifyItem-PSCH-ReconfRqst-ExtIEs NBAP-PROTOCOL-EXTENSION ::= {
--	...
--}

--PDSCHSets-DeleteList-PSCH-ReconfRqst ::= SEQUENCE (SIZE (1..maxNrOfPDSCHSets)) OF PDSCHSets-DeleteItem-PSCH-ReconfRqst
PDSCHSets-DeleteList-PSCH-ReconfRqst ::= SEQUENCE (SIZE (1..256)) OF PDSCHSets-DeleteItem-PSCH-ReconfRqst

PDSCHSets-DeleteItem-PSCH-ReconfRqst	 ::= SEQUENCE {
	pDSCHSet-ID									PDSCHSet-ID,
--	iE-Extensions								ProtocolExtensionContainer { {PDSCHSets-DeleteItem-PSCH-ReconfRqst-ExtIEs} }		OPTIONAL,
	iE-Extensions								ProtocolExtensionContainer OPTIONAL,
	...
}

--PDSCHSets-DeleteItem-PSCH-ReconfRqst-ExtIEs  NBAP-PROTOCOL-EXTENSION ::= {
--	...
--}

--PUSCHSets-AddList-PSCH-ReconfRqst ::= SEQUENCE (SIZE (1..maxNrOfPUSCHSets)) OF PUSCHSets-AddItem-PSCH-ReconfRqst
PUSCHSets-AddList-PSCH-ReconfRqst ::= SEQUENCE (SIZE (1..256)) OF PUSCHSets-AddItem-PSCH-ReconfRqst

PUSCHSets-AddItem-PSCH-ReconfRqst	 ::= SEQUENCE {
	pUSCHSet-ID									PUSCHSet-ID,
	pUSCH-InformationList						PUSCH-Information-AddList-PSCH-ReconfRqst 	OPTIONAL,
	-- Mandatory for 3.84Mcps TDD, Not Applicable to 1.28Mcps TDD
--	iE-Extensions								ProtocolExtensionContainer { {PUSCHSets-AddItem-PSCH-ReconfRqst-ExtIEs} }		OPTIONAL,
	iE-Extensions								ProtocolExtensionContainer OPTIONAL,
	...
}

--PUSCHSets-AddItem-PSCH-ReconfRqst-ExtIEs  NBAP-PROTOCOL-EXTENSION ::= {
--	{ID id-PUSCH-AddInformation-LCR-PSCH-ReconfRqst	CRITICALITY	reject		EXTENSION 	PUSCH-AddInformation-LCR-AddItem-PSCH-ReconfRqst			PRESENCE	optional},
	-- Mandatory for 1.28Mcps TDD, Not Applicable to 3.84Mcps TDD
--	...
--}

--PUSCH-Information-AddList-PSCH-ReconfRqst ::=  ProtocolIE-Single-Container {{ PUSCH-Information-AddListIEs-PSCH-ReconfRqst }}
PUSCH-Information-AddList-PSCH-ReconfRqst ::=  ProtocolIE-Single-Container

--PUSCH-Information-AddListIEs-PSCH-ReconfRqst NBAP-PROTOCOL-IES ::= {
--	{ID id-PUSCH-Information-AddListIE-PSCH-ReconfRqst 	CRITICALITY	reject		TYPE	PUSCH-Information-AddItem-PSCH-ReconfRqst			PRESENCE	mandatory}
--}

PUSCH-Information-AddItem-PSCH-ReconfRqst ::= SEQUENCE {
	repetitionPeriod						RepetitionPeriod,
	repetitionLength						RepetitionLength,
	tdd-PhysicalChannelOffset				TDD-PhysicalChannelOffset,
	uL-Timeslot-InformationAddList-PSCH-ReconfRqst				UL-Timeslot-InformationAddList-PSCH-ReconfRqst,
--	iE-Extensions								ProtocolExtensionContainer { {PUSCH-Information-AddItem-PSCH-ReconfRqst-ExtIEs} }		OPTIONAL,
	iE-Extensions								ProtocolExtensionContainer OPTIONAL,
	...
	}

--PUSCH-Information-AddItem-PSCH-ReconfRqst-ExtIEs  NBAP-PROTOCOL-EXTENSION ::= {
--	...
--}

--UL-Timeslot-InformationAddList-PSCH-ReconfRqst ::= SEQUENCE (SIZE (1..maxNrOfULTSs)) OF UL-Timeslot-InformationAddItem-PSCH-ReconfRqst
UL-Timeslot-InformationAddList-PSCH-ReconfRqst ::= SEQUENCE (SIZE (1..15)) OF UL-Timeslot-InformationAddItem-PSCH-ReconfRqst

UL-Timeslot-InformationAddItem-PSCH-ReconfRqst ::= SEQUENCE {
	timeSlot								TimeSlot,
	midambleShiftAndBurstType				MidambleShiftAndBurstType,
	tFCI-Presence							TFCI-Presence,
	uL-Code-InformationAddList-PSCH-ReconfRqst				UL-Code-InformationAddList-PSCH-ReconfRqst,
--	iE-Extensions							ProtocolExtensionContainer { { UL-Timeslot-InformationAddItem-PSCH-ReconfRqst-ExtIEs} }		OPTIONAL,
	iE-Extensions							ProtocolExtensionContainer OPTIONAL,
	...
}

--UL-Timeslot-InformationAddItem-PSCH-ReconfRqst-ExtIEs NBAP-PROTOCOL-EXTENSION ::= {
--	...
--}

--UL-Code-InformationAddList-PSCH-ReconfRqst ::= SEQUENCE (SIZE (1..maxNrOfPUSCHs)) OF UL-Code-InformationAddItem-PSCH-ReconfRqst
UL-Code-InformationAddList-PSCH-ReconfRqst ::= SEQUENCE (SIZE (1..256)) OF UL-Code-InformationAddItem-PSCH-ReconfRqst

UL-Code-InformationAddItem-PSCH-ReconfRqst ::= SEQUENCE {
	pUSCH-ID								PUSCH-ID,
	tdd-ChannelisationCode					TDD-ChannelisationCode,
--	iE-Extensions							ProtocolExtensionContainer { { UL-Code-InformationAddItem-PSCH-ReconfRqst-ExtIEs} }		OPTIONAL,
	iE-Extensions							ProtocolExtensionContainer OPTIONAL,
	...
}

--UL-Code-InformationAddItem-PSCH-ReconfRqst-ExtIEs NBAP-PROTOCOL-EXTENSION ::= {
--	...
--}

PUSCH-AddInformation-LCR-AddItem-PSCH-ReconfRqst ::= SEQUENCE {
	repetitionPeriod						RepetitionPeriod,
	repetitionLength						RepetitionLength,
	tdd-PhysicalChannelOffset				TDD-PhysicalChannelOffset,
	uL-Timeslot-InformationAddList-LCR-PSCH-ReconfRqst				UL-Timeslot-InformationAddList-LCR-PSCH-ReconfRqst,
--	iE-Extensions								ProtocolExtensionContainer { {PUSCH-AddInformation-LCR-AddItem-PSCH-ReconfRqst-ExtIEs} }		OPTIONAL,
	iE-Extensions								ProtocolExtensionContainer OPTIONAL,
	...
	}

--PUSCH-AddInformation-LCR-AddItem-PSCH-ReconfRqst-ExtIEs  NBAP-PROTOCOL-EXTENSION ::= {
--	...
--}

--UL-Timeslot-InformationAddList-LCR-PSCH-ReconfRqst ::= SEQUENCE (SIZE (1.. maxNrOfULTSLCRs)) OF UL-Timeslot-InformationAddItem-LCR-PSCH-ReconfRqst
UL-Timeslot-InformationAddList-LCR-PSCH-ReconfRqst ::= SEQUENCE (SIZE (1.. 6)) OF UL-Timeslot-InformationAddItem-LCR-PSCH-ReconfRqst

UL-Timeslot-InformationAddItem-LCR-PSCH-ReconfRqst ::= SEQUENCE {
	timeSlotLCR								TimeSlotLCR,
	midambleShiftLCR						MidambleShiftLCR,
	tFCI-Presence							TFCI-Presence,
	uL-Code-InformationAddList-LCR-PSCH-ReconfRqst				UL-Code-InformationAddList-LCR-PSCH-ReconfRqst,
--	iE-Extensions							ProtocolExtensionContainer { { UL-Timeslot-InformationAddItem-LCR-PSCH-ReconfRqst-ExtIEs} }		OPTIONAL,
	iE-Extensions							ProtocolExtensionContainer OPTIONAL,
	...
}

--UL-Timeslot-InformationAddItem-LCR-PSCH-ReconfRqst-ExtIEs NBAP-PROTOCOL-EXTENSION ::= {
--	...
--}

--UL-Code-InformationAddList-LCR-PSCH-ReconfRqst ::= SEQUENCE (SIZE (1..maxNrOfPUSCHs)) OF UL-Code-InformationAddItem-LCR-PSCH-ReconfRqst
UL-Code-InformationAddList-LCR-PSCH-ReconfRqst ::= SEQUENCE (SIZE (1..256)) OF UL-Code-InformationAddItem-LCR-PSCH-ReconfRqst

UL-Code-InformationAddItem-LCR-PSCH-ReconfRqst ::= SEQUENCE {
	pUSCH-ID								PUSCH-ID,
	tdd-ChannelisationCodeLCR				TDD-ChannelisationCodeLCR,
--	iE-Extensions							ProtocolExtensionContainer { { UL-Code-InformationAddItem-LCR-PSCH-ReconfRqst-ExtIEs} }		OPTIONAL,
	iE-Extensions							ProtocolExtensionContainer OPTIONAL,
	...
}

--UL-Code-InformationAddItem-LCR-PSCH-ReconfRqst-ExtIEs NBAP-PROTOCOL-EXTENSION ::= {
--	...
--}

--PUSCHSets-ModifyList-PSCH-ReconfRqst ::= SEQUENCE (SIZE (1..maxNrOfPUSCHSets)) OF PUSCHSets-ModifyItem-PSCH-ReconfRqst
PUSCHSets-ModifyList-PSCH-ReconfRqst ::= SEQUENCE (SIZE (1..256)) OF PUSCHSets-ModifyItem-PSCH-ReconfRqst

PUSCHSets-ModifyItem-PSCH-ReconfRqst	 ::= SEQUENCE {
	pUSCHSet-ID									PUSCHSet-ID,
	pUSCH-InformationList						PUSCH-Information-ModifyList-PSCH-ReconfRqst,
--	iE-Extensions								ProtocolExtensionContainer { {PUSCHSets-ModifyItem-PSCH-ReconfRqst-ExtIEs} }		OPTIONAL,
	iE-Extensions								ProtocolExtensionContainer OPTIONAL,
	...
}

--PUSCHSets-ModifyItem-PSCH-ReconfRqst-ExtIEs  NBAP-PROTOCOL-EXTENSION ::= {
--	...
--}

--PUSCH-Information-ModifyList-PSCH-ReconfRqst ::= ProtocolIE-Single-Container {{ PUSCH-Information-ModifyListIEs-PSCH-ReconfRqst }}	
PUSCH-Information-ModifyList-PSCH-ReconfRqst ::= ProtocolIE-Single-Container

--PUSCH-Information-ModifyListIEs-PSCH-ReconfRqst NBAP-PROTOCOL-IES ::= {
--	{ID id-PUSCH-Information-ModifyListIE-PSCH-ReconfRqst	CRITICALITY reject		TYPE PUSCH-Information-ModifyItem-PSCH-ReconfRqst			PRESENCE	optional}|
--	{ID id-PUSCH-ModifyInformation-LCR-PSCH-ReconfRqst		CRITICALITY reject		TYPE PUSCH-ModifyInformation-LCR-ModifyItem-PSCH-ReconfRqst			PRESENCE	optional}
--}

PUSCH-Information-ModifyItem-PSCH-ReconfRqst ::= SEQUENCE {
	repetitionPeriod						RepetitionPeriod					OPTIONAL,
	repetitionLength						RepetitionLength					OPTIONAL,
	tdd-PhysicalChannelOffset				TDD-PhysicalChannelOffset			OPTIONAL,
	uL-Timeslot-InformationModifyList-PSCH-ReconfRqst				UL-Timeslot-InformationModifyList-PSCH-ReconfRqst		OPTIONAL,
--	iE-Extensions								ProtocolExtensionContainer { {PUSCH-Information-ModifyItem-PSCH-ReconfRqst-ExtIEs} }		OPTIONAL,
	iE-Extensions								ProtocolExtensionContainer OPTIONAL,
		...
	}

--PUSCH-Information-ModifyItem-PSCH-ReconfRqst-ExtIEs  NBAP-PROTOCOL-EXTENSION ::= {
--	...
--}

--UL-Timeslot-InformationModifyList-PSCH-ReconfRqst ::= SEQUENCE (SIZE (1..maxNrOfULTSs)) OF UL-Timeslot-InformationModifyItem-PSCH-ReconfRqst
UL-Timeslot-InformationModifyList-PSCH-ReconfRqst ::= SEQUENCE (SIZE (1..15)) OF UL-Timeslot-InformationModifyItem-PSCH-ReconfRqst

UL-Timeslot-InformationModifyItem-PSCH-ReconfRqst ::= SEQUENCE {
	timeSlot								TimeSlot,
	midambleShiftAndBurstType				MidambleShiftAndBurstType	OPTIONAL,
	tFCI-Presence							TFCI-Presence	OPTIONAL,
	uL-Code-InformationModifyList-PSCH-ReconfRqst				UL-Code-InformationModifyList-PSCH-ReconfRqst		OPTIONAL,
--	iE-Extensions							ProtocolExtensionContainer { { UL-Timeslot-InformationModifyItem-PSCH-ReconfRqst-ExtIEs} }		OPTIONAL,
	iE-Extensions							ProtocolExtensionContainer OPTIONAL,
	...
}

--UL-Timeslot-InformationModifyItem-PSCH-ReconfRqst-ExtIEs NBAP-PROTOCOL-EXTENSION ::= {
--	...
--}

--UL-Code-InformationModifyList-PSCH-ReconfRqst ::= SEQUENCE (SIZE (1..maxNrOfPUSCHs)) OF UL-Code-InformationModifyItem-PSCH-ReconfRqst
UL-Code-InformationModifyList-PSCH-ReconfRqst ::= SEQUENCE (SIZE (1..256)) OF UL-Code-InformationModifyItem-PSCH-ReconfRqst

UL-Code-InformationModifyItem-PSCH-ReconfRqst ::= SEQUENCE {
	pUSCH-ID								PUSCH-ID,
	tdd-ChannelisationCode					TDD-ChannelisationCode,
--	iE-Extensions							ProtocolExtensionContainer { { UL-Code-InformationModifyItem-PSCH-ReconfRqst-ExtIEs} }		OPTIONAL,
	iE-Extensions							ProtocolExtensionContainer OPTIONAL,
	...
}

--UL-Code-InformationModifyItem-PSCH-ReconfRqst-ExtIEs NBAP-PROTOCOL-EXTENSION ::= {
--	...
--}

PUSCH-ModifyInformation-LCR-ModifyItem-PSCH-ReconfRqst ::= SEQUENCE {
	repetitionPeriod						RepetitionPeriod		OPTIONAL,
	repetitionLength						RepetitionLength		OPTIONAL,
	tdd-PhysicalChannelOffset				TDD-PhysicalChannelOffset	OPTIONAL,
	uL-Timeslot-InformationModifyList-LCR-PSCH-ReconfRqst				UL-Timeslot-LCR-InformationModifyList-PSCH-ReconfRqst		OPTIONAL,
--	iE-Extensions								ProtocolExtensionContainer { {PUSCH-ModifyInformation-LCR-ModifyItem-PSCH-ReconfRqst-ExtIEs} }		OPTIONAL,
	iE-Extensions								ProtocolExtensionContainer OPTIONAL,
		...
	}

--PUSCH-ModifyInformation-LCR-ModifyItem-PSCH-ReconfRqst-ExtIEs  NBAP-PROTOCOL-EXTENSION ::= {
--	...
--}

--UL-Timeslot-LCR-InformationModifyList-PSCH-ReconfRqst ::= SEQUENCE (SIZE (1..maxNrOfULTSLCRs)) OF UL-Timeslot-LCR-InformationModifyItem-PSCH-ReconfRqst
UL-Timeslot-LCR-InformationModifyList-PSCH-ReconfRqst ::= SEQUENCE (SIZE (1..6)) OF UL-Timeslot-LCR-InformationModifyItem-PSCH-ReconfRqst

UL-Timeslot-LCR-InformationModifyItem-PSCH-ReconfRqst ::= SEQUENCE {
	timeSlotLCR								TimeSlotLCR,
	midambleShiftLCR						MidambleShiftLCR 	OPTIONAL,
	tFCI-Presence							TFCI-Presence		OPTIONAL,
	uL-Code-LCR-InformationModifyList-PSCH-ReconfRqst				UL-Code-LCR-InformationModifyList-PSCH-ReconfRqst		OPTIONAL,
--	iE-Extensions							ProtocolExtensionContainer { { UL-Timeslot-LCR-InformationModifyItem-PSCH-ReconfRqst-ExtIEs} }		OPTIONAL,
	iE-Extensions							ProtocolExtensionContainer OPTIONAL,
	...
}

--UL-Timeslot-LCR-InformationModifyItem-PSCH-ReconfRqst-ExtIEs NBAP-PROTOCOL-EXTENSION ::= {
--	...
--}

--UL-Code-LCR-InformationModifyList-PSCH-ReconfRqst ::= SEQUENCE (SIZE (1..maxNrOfPUSCHs)) OF UL-Code-LCR-InformationModifyItem-PSCH-ReconfRqst
UL-Code-LCR-InformationModifyList-PSCH-ReconfRqst ::= SEQUENCE (SIZE (1..256)) OF UL-Code-LCR-InformationModifyItem-PSCH-ReconfRqst

UL-Code-LCR-InformationModifyItem-PSCH-ReconfRqst ::= SEQUENCE {
	pUSCH-ID								PUSCH-ID,
	tdd-ChannelisationCodeLCR					TDD-ChannelisationCodeLCR,
--	iE-Extensions							ProtocolExtensionContainer { { UL-Code-LCR-InformationModifyItem-PSCH-ReconfRqst-ExtIEs} }		OPTIONAL,
	iE-Extensions							ProtocolExtensionContainer OPTIONAL,
	...
}

--UL-Code-LCR-InformationModifyItem-PSCH-ReconfRqst-ExtIEs NBAP-PROTOCOL-EXTENSION ::= {
--	...
--}

--PUSCHSets-DeleteList-PSCH-ReconfRqst ::= SEQUENCE (SIZE (1..maxNrOfPUSCHSets)) OF PUSCHSets-DeleteItem-PSCH-ReconfRqst
PUSCHSets-DeleteList-PSCH-ReconfRqst ::= SEQUENCE (SIZE (1..256)) OF PUSCHSets-DeleteItem-PSCH-ReconfRqst

PUSCHSets-DeleteItem-PSCH-ReconfRqst	 ::= SEQUENCE {
	pUSCHSet-ID									PUSCHSet-ID,
--	iE-Extensions								ProtocolExtensionContainer { {PUSCHSets-DeleteItem-PSCH-ReconfRqst-ExtIEs} }		OPTIONAL,
	iE-Extensions								ProtocolExtensionContainer OPTIONAL,
	...
}

--PUSCHSets-DeleteItem-PSCH-ReconfRqst-ExtIEs  NBAP-PROTOCOL-EXTENSION ::= {
--	...
--}

HS-PDSCH-TDD-Information-PSCH-ReconfRqst ::= SEQUENCE {
	dL-HS-PDSCH-Timeslot-Information-PSCH-ReconfRqst					DL-HS-PDSCH-Timeslot-Information-PSCH-ReconfRqst		OPTIONAL,
	dL-HS-PDSCH-Timeslot-Information-LCR-PSCH-ReconfRqst				DL-HS-PDSCH-Timeslot-Information-LCR-PSCH-ReconfRqst		OPTIONAL,
--	iE-Extensions								ProtocolExtensionContainer { { HS-PDSCH-TDD-Information-PSCH-ReconfRqst-ExtIEs} }		OPTIONAL,
	iE-Extensions								ProtocolExtensionContainer OPTIONAL,
		...
	}

--HS-PDSCH-TDD-Information-PSCH-ReconfRqst-ExtIEs  NBAP-PROTOCOL-EXTENSION ::= {
--	...
--}

--DL-HS-PDSCH-Timeslot-Information-PSCH-ReconfRqst ::= SEQUENCE (SIZE (1..maxNrOfDLTSs)) OF DL-HS-PDSCH-Timeslot-InformationItem-PSCH-ReconfRqst
DL-HS-PDSCH-Timeslot-Information-PSCH-ReconfRqst ::= SEQUENCE (SIZE (1..15)) OF DL-HS-PDSCH-Timeslot-InformationItem-PSCH-ReconfRqst

DL-HS-PDSCH-Timeslot-InformationItem-PSCH-ReconfRqst::= SEQUENCE {
	timeSlot								TimeSlot,
	midambleShiftAndBurstType				MidambleShiftAndBurstType,
	dl-HS-PDSCH-Codelist-PSCH-ReconfRqst	DL-HS-PDSCH-Codelist-PSCH-ReconfRqst,
	maxHSDSCH-HSSCCH-Power					MaximumTransmissionPower	OPTIONAL,
--	iE-Extensions							ProtocolExtensionContainer { { DL-HS-PDSCH-Timeslot-InformationItem-PSCH-ReconfRqst-ExtIEs} }		OPTIONAL,
	iE-Extensions							ProtocolExtensionContainer OPTIONAL,
	...
}

--DL-HS-PDSCH-Timeslot-InformationItem-PSCH-ReconfRqst-ExtIEs NBAP-PROTOCOL-EXTENSION ::= {
--	...
--}

--DL-HS-PDSCH-Codelist-PSCH-ReconfRqst ::= SEQUENCE (SIZE (1..maxNrOfHSPDSCHs)) OF TDD-ChannelisationCode
DL-HS-PDSCH-Codelist-PSCH-ReconfRqst ::= SEQUENCE (SIZE (1..16)) OF TDD-ChannelisationCode

--DL-HS-PDSCH-Timeslot-Information-LCR-PSCH-ReconfRqst ::= SEQUENCE (SIZE (1..maxNrOfDLTSLCRs)) OF DL-HS-PDSCH-Timeslot-InformationItem-LCR-PSCH-ReconfRqst
DL-HS-PDSCH-Timeslot-Information-LCR-PSCH-ReconfRqst ::= SEQUENCE (SIZE (1..6)) OF DL-HS-PDSCH-Timeslot-InformationItem-LCR-PSCH-ReconfRqst

DL-HS-PDSCH-Timeslot-InformationItem-LCR-PSCH-ReconfRqst::= SEQUENCE {
	timeSlot								TimeSlotLCR,
	midambleShiftAndBurstType				MidambleShiftLCR,
	dl-HS-PDSCH-Codelist-LCR-PSCH-ReconfRqst	DL-HS-PDSCH-Codelist-LCR-PSCH-ReconfRqst,
	maxHSDSCH-HSSCCH-Power						MaximumTransmissionPower	OPTIONAL,
--	iE-Extensions							ProtocolExtensionContainer { { DL-HS-PDSCH-Timeslot-InformationItem-LCR-PSCH-ReconfRqst-ExtIEs} }		OPTIONAL,
	iE-Extensions							ProtocolExtensionContainer OPTIONAL,
	...
}

--DL-HS-PDSCH-Timeslot-InformationItem-LCR-PSCH-ReconfRqst-ExtIEs NBAP-PROTOCOL-EXTENSION ::= {
--	...
--}

--DL-HS-PDSCH-Codelist-LCR-PSCH-ReconfRqst ::= SEQUENCE (SIZE (1..maxNrOfHSPDSCHs)) OF TDD-ChannelisationCode
DL-HS-PDSCH-Codelist-LCR-PSCH-ReconfRqst ::= SEQUENCE (SIZE (1..15)) OF TDD-ChannelisationCode

Add-To-HS-SCCH-Resource-Pool-PSCH-ReconfRqst::= SEQUENCE {
	hS-SCCH-Information-PSCH-ReconfRqst		HS-SCCH-Information-PSCH-ReconfRqst		OPTIONAL,
	hS-SCCH-Information-LCR-PSCH-ReconfRqst	HS-SCCH-Information-LCR-PSCH-ReconfRqst		OPTIONAL,
--	iE-Extensions							ProtocolExtensionContainer { { Add-To-HS-SCCH-Resource-Pool-PSCH-ReconfRqst-ExtIEs} }		OPTIONAL,
	iE-Extensions							ProtocolExtensionContainer OPTIONAL,
	...
}

--Add-To-HS-SCCH-Resource-Pool-PSCH-ReconfRqst-ExtIEs NBAP-PROTOCOL-EXTENSION ::= {
--	...
--}

--HS-SCCH-Information-PSCH-ReconfRqst::= SEQUENCE (SIZE (1..maxNrOfHSSCCHs)) OF HS-SCCH-InformationItem-PSCH-ReconfRqst
HS-SCCH-Information-PSCH-ReconfRqst::= SEQUENCE (SIZE (1..32)) OF HS-SCCH-InformationItem-PSCH-ReconfRqst

HS-SCCH-InformationItem-PSCH-ReconfRqst	 ::= SEQUENCE {
	hS-SCCH-ID								HS-SCCH-ID,
	timeSlot								TimeSlot,
	midambleShiftAndBurstType				MidambleShiftAndBurstType,
	tdd-ChannelisationCode					TDD-ChannelisationCode,
	hS-SCCH-MaxPower						DL-Power,
	hS-SICH-Information						HS-SICH-Information-PSCH-ReconfRqst,
--	iE-Extensions							ProtocolExtensionContainer { { HS-SCCH-InformationItem-PSCH-ReconfRqst-ExtIEs} }		OPTIONAL,
	iE-Extensions							ProtocolExtensionContainer OPTIONAL,
	...
}

--HS-SCCH-InformationItem-PSCH-ReconfRqst-ExtIEs  NBAP-PROTOCOL-EXTENSION ::= {
--	...
--}

HS-SICH-Information-PSCH-ReconfRqst	 ::= SEQUENCE {
	hsSICH-ID								HS-SICH-ID,
	timeSlot								TimeSlot,
	midambleShiftAndBurstType				MidambleShiftAndBurstType,
	tdd-ChannelisationCode					TDD-ChannelisationCode,
--	iE-Extensions							ProtocolExtensionContainer { { HS-SICH-Information-PSCH-ReconfRqst-ExtIEs} }		OPTIONAL,
	iE-Extensions							ProtocolExtensionContainer OPTIONAL,
	...
}

--HS-SICH-Information-PSCH-ReconfRqst-ExtIEs  NBAP-PROTOCOL-EXTENSION ::= {
--	...
--}

--HS-SCCH-Information-LCR-PSCH-ReconfRqst::= SEQUENCE (SIZE (1..maxNrOfHSSCCHs)) OF HS-SCCH-InformationItem-LCR-PSCH-ReconfRqst
HS-SCCH-Information-LCR-PSCH-ReconfRqst::= SEQUENCE (SIZE (1..32)) OF HS-SCCH-InformationItem-LCR-PSCH-ReconfRqst

HS-SCCH-InformationItem-LCR-PSCH-ReconfRqst	 ::= SEQUENCE {
	hS-SCCH-ID								HS-SCCH-ID,
	timeSlotLCR								TimeSlotLCR,
	midambleShiftLCR						MidambleShiftLCR,
	first-TDD-ChannelisationCode			TDD-ChannelisationCode,
	second-TDD-ChannelisationCode			TDD-ChannelisationCode,
	hS-SCCH-MaxPower						DL-Power,
	hS-SICH-Information-LCR					HS-SICH-Information-LCR-PSCH-ReconfRqst,
--	iE-Extensions							ProtocolExtensionContainer { { HS-SCCH-InformationItem-LCR-PSCH-ReconfRqst-ExtIEs} }		OPTIONAL,
	iE-Extensions							ProtocolExtensionContainer OPTIONAL,
	...
}

--HS-SCCH-InformationItem-LCR-PSCH-ReconfRqst-ExtIEs  NBAP-PROTOCOL-EXTENSION ::= {
--	...
--}

HS-SICH-Information-LCR-PSCH-ReconfRqst	 ::= SEQUENCE {
	hsSICH-ID								HS-SICH-ID,
	timeSlotLCR								TimeSlotLCR,
	midambleShiftLCR						MidambleShiftLCR,
	tdd-ChannelisationCode				TDD-ChannelisationCode,
--	iE-Extensions							ProtocolExtensionContainer { { HS-SICH-Information-LCR-PSCH-ReconfRqst-ExtIEs} }		OPTIONAL,
	iE-Extensions							ProtocolExtensionContainer OPTIONAL,
	...
}

--HS-SICH-Information-LCR-PSCH-ReconfRqst-ExtIEs  NBAP-PROTOCOL-EXTENSION ::= {
--	...
--}

Modify-HS-SCCH-Resource-Pool-PSCH-ReconfRqst::= SEQUENCE {
	hS-SCCH-InformationModify-PSCH-ReconfRqst		HS-SCCH-InformationModify-PSCH-ReconfRqst	OPTIONAL,
	hS-SCCH-InformationModify-LCR-PSCH-ReconfRqst	HS-SCCH-InformationModify-LCR-PSCH-ReconfRqst	OPTIONAL,
--	iE-Extensions									ProtocolExtensionContainer { { Modify-HS-SCCH-Resource-Pool-PSCH-ReconfRqst-ExtIEs} }		OPTIONAL,
	iE-Extensions									ProtocolExtensionContainer OPTIONAL,
	...
}

--Modify-HS-SCCH-Resource-Pool-PSCH-ReconfRqst-ExtIEs NBAP-PROTOCOL-EXTENSION ::= {
--	...
--}

--HS-SCCH-InformationModify-PSCH-ReconfRqst::= SEQUENCE (SIZE (1..maxNrOfHSSCCHs)) OF HS-SCCH-InformationModifyItem-PSCH-ReconfRqst
HS-SCCH-InformationModify-PSCH-ReconfRqst::= SEQUENCE (SIZE (1..32)) OF HS-SCCH-InformationModifyItem-PSCH-ReconfRqst

HS-SCCH-InformationModifyItem-PSCH-ReconfRqst	 ::= SEQUENCE {
	hS-SCCH-ID								HS-SCCH-ID,
	timeSlot								TimeSlot 	OPTIONAL,
	midambleShiftAndBurstType				MidambleShiftAndBurstType 	OPTIONAL,
	tdd-ChannelisationCode					TDD-ChannelisationCode 	OPTIONAL,
	hS-SCCH-MaxPower						DL-Power 	OPTIONAL,
	hS-SICH-Information						HS-SICH-InformationModify-PSCH-ReconfRqst 	OPTIONAL,
--	iE-Extensions							ProtocolExtensionContainer { { HS-SCCH-InformationModifyItem-PSCH-ReconfRqst-ExtIEs} }		OPTIONAL,
	iE-Extensions							ProtocolExtensionContainer OPTIONAL,
	...
}

--HS-SCCH-InformationModifyItem-PSCH-ReconfRqst-ExtIEs  NBAP-PROTOCOL-EXTENSION ::= {
--	...
--}

HS-SICH-InformationModify-PSCH-ReconfRqst	 ::= SEQUENCE {
	hsSICH-ID								HS-SICH-ID,
	timeSlot								TimeSlot 	OPTIONAL,
	midambleShiftAndBurstType				MidambleShiftAndBurstType 	OPTIONAL,
	tdd-ChannelisationCode					TDD-ChannelisationCode 	OPTIONAL,
--	iE-Extensions							ProtocolExtensionContainer { { HS-SICH-InformationModify-PSCH-ReconfRqst-ExtIEs} }		OPTIONAL,
	iE-Extensions							ProtocolExtensionContainer OPTIONAL,
	...
}

--HS-SICH-InformationModify-PSCH-ReconfRqst-ExtIEs  NBAP-PROTOCOL-EXTENSION ::= {
--	...
--}

--HS-SCCH-InformationModify-LCR-PSCH-ReconfRqst::= SEQUENCE (SIZE (1..maxNrOfHSSCCHs)) OF HS-SCCH-InformationModifyItem-LCR-PSCH-ReconfRqst
HS-SCCH-InformationModify-LCR-PSCH-ReconfRqst::= SEQUENCE (SIZE (1..32)) OF HS-SCCH-InformationModifyItem-LCR-PSCH-ReconfRqst

HS-SCCH-InformationModifyItem-LCR-PSCH-ReconfRqst	 ::= SEQUENCE {
	hS-SCCH-ID								HS-SCCH-ID,
	timeSlotLCR								TimeSlotLCR 	OPTIONAL,
	midambleShiftLCR						MidambleShiftLCR 	OPTIONAL,
	first-TDD-ChannelisationCode			TDD-ChannelisationCode	OPTIONAL,
	second-TDD-ChannelisationCode			TDD-ChannelisationCode	OPTIONAL,
	hS-SCCH-MaxPower						DL-Power 	OPTIONAL,
	hS-SICH-Information-LCR					HS-SICH-InformationModify-LCR-PSCH-ReconfRqst 	OPTIONAL,
--	iE-Extensions							ProtocolExtensionContainer { { HS-SCCH-InformationModifyItem-LCR-PSCH-ReconfRqst-ExtIEs} }		OPTIONAL,
	iE-Extensions							ProtocolExtensionContainer OPTIONAL,
	...
}

--HS-SCCH-InformationModifyItem-LCR-PSCH-ReconfRqst-ExtIEs  NBAP-PROTOCOL-EXTENSION ::= {
--	...
--}

HS-SICH-InformationModify-LCR-PSCH-ReconfRqst	 ::= SEQUENCE {
	hsSICH-ID								HS-SICH-ID,
	timeSlotLCR								TimeSlotLCR 	OPTIONAL,
	midambleShiftLCR						MidambleShiftLCR 	OPTIONAL,
	tdd-ChannelisationCode				TDD-ChannelisationCode	OPTIONAL,
--	iE-Extensions							ProtocolExtensionContainer { { HS-SICH-InformationModify-LCR-PSCH-ReconfRqst-ExtIEs} }		OPTIONAL,
	iE-Extensions							ProtocolExtensionContainer OPTIONAL,
	...
}

--HS-SICH-InformationModify-LCR-PSCH-ReconfRqst-ExtIEs  NBAP-PROTOCOL-EXTENSION ::= {
--	...
--}

--Delete-From-HS-SCCH-Resource-Pool-PSCH-ReconfRqst ::= SEQUENCE (SIZE (1..maxNrOfHSSCCHs)) OF Delete-From-HS-SCCH-Resource-PoolItem-PSCH-ReconfRqst
Delete-From-HS-SCCH-Resource-Pool-PSCH-ReconfRqst ::= SEQUENCE (SIZE (1..32)) OF Delete-From-HS-SCCH-Resource-PoolItem-PSCH-ReconfRqst

Delete-From-HS-SCCH-Resource-PoolItem-PSCH-ReconfRqst	 ::= SEQUENCE {
	hS-SCCH-ID								HS-SCCH-ID,
--	iE-Extensions								ProtocolExtensionContainer { { Delete-From-HS-SCCH-Resource-PoolItem-PSCH-ReconfRqst-ExtIEs} }		OPTIONAL,
	iE-Extensions								ProtocolExtensionContainer OPTIONAL,
	...
}

--Delete-From-HS-SCCH-Resource-PoolItem-PSCH-ReconfRqst-ExtIEs  NBAP-PROTOCOL-EXTENSION ::= {
--	...
--}

-- **************************************************************
--
-- PHYSICAL SHARED CHANNEL RECONFIGURATION RESPONSE
--
-- **************************************************************

--PhysicalSharedChannelReconfigurationResponse ::= SEQUENCE {
--	protocolIEs			ProtocolIE-Container  {{PhysicalSharedChannelReconfigurationResponse-IEs}},
--	protocolExtensions	ProtocolExtensionContainer {{PhysicalSharedChannelReconfigurationResponse-Extensions}}                   OPTIONAL,
--	...
--}
PhysicalSharedChannelReconfigurationResponse ::= SEQUENCE {
	protocolIEs			ProtocolIE-Container,
	protocolExtensions	ProtocolExtensionContainer OPTIONAL,
	...
}

--PhysicalSharedChannelReconfigurationResponse-IEs NBAP-PROTOCOL-IES ::= {
--	{ ID	id-CriticalityDiagnostics		CRITICALITY		ignore		TYPE		CriticalityDiagnostics		PRESENCE	optional	},
--	...
--}

--PhysicalSharedChannelReconfigurationResponse-Extensions NBAP-PROTOCOL-EXTENSION ::= {
--	...
--}


-- **************************************************************
--
-- PHYSICAL SHARED CHANNEL RECONFIGURATION FAILURE
--
-- **************************************************************

--PhysicalSharedChannelReconfigurationFailure ::= SEQUENCE {
--	protocolIEs			ProtocolIE-Container  {{PhysicalSharedChannelReconfigurationFailure-IEs}},
--	protocolExtensions	ProtocolExtensionContainer {{PhysicalSharedChannelReconfigurationFailure-Extensions}}                   OPTIONAL,
--	...
--}
PhysicalSharedChannelReconfigurationFailure ::= SEQUENCE {
	protocolIEs			ProtocolIE-Container,
	protocolExtensions	ProtocolExtensionContainer OPTIONAL,
	...
}

--PhysicalSharedChannelReconfigurationFailure-IEs NBAP-PROTOCOL-IES ::= {
--	{ ID    id-CauseLevel-PSCH-ReconfFailure		CRITICALITY ignore	TYPE CauseLevel-PSCH-ReconfFailure	 PRESENCE mandatory }|
--	{ ID	id-CriticalityDiagnostics		CRITICALITY ignore		TYPE	CriticalityDiagnostics	PRESENCE	optional	},
--	...
--}

--PhysicalSharedChannelReconfigurationFailure-Extensions NBAP-PROTOCOL-EXTENSION ::= {
--	...
--}

CauseLevel-PSCH-ReconfFailure ::= CHOICE {
	generalCause			GeneralCauseList-PSCH-ReconfFailure,
	setSpecificCause		SetSpecificCauseList-PSCH-ReconfFailureTDD,
	...
}

GeneralCauseList-PSCH-ReconfFailure ::= SEQUENCE {
	cause						Cause,
--	iE-Extensions				ProtocolExtensionContainer { { GeneralCauseItem-PSCH-ReconfFailure-ExtIEs} }		OPTIONAL,
	iE-Extensions				ProtocolExtensionContainer OPTIONAL,
	...
}

--GeneralCauseItem-PSCH-ReconfFailure-ExtIEs NBAP-PROTOCOL-EXTENSION ::= {
--	...
--}

SetSpecificCauseList-PSCH-ReconfFailureTDD ::= SEQUENCE {
	unsuccessful-PDSCHSetList-PSCH-ReconfFailureTDD	Unsuccessful-PDSCHSetList-PSCH-ReconfFailureTDD		OPTIONAL,
	unsuccessful-PUSCHSetList-PSCH-ReconfFailureTDD	Unsuccessful-PUSCHSetList-PSCH-ReconfFailureTDD		OPTIONAL,
--	iE-Extensions									ProtocolExtensionContainer { { SetSpecificCauseItem-PSCH-ReconfFailureTDD-ExtIEs} }		OPTIONAL,
	iE-Extensions									ProtocolExtensionContainer OPTIONAL,
	...
}

--SetSpecificCauseItem-PSCH-ReconfFailureTDD-ExtIEs NBAP-PROTOCOL-EXTENSION ::= {
--	...
--}

--Unsuccessful-PDSCHSetList-PSCH-ReconfFailureTDD ::= SEQUENCE (SIZE (0.. maxNrOfPDSCHSets)) OF ProtocolIE-Single-Container {{ Unsuccessful-PDSCHSetItemIE-PSCH-ReconfFailureTDD }}
Unsuccessful-PDSCHSetList-PSCH-ReconfFailureTDD ::= SEQUENCE (SIZE (0.. 256)) OF ProtocolIE-Single-Container

--Unsuccessful-PDSCHSetItemIE-PSCH-ReconfFailureTDD NBAP-PROTOCOL-IES ::= {
--	{ ID	id-Unsuccessful-PDSCHSetItem-PSCH-ReconfFailureTDD	CRITICALITY ignore	TYPE Unsuccessful-PDSCHSetItem-PSCH-ReconfFailureTDD	PRESENCE mandatory}
--}

Unsuccessful-PDSCHSetItem-PSCH-ReconfFailureTDD ::= SEQUENCE {
	pDSCHSet-ID				PDSCHSet-ID,
	cause					Cause,
--	iE-Extensions			ProtocolExtensionContainer { {Unsuccessful-PDSCHSetItem-PSCH-ReconfFailureTDD-ExtIEs} }		OPTIONAL,
	iE-Extensions			ProtocolExtensionContainer OPTIONAL,
	...
}

--Unsuccessful-PDSCHSetItem-PSCH-ReconfFailureTDD-ExtIEs NBAP-PROTOCOL-EXTENSION ::= {
--	...
--}

--Unsuccessful-PUSCHSetList-PSCH-ReconfFailureTDD ::= SEQUENCE (SIZE (0.. maxNrOfPUSCHSets)) OF ProtocolIE-Single-Container {{ Unsuccessful-PUSCHSetItemIE-PSCH-ReconfFailureTDD }}
Unsuccessful-PUSCHSetList-PSCH-ReconfFailureTDD ::= SEQUENCE (SIZE (0.. 256)) OF ProtocolIE-Single-Container

--Unsuccessful-PUSCHSetItemIE-PSCH-ReconfFailureTDD NBAP-PROTOCOL-IES ::= {
--	{ ID	id-Unsuccessful-PUSCHSetItem-PSCH-ReconfFailureTDD	CRITICALITY ignore	TYPE Unsuccessful-PUSCHSetItem-PSCH-ReconfFailureTDD	PRESENCE mandatory}
--}

Unsuccessful-PUSCHSetItem-PSCH-ReconfFailureTDD ::= SEQUENCE {
	pUSCHSet-ID				PUSCHSet-ID,
	cause					Cause,
--	iE-Extensions			ProtocolExtensionContainer { {Unsuccessful-PUSCHSetItem-PSCH-ReconfFailureTDD-ExtIEs} }		OPTIONAL,
	iE-Extensions			ProtocolExtensionContainer OPTIONAL,
	...
}

--Unsuccessful-PUSCHSetItem-PSCH-ReconfFailureTDD-ExtIEs NBAP-PROTOCOL-EXTENSION ::= {
--	...
--}

-- **************************************************************
--
-- RESET REQUEST
--
-- **************************************************************

--ResetRequest ::= SEQUENCE {
--	protocolIEs				ProtocolIE-Container	{{ResetRequest-IEs}},
--	protocolExtensions		ProtocolExtensionContainer	{{ResetRequest-Extensions}}		OPTIONAL,
--	...
--}
ResetRequest ::= SEQUENCE {
	protocolIEs				ProtocolIE-Container,
	protocolExtensions		ProtocolExtensionContainer	OPTIONAL,
	...
}

--ResetRequest-IEs NBAP-PROTOCOL-IES ::= {
--	{ID	id-ResetIndicator		CRITICALITY	ignore		TYPE 	ResetIndicator		PRESENCE 	mandatory},
--	...
--}

--ResetRequest-Extensions NBAP-PROTOCOL-EXTENSION ::= {
--	...
--}

ResetIndicator ::= CHOICE {
	communicationContext			CommunicationContextList-Reset,
	communicationControlPort		CommunicationControlPortList-Reset,
	nodeB							NULL,
	...
}

CommunicationContextList-Reset ::= SEQUENCE {
	communicationContextInfoList-Reset		CommunicationContextInfoList-Reset,
--	iE-Extensions							ProtocolExtensionContainer  { {CommunicationContextItem-Reset-ExtIEs} }		OPTIONAL,
	iE-Extensions							ProtocolExtensionContainer  OPTIONAL,
	...
}

--CommunicationContextItem-Reset-ExtIEs NBAP-PROTOCOL-EXTENSION ::= {
--	...
--}

--CommunicationContextInfoList-Reset ::= SEQUENCE (SIZE (1.. maxCommunicationContext))	OF ProtocolIE-Single-Container {{ CommunicationContextInfoItemIE-Reset }}
CommunicationContextInfoList-Reset ::= SEQUENCE (SIZE (1.. 1048575))	OF ProtocolIE-Single-Container

--CommunicationContextInfoItemIE-Reset NBAP-PROTOCOL-IES ::= {
--	{ID id-CommunicationContextInfoItem-Reset		CRITICALITY reject		TYPE CommunicationContextInfoItem-Reset		PRESENCE mandatory}
--}

CommunicationContextInfoItem-Reset ::= SEQUENCE {
	communicationContextType-Reset			CommunicationContextType-Reset,
--	iE-Extensions							ProtocolExtensionContainer  { { CommunicationContextInfoItem-Reset-ExtIEs} }		OPTIONAL,
	iE-Extensions							ProtocolExtensionContainer  OPTIONAL,
	...
}

--CommunicationContextInfoItem-Reset-ExtIEs NBAP-PROTOCOL-EXTENSION ::= {
--	...
--}

CommunicationContextType-Reset ::= CHOICE {
	cRNC-CommunicationContextID				CRNC-CommunicationContextID,
	nodeB-CommunicationContextID			NodeB-CommunicationContextID,
	...
}

CommunicationControlPortList-Reset ::= SEQUENCE {
	communicationControlPortInfoList-Reset		CommunicationControlPortInfoList-Reset,
--	iE-Extensions								ProtocolExtensionContainer  { {CommunicationControlPortItem-Reset-ExtIEs} }		OPTIONAL,
	iE-Extensions								ProtocolExtensionContainer  OPTIONAL,
	...
}

--CommunicationControlPortItem-Reset-ExtIEs NBAP-PROTOCOL-EXTENSION ::= {
--	...
--}

--CommunicationControlPortInfoList-Reset ::= SEQUENCE (SIZE (1.. maxCCPinNodeB))	OF ProtocolIE-Single-Container {{CommunicationControlPortInfoItemIE-Reset }}
CommunicationControlPortInfoList-Reset ::= SEQUENCE (SIZE (1.. 256))	OF ProtocolIE-Single-Container

--CommunicationControlPortInfoItemIE-Reset NBAP-PROTOCOL-IES ::= {
--	{ID id-CommunicationControlPortInfoItem-Reset		CRITICALITY reject		TYPE CommunicationControlPortInfoItem-Reset		PRESENCE mandatory}
--}

CommunicationControlPortInfoItem-Reset ::= SEQUENCE {
	communicationControlPortID			CommunicationControlPortID,
--	iE-Extensions						ProtocolExtensionContainer { {CommunicationControlPortInfoItem-Reset-ExtIEs} }	OPTIONAL,
	iE-Extensions						ProtocolExtensionContainer OPTIONAL,
	...
}

--CommunicationControlPortInfoItem-Reset-ExtIEs NBAP-PROTOCOL-EXTENSION ::= {
--	...
--}

-- **************************************************************
--
-- RESET RESPONSE
--
-- **************************************************************

--ResetResponse ::= SEQUENCE {
--	protocolIEs				ProtocolIE-Container	{{ResetResponse-IEs}},
--	protocolExtensions		ProtocolExtensionContainer	{{ResetResponse-Extensions}}     		OPTIONAL,
--	...
--}
ResetResponse ::= SEQUENCE {
	protocolIEs				ProtocolIE-Container,
	protocolExtensions		ProtocolExtensionContainer	OPTIONAL,
	...
}
--ResetResponse-IEs NBAP-PROTOCOL-IES ::= {
--	{ID	id-CriticalityDiagnostics		CRITICALITY		ignore		TYPE	CriticalityDiagnostics		PRESENCE	optional},
--	...
--}

--ResetResponse-Extensions NBAP-PROTOCOL-EXTENSION ::= {
--	...
--}

-- **************************************************************
--
-- INFORMATION EXCHANGE INITIATION REQUEST
--
-- **************************************************************

--InformationExchangeInitiationRequest ::= SEQUENCE {
--	protocolIEs				ProtocolIE-Container	{{InformationExchangeInitiationRequest-IEs}},
--	protocolExtensions		ProtocolExtensionContainer	{{InformationExchangeInitiationRequest-Extensions}}		OPTIONAL,
--	...
--}
InformationExchangeInitiationRequest ::= SEQUENCE {
	protocolIEs				ProtocolIE-Container,
	protocolExtensions		ProtocolExtensionContainer	OPTIONAL,
	...
}
--InformationExchangeInitiationRequest-IEs NBAP-PROTOCOL-IES ::= {
--	{ ID	id-InformationExchangeID								CRITICALITY	reject			TYPE	InformationExchangeID							PRESENCE	mandatory	}|
--	{ ID	id-InformationExchangeObjectType-InfEx-Rqst			CRITICALITY	reject			TYPE 	InformationExchangeObjectType-InfEx-Rqst		PRESENCE 	mandatory	}|
--	{ ID	id-InformationType						CRITICALITY	reject			        TYPE	InformationType					PRESENCE	mandatory	}|
--	{ ID	id-InformationReportCharacteristics						CRITICALITY	reject			TYPE	InformationReportCharacteristics					PRESENCE	mandatory},
--	...
--}

--InformationExchangeInitiationRequest-Extensions NBAP-PROTOCOL-EXTENSION ::= {
--	...
--}

InformationExchangeObjectType-InfEx-Rqst ::= CHOICE {
	cell							Cell-InfEx-Rqst,
	...
}

Cell-InfEx-Rqst ::= SEQUENCE {
	c-ID							C-ID,
--	iE-Extensions					ProtocolExtensionContainer  { { CellItem-InfEx-Rqst-ExtIEs} }		OPTIONAL,
	iE-Extensions					ProtocolExtensionContainer  OPTIONAL,
	...
}

--CellItem-InfEx-Rqst-ExtIEs NBAP-PROTOCOL-EXTENSION ::= {
--	...
--}

-- **************************************************************
--
-- INFORMATION EXCHANGE INITIATION RESPONSE
--
-- **************************************************************
--InformationExchangeInitiationResponse ::= SEQUENCE {
--	protocolIEs				ProtocolIE-Container	{{InformationExchangeInitiationResponse-IEs}},
--	protocolExtensions		ProtocolExtensionContainer	{{InformationExchangeInitiationResponse-Extensions}}		OPTIONAL,
--	...
--}
InformationExchangeInitiationResponse ::= SEQUENCE {
	protocolIEs				ProtocolIE-Container,
	protocolExtensions		ProtocolExtensionContainer	OPTIONAL,
	...
}
--InformationExchangeInitiationResponse-IEs NBAP-PROTOCOL-IES ::= {
--	{ ID	id-InformationExchangeID							CRITICALITY	ignore			TYPE	InformationExchangeID							PRESENCE	mandatory	}|
--	{ ID	id-InformationExchangeObjectType-InfEx-Rsp		CRITICALITY	ignore			TYPE	InformationExchangeObjectType-InfEx-Rsp		PRESENCE	optional	}|
--	{ ID	id-CriticalityDiagnostics					CRITICALITY	ignore			TYPE	CriticalityDiagnostics					PRESENCE	optional	},
--	...
--}

--InformationExchangeInitiationResponse-Extensions NBAP-PROTOCOL-EXTENSION ::= {
--	...
--}

InformationExchangeObjectType-InfEx-Rsp ::= CHOICE {
 	cell						Cell-InfEx-Rsp,
	...
 }

Cell-InfEx-Rsp ::= SEQUENCE {
 	requestedDataValue			    RequestedDataValue,
--	iE-Extensions					ProtocolExtensionContainer  { { CellItem-InfEx-Rsp-ExtIEs} }		OPTIONAL,
	iE-Extensions					ProtocolExtensionContainer  OPTIONAL,
	...
 }

--CellItem-InfEx-Rsp-ExtIEs NBAP-PROTOCOL-EXTENSION ::= {
--	...
--}

-- **************************************************************
--
-- INFORMATION EXCHANGE INITIATION FAILURE
--
-- **************************************************************

--InformationExchangeInitiationFailure ::= SEQUENCE {
--	protocolIEs				ProtocolIE-Container	{{InformationExchangeInitiationFailure-IEs}},
--	protocolExtensions		ProtocolExtensionContainer	{{InformationExchangeInitiationFailure-Extensions}}		OPTIONAL,
--	...
--}
InformationExchangeInitiationFailure ::= SEQUENCE {
	protocolIEs				ProtocolIE-Container,
	protocolExtensions		ProtocolExtensionContainer	OPTIONAL,
	...
}
--InformationExchangeInitiationFailure-IEs NBAP-PROTOCOL-IES ::= {
--	{ ID	id-InformationExchangeID				CRITICALITY		ignore			TYPE	InformationExchangeID				PRESENCE	mandatory	}|
--	{ ID	id-Cause						CRITICALITY		ignore			TYPE	Cause						PRESENCE	mandatory	}|
--	{ ID	id-CriticalityDiagnostics		CRITICALITY		ignore			TYPE	CriticalityDiagnostics		PRESENCE	optional	},
--	...
--}

--InformationExchangeInitiationFailure-Extensions NBAP-PROTOCOL-EXTENSION ::= {
--	...
--}

-- **************************************************************
--
-- INFORMATION REPORT
--
-- **************************************************************

--InformationReport ::= SEQUENCE {
--	protocolIEs				ProtocolIE-Container	{{InformationReport-IEs}},
--	protocolExtensions		ProtocolExtensionContainer	{{InformationReport-Extensions}}		OPTIONAL,
--	...
--}
InformationReport ::= SEQUENCE {
	protocolIEs				ProtocolIE-Container,
	protocolExtensions		ProtocolExtensionContainer	OPTIONAL,
	...
}

--InformationReport-IEs NBAP-PROTOCOL-IES ::= {
--	{ ID	id-InformationExchangeID							CRITICALITY	ignore			TYPE	InformationExchangeID							PRESENCE	mandatory	}|
--	{ ID	id-InformationExchangeObjectType-InfEx-Rprt		CRITICALITY	ignore			TYPE	InformationExchangeObjectType-InfEx-Rprt		PRESENCE	mandatory	},
--	...
--}

--InformationReport-Extensions NBAP-PROTOCOL-EXTENSION ::= {
--	...
--}

InformationExchangeObjectType-InfEx-Rprt ::= CHOICE {
	cell							Cell-Inf-Rprt,
	...
 }

Cell-Inf-Rprt ::= SEQUENCE {
	requestedDataValueInformation	RequestedDataValueInformation,
--	iE-Extensions					ProtocolExtensionContainer  {{ CellItem-Inf-Rprt-ExtIEs }}		OPTIONAL,
	iE-Extensions					ProtocolExtensionContainer  OPTIONAL,
	...

 }

--CellItem-Inf-Rprt-ExtIEs NBAP-PROTOCOL-EXTENSION ::= {
--	...
--

-- **************************************************************
--
-- INFORMATION EXCHANGE TERMINATION REQUEST
--
-- **************************************************************

--formationExchangeTerminationRequest ::= SEQUENCE {
--protocolIEs				ProtocolIE-Container	{{InformationExchangeTerminationRequest-IEs}},
--	protocolExtensions		ProtocolExtensionContainer	{{InformationExchangeTerminationRequest-Extensions}}		OPTIONAL,
--	...
--}
InformationExchangeTerminationRequest ::= SEQUENCE {
	protocolIEs				ProtocolIE-Container,
	protocolExtensions		ProtocolExtensionContainer	OPTIONAL,
	...
}

--InformationExchangeTerminationRequest-IEs NBAP-PROTOCOL-IES ::= {
--	{ ID	id-InformationExchangeID			CRITICALITY		ignore				TYPE	InformationExchangeID			PRESENCE	mandatory},
--	...
--}

--InformationExchangeTerminationRequest-Extensions NBAP-PROTOCOL-EXTENSION ::= {
--	...
--}

-- **************************************************************
--
-- INFORMATION EXCHANGE FAILURE INDICATION
--
-- **************************************************************

--InformationExchangeFailureIndication ::= SEQUENCE {
--	protocolIEs				ProtocolIE-Container	{{InformationExchangeFailureIndication-IEs}},
--	protocolExtensions			ProtocolExtensionContainer	{{InformationExchangeFailureIndication-Extensions}}				OPTIONAL,
--	...
--}
InformationExchangeFailureIndication ::= SEQUENCE {
	protocolIEs				ProtocolIE-Container,
	protocolExtensions			ProtocolExtensionContainer	OPTIONAL,
	...
}

--InformationExchangeFailureIndication-IEs NBAP-PROTOCOL-IES ::= {
--	{ ID	id-InformationExchangeID			CRITICALITY	ignore			TYPE	InformationExchangeID			PRESENCE	mandatory	}|
--	{ ID	id-Cause					CRITICALITY	ignore			TYPE	Cause					PRESENCE	mandatory	},
--	...
--}

--InformationExchangeFailureIndication-Extensions NBAP-PROTOCOL-EXTENSION ::= {
--	...
--}

-- **************************************************************
--
-- CELL SYNCHRONISATION INITIATION REQUEST TDD
--
-- **************************************************************

--CellSynchronisationInitiationRequestTDD ::= SEQUENCE {
--	protocolIEs				ProtocolIE-Container	{{CellSynchronisationInitiationRequestTDD-IEs}},
--	protocolExtensions		ProtocolExtensionContainer	{{CellSynchronisationInitiationRequestTDD-Extensions}}     OPTIONAL,
--	...
--}
CellSynchronisationInitiationRequestTDD ::= SEQUENCE {
	protocolIEs				ProtocolIE-Container,
	protocolExtensions		ProtocolExtensionContainer	OPTIONAL,
	...
}

--CellSynchronisationInitiationRequestTDD-Extensions NBAP-PROTOCOL-EXTENSION ::= {
--	{ ID	id-SYNCDlCodeId-TransInitLCR-CellSyncInitiationRqstTDD		CRITICALITY 	reject		EXTENSION	SYNCDlCodeId-TransInitLCR-CellSyncInitiationRqstTDD		PRESENCE 	optional	}|
	-- Applicable to 1.28Mcps TDD only
--	{ ID	id-SYNCDlCodeId-MeasureInitLCR-CellSyncInitiationRqstTDD		CRITICALITY 	reject		EXTENSION	SYNCDlCodeId-MeasureInitLCR-CellSyncInitiationRqstTDD		PRESENCE 	optional	},
	-- Applicable to 1.28Mcps TDD only
--	...
--}

--CellSynchronisationInitiationRequestTDD-IEs NBAP-PROTOCOL-IES ::= {
--	{ ID	id-C-ID							CRITICALITY		reject		TYPE	C-ID							PRESENCE	mandatory	}|
--	{ ID	id-cellSyncBurstRepetitionPeriod			CRITICALITY		reject		TYPE	CellSyncBurstRepetitionPeriod		PRESENCE	mandatory	}|
--	{ ID	id-timeslotInfo-CellSyncInitiationRqstTDD	CRITICALITY 	reject		TYPE	TimeslotInfo-CellSyncInitiationRqstTDD		PRESENCE 	optional	}|
	-- Mandatory for 3.84Mcps TDD. Not Applicable to 1.28Mcps TDD.
--	{ ID	id-CellSyncBurstTransInit-CellSyncInitiationRqstTDD		CRITICALITY 	reject		TYPE	CellSyncBurstTransInit-CellSyncInitiationRqstTDD		PRESENCE 	optional	}|
	-- Applicable to 3.84Mcps TDD only
--	{ ID	id-CellSyncBurstMeasureInit-CellSyncInitiationRqstTDD		CRITICALITY 	reject		TYPE	CellSyncBurstMeasureInit-CellSyncInitiationRqstTDD		PRESENCE 	optional	},
	-- Applicable to 3.84Mcps TDD only
--	...
--}

CellSyncBurstTransInit-CellSyncInitiationRqstTDD::= SEQUENCE {
	cSBTransmissionID						CSBTransmissionID,
	sfn										SFN,
 	cellSyncBurstCode						CellSyncBurstCode,
	cellSyncBurstCodeShift					CellSyncBurstCodeShift,
	initialDLTransPower						DL-Power,
--	iE-Extensions							ProtocolExtensionContainer { { CellSyncBurstTransInit-CellSyncInitiationRqstTDD-ExtIEs} }		OPTIONAL,
	iE-Extensions							ProtocolExtensionContainer OPTIONAL,
	...
 }

--CellSyncBurstTransInit-CellSyncInitiationRqstTDD-ExtIEs NBAP-PROTOCOL-EXTENSION ::= {
--	...
--}

TimeslotInfo-CellSyncInitiationRqstTDD::= SEQUENCE (SIZE (1..15)) OF TimeSlot

CellSyncBurstMeasureInit-CellSyncInitiationRqstTDD::= SEQUENCE {
	cSBMeasurementID						CSBMeasurementID,
	cellSyncBurstCode						CellSyncBurstCode,
	cellSyncBurstCodeShift					CellSyncBurstCodeShift,
	synchronisationReportType				SynchronisationReportType,
	sfn										SFN							OPTIONAL,
	synchronisationReportCharacteristics	SynchronisationReportCharacteristics,
--	iE-Extensions							ProtocolExtensionContainer { { CellSyncBurstMeasureInit-CellSyncInitiationRqstTDD-ExtIEs} }		OPTIONAL,
	iE-Extensions							ProtocolExtensionContainer OPTIONAL,
	...
 }

--CellSyncBurstMeasureInit-CellSyncInitiationRqstTDD-ExtIEs NBAP-PROTOCOL-EXTENSION ::= {
--	...
--}

SYNCDlCodeId-TransInitLCR-CellSyncInitiationRqstTDD::= SEQUENCE {
	cSBTransmissionID						CSBTransmissionID,
	sfn										SFN,
	uARFCN									UARFCN,
	sYNCDlCodeId							SYNCDlCodeId,
	dwPCH-Power								DwPCH-Power,
--	iE-Extensions							ProtocolExtensionContainer { { SYNCDlCodeId-TransInitLCR-CellSyncInitiationRqstTDD-ExtIEs } }	OPTIONAL,
	iE-Extensions							ProtocolExtensionContainer OPTIONAL,
	...
}

--SYNCDlCodeId-TransInitLCR-CellSyncInitiationRqstTDD-ExtIEs NBAP-PROTOCOL-EXTENSION ::= {
--	...
--}

SYNCDlCodeId-MeasureInitLCR-CellSyncInitiationRqstTDD::= SEQUENCE {
	cSBMeasurementID						CSBMeasurementID,
	sfn										SFN				OPTIONAL,
	uARFCN									UARFCN,
	sYNCDlCodeId							SYNCDlCodeId,
	synchronisationReportType				SynchronisationReportType,
	synchronisationReportCharacteristics	SynchronisationReportCharacteristics,
--	iE-Extensions							ProtocolExtensionContainer { { SYNCDlCodeId-MeasureInitLCR-CellSyncInitiationRqstTDD-ExtIEs } }	OPTIONAL,
	iE-Extensions							ProtocolExtensionContainer OPTIONAL,
	...
}

--SYNCDlCodeId-MeasureInitLCR-CellSyncInitiationRqstTDD-ExtIEs NBAP-PROTOCOL-EXTENSION ::= {
--	...
--}

-- **************************************************************
--
-- CELL SYNCHRONISATION INITIATION RESPONSE TDD
--
-- **************************************************************
--CellSynchronisationInitiationResponseTDD ::= SEQUENCE {
--	protocolIEs				ProtocolIE-Container	{{CellSynchronisationInitiationResponseTDD-IEs}},
--	protocolExtensions		ProtocolExtensionContainer	{{CellSynchronisationInitiationResponseTDD-Extensions}}     OPTIONAL,
--	...
--}
CellSynchronisationInitiationResponseTDD ::= SEQUENCE {
	protocolIEs				ProtocolIE-Container,
	protocolExtensions		ProtocolExtensionContainer	OPTIONAL,
	...
}

--CellSynchronisationInitiationResponseTDD-Extensions NBAP-PROTOCOL-EXTENSION ::= {
--	...
--}

--CellSynchronisationInitiationResponseTDD-IEs NBAP-PROTOCOL-IES ::= {
--	{ ID	id-CriticalityDiagnostics					CRITICALITY		ignore		TYPE	CriticalityDiagnostics								PRESENCE	optional	},
--	...
--}

-- **************************************************************
--
-- CELL SYNCHRONISATION INITIATION FAILURE TDD
--
-- **************************************************************

--CellSynchronisationInitiationFailureTDD ::= SEQUENCE {
--	protocolIEs				ProtocolIE-Container	{{CellSynchronisationInitiationFailureTDD-IEs}},
--	protocolExtensions		ProtocolExtensionContainer	{{CellSynchronisationInitiationFailureTDD-Extensions}}     OPTIONAL,
--	...
--}
CellSynchronisationInitiationFailureTDD ::= SEQUENCE {
	protocolIEs				ProtocolIE-Container,
	protocolExtensions		ProtocolExtensionContainer	OPTIONAL,
	...
}

--CellSynchronisationInitiationFailureTDD-Extensions NBAP-PROTOCOL-EXTENSION ::= {
--	...
--}

--CellSynchronisationInitiationFailureTDD-IEs NBAP-PROTOCOL-IES ::= {
--	{ ID	id-Cause							CRITICALITY		ignore		TYPE	Cause							PRESENCE	mandatory	}|
--	{ ID	id-CriticalityDiagnostics			CRITICALITY		ignore		TYPE	CriticalityDiagnostics		PRESENCE	optional	},
--	...
--}

-- **************************************************************
--
-- CELL SYNCHRONISATION RECONFIGURATION REQUEST TDD
--
-- **************************************************************

--CellSynchronisationReconfigurationRequestTDD ::= SEQUENCE {
--	protocolIEs				ProtocolIE-Container	{{CellSynchronisationReconfigurationRequestTDD-IEs}},
--	protocolExtensions		ProtocolExtensionContainer	{{CellSynchronisationReconfigurationRequestTDD-Extensions}}     OPTIONAL,
--	...
--}
CellSynchronisationReconfigurationRequestTDD ::= SEQUENCE {
	protocolIEs				ProtocolIE-Container,
	protocolExtensions		ProtocolExtensionContainer	OPTIONAL,
	...
}

--CellSynchronisationReconfigurationRequestTDD-Extensions NBAP-PROTOCOL-EXTENSION ::= {
--	{ ID id-NSubCyclesPerCyclePeriod-CellSyncReconfRqstTDD				CRITICALITY reject	EXTENSION	NSubCyclesPerCyclePeriod										PRESENCE optional }|
	-- Applicable to 1.28Mcps TDD only
--	{ ID id-SYNCDlCodeIdTransReconfInfoLCR-CellSyncReconfRqstTDD			CRITICALITY reject	EXTENSION	SYNCDlCodeIdTransReconfInfoLCR-CellSyncReconfRqstTDD			PRESENCE optional }|
	-- Applicable to 1.28Mcps TDD only
--	{ ID id-SYNCDlCodeIdMeasReconfigurationLCR-CellSyncReconfRqstTDD		CRITICALITY reject	EXTENSION	SYNCDlCodeIdMeasInfoLCR-CellSyncReconfRqstTDD		PRESENCE optional },
	-- Applicable to 1.28Mcps TDD only
--	...
--}

--CellSynchronisationReconfigurationRequestTDD-IEs NBAP-PROTOCOL-IES ::= {
--	{ ID	id-C-ID							CRITICALITY		reject		TYPE	C-ID							PRESENCE		mandatory	}|
--	{ ID	id-TimeSlot						CRITICALITY		reject		TYPE	TimeSlot						PRESENCE 	mandatory	}|
	-- Applicable to 3.84Mcps TDD only. For 1.28Mcps TDD, the CRNC should set this to 0 and the Node B shall ignore it.
--	{ ID	id-NCyclesPerSFNperiod			CRITICALITY		reject		TYPE	NCyclesPerSFNperiod			PRESENCE 	mandatory	}|
--	{ ID	id-NRepetitionsPerCyclePeriod	CRITICALITY		reject		TYPE	NRepetitionsPerCyclePeriod PRESENCE 	mandatory	}|
--	{ ID	id-CellSyncBurstTransReconfInfo-CellSyncReconfRqstTDD		CRITICALITY 	reject		TYPE	CellSyncBurstTransReconfInfo-CellSyncReconfRqstTDD		PRESENCE 	optional	}|
	-- Applicable to 3.84Mcps TDD only
--	{ ID	id-CellSyncBurstMeasReconfiguration-CellSyncReconfRqstTDD		CRITICALITY 	reject		TYPE	CellSyncBurstMeasInfo-CellSyncReconfRqstTDD		PRESENCE 	optional	},
	-- Applicable to 3.84Mcps TDD only
--	...
--}

--CellSyncBurstTransReconfInfo-CellSyncReconfRqstTDD ::= SEQUENCE (SIZE (1.. maxNrOfCellSyncBursts)) OF CellSyncBurstTransInfoItem-CellSyncReconfRqstTDD
CellSyncBurstTransReconfInfo-CellSyncReconfRqstTDD ::= SEQUENCE (SIZE (1.. 10)) OF CellSyncBurstTransInfoItem-CellSyncReconfRqstTDD

CellSyncBurstTransInfoItem-CellSyncReconfRqstTDD ::= SEQUENCE {
	cSBTransmissionID							CSBTransmissionID,
	syncFrameNumberToTransmit					SyncFrameNumber,
	cellSyncBurstCode							CellSyncBurstCode			OPTIONAL,
	cellSyncBurstCodeShift						CellSyncBurstCodeShift		OPTIONAL,
	dlTransPower								DL-Power					OPTIONAL,
--	iE-Extensions								ProtocolExtensionContainer { { CellSyncBurstTransInfoItem-CellSyncReconfRqstTDD-ExtIEs} }		OPTIONAL,
	iE-Extensions								ProtocolExtensionContainer OPTIONAL,
	...
}

--CellSyncBurstTransInfoItem-CellSyncReconfRqstTDD-ExtIEs NBAP-PROTOCOL-EXTENSION ::= {
--	...
--}


CellSyncBurstMeasInfo-CellSyncReconfRqstTDD ::= SEQUENCE {
	cellSyncBurstMeasInfoList-CellSyncReconfRqstTDD		CellSyncBurstMeasInfoList-CellSyncReconfRqstTDD,
	synchronisationReportType							SynchronisationReportTypeIE				OPTIONAL,
	synchronisationReportCharacteristics				SynchronisationReportCharacteristicsIE	OPTIONAL,
--	iE-Extensions										ProtocolExtensionContainer { { CellSyncBurstMeasInfo-CellSyncReconfRqstTDD-ExtIEs} }		OPTIONAL,
	iE-Extensions										ProtocolExtensionContainer OPTIONAL,
	...
}

--CellSyncBurstMeasInfo-CellSyncReconfRqstTDD-ExtIEs NBAP-PROTOCOL-EXTENSION ::= {
--	...
--}

--CellSyncBurstMeasInfoList-CellSyncReconfRqstTDD ::= ProtocolIE-Single-Container {{ CellSyncBurstMeasInfoListIEs-CellSyncReconfRqstTDD }}
CellSyncBurstMeasInfoList-CellSyncReconfRqstTDD ::= ProtocolIE-Single-Container

--CellSyncBurstMeasInfoListIEs-CellSyncReconfRqstTDD NBAP-PROTOCOL-IES ::= {
--	{ ID id-CellSyncBurstMeasInfoList-CellSyncReconfRqstTDD   CRITICALITY reject	TYPE CellSyncBurstMeasInfoListIE-CellSyncReconfRqstTDD		PRESENCE mandatory }
--}

SynchronisationReportTypeIE ::= ProtocolIE-Single-Container

--SynchronisationReportTypeIEs NBAP-PROTOCOL-IES ::= {
--	{ ID id-SynchronisationReportType					CRITICALITY reject	TYPE SynchronisationReportType			 				PRESENCE	mandatory }
--}

--SynchronisationReportCharacteristicsIE ::= ProtocolIE-Single-Container {{ SynchronisationReportCharacteristicsIEs }}
SynchronisationReportCharacteristicsIE ::= ProtocolIE-Single-Container

--SynchronisationReportCharacteristicsIEs NBAP-PROTOCOL-IES ::= {
--	{ ID id-SynchronisationReportCharacteristics		CRITICALITY reject	TYPE SynchronisationReportCharacteristics		 	PRESENCE	mandatory }
--}


--CellSyncBurstMeasInfoListIE-CellSyncReconfRqstTDD ::= SEQUENCE (SIZE (1.. maxNrOfCellSyncBursts)) OF CellSyncBurstMeasInfoItem-CellSyncReconfRqstTDD
CellSyncBurstMeasInfoListIE-CellSyncReconfRqstTDD ::= SEQUENCE (SIZE (1.. 10)) OF CellSyncBurstMeasInfoItem-CellSyncReconfRqstTDD

CellSyncBurstMeasInfoItem-CellSyncReconfRqstTDD ::= SEQUENCE {
	syncFrameNrToReceive					SyncFrameNumber,
	syncBurstInfo							CellSyncBurstInfoList-CellSyncReconfRqstTDD,
--	iE-Extensions							ProtocolExtensionContainer { { CellSyncBurstMeasInfoItem-CellSyncReconfRqstTDD-ExtIEs} }		OPTIONAL,
	iE-Extensions							ProtocolExtensionContainer OPTIONAL,
	...
}

--CellSyncBurstMeasInfoItem-CellSyncReconfRqstTDD-ExtIEs NBAP-PROTOCOL-EXTENSION ::= {
--	...
--}

--CellSyncBurstInfoList-CellSyncReconfRqstTDD ::= SEQUENCE (SIZE (1..maxNrOfReceptsPerSyncFrame)) OF CellSyncBurstInfoItem-CellSyncReconfRqstTDD
CellSyncBurstInfoList-CellSyncReconfRqstTDD ::= SEQUENCE (SIZE (1..16)) OF CellSyncBurstInfoItem-CellSyncReconfRqstTDD

CellSyncBurstInfoItem-CellSyncReconfRqstTDD ::= SEQUENCE {
	cSBMeasurementID							CSBMeasurementID,
	cellSyncBurstCode							CellSyncBurstCode,
	cellSyncBurstCodeShift						CellSyncBurstCodeShift,
--	iE-Extensions								ProtocolExtensionContainer { { CellSyncBurstInfoItem-CellSyncReconfRqstTDD-ExtIEs} }		OPTIONAL,
	iE-Extensions								ProtocolExtensionContainer OPTIONAL,
	...
}

--CellSyncBurstInfoItem-CellSyncReconfRqstTDD-ExtIEs NBAP-PROTOCOL-EXTENSION ::= {
--	...
--}

--SYNCDlCodeIdTransReconfInfoLCR-CellSyncReconfRqstTDD ::= SEQUENCE (SIZE (1..maxNrOfSyncFramesLCR)) OF SYNCDlCodeIdTransReconfItemLCR-CellSyncReconfRqstTDD
SYNCDlCodeIdTransReconfInfoLCR-CellSyncReconfRqstTDD ::= SEQUENCE (SIZE (1..512)) OF SYNCDlCodeIdTransReconfItemLCR-CellSyncReconfRqstTDD

SYNCDlCodeIdTransReconfItemLCR-CellSyncReconfRqstTDD ::= SEQUENCE {
	cSBTransmissionID							CSBTransmissionID,
	syncFrameNumberforTransmit					SyncFrameNumber,
	uARFCN										UARFCN,
	sYNCDlCodeId								SYNCDlCodeId	OPTIONAL,
	dwPCH-Power									DwPCH-Power		OPTIONAL,
--	iE-Extensions								ProtocolExtensionContainer { { SYNCDlCodeIdTransReconfInfoLCR-CellSyncReconfRqstTDD-ExtIEs} }		OPTIONAL,
	iE-Extensions								ProtocolExtensionContainer OPTIONAL,
	...
}

--SYNCDlCodeIdTransReconfInfoLCR-CellSyncReconfRqstTDD-ExtIEs NBAP-PROTOCOL-EXTENSION ::= {
--	...
--}


SYNCDlCodeIdMeasInfoLCR-CellSyncReconfRqstTDD::= SEQUENCE {

	sYNCDlCodeIdMeasInfoList					SYNCDlCodeIdMeasInfoList-CellSyncReconfRqstTDD,
	synchronisationReportType					SynchronisationReportType						OPTIONAL,
	synchronisationReportCharacteristics		SynchronisationReportCharacteristics   		OPTIONAL,
--	iE-Extensions		ProtocolExtensionContainer	 { { SYNCDlCodeIdMeasInfoLCR-CellSyncReconfRqstTDD-ExtIEs} } OPTIONAL,
	iE-Extensions		ProtocolExtensionContainer	OPTIONAL,
	...
}

--SYNCDlCodeIdMeasInfoLCR-CellSyncReconfRqstTDD-ExtIEs NBAP-PROTOCOL-EXTENSION ::= {
--	...
--}

--SYNCDlCodeIdMeasInfoList-CellSyncReconfRqstTDD::= SEQUENCE (SIZE (1.. maxNrOfSyncDLCodesLCR)) OF SYNCDlCodeIdMeasInfoItem-CellSyncReconfRqstTDD
SYNCDlCodeIdMeasInfoList-CellSyncReconfRqstTDD::= SEQUENCE (SIZE (1.. 32)) OF SYNCDlCodeIdMeasInfoItem-CellSyncReconfRqstTDD

SYNCDlCodeIdMeasInfoItem-CellSyncReconfRqstTDD ::= SEQUENCE {
	syncFrameNrToReceive					SyncFrameNumber,
	sYNCDlCodeIdInfoLCR						SYNCDlCodeIdInfoListLCR-CellSyncReconfRqstTDD,
--	iE-Extensions							ProtocolExtensionContainer { { SYNCDlCodeIdMeasInfoItem-CellSyncReconfRqstTDD-ExtIEs} }		OPTIONAL,
	iE-Extensions							ProtocolExtensionContainer OPTIONAL,
	...
}

--SYNCDlCodeIdMeasInfoItem-CellSyncReconfRqstTDD-ExtIEs NBAP-PROTOCOL-EXTENSION ::= {
--	...
--}

--SYNCDlCodeIdInfoListLCR-CellSyncReconfRqstTDD ::= SEQUENCE (SIZE (1.. maxNrOfReceptionsperSyncFrameLCR)) OF SYNCDlCodeIdInfoItemLCR-CellSyncReconfRqstTDD
SYNCDlCodeIdInfoListLCR-CellSyncReconfRqstTDD ::= SEQUENCE (SIZE (1.. 8)) OF SYNCDlCodeIdInfoItemLCR-CellSyncReconfRqstTDD

SYNCDlCodeIdInfoItemLCR-CellSyncReconfRqstTDD ::= SEQUENCE {
	cSBMeasurementID							CSBMeasurementID,
	sYNCDlCodeId								SYNCDlCodeId,
	uARFCN										UARFCN,
	propagationDelayCompensation				TimingAdjustmentValueLCR		OPTIONAL,
--	iE-Extensions								ProtocolExtensionContainer { { SYNCDlCodeIdInfoItemLCR-CellSyncReconfRqstTDD-ExtIEs} }		OPTIONAL,
	iE-Extensions								ProtocolExtensionContainer OPTIONAL,
	...
}

--SYNCDlCodeIdInfoItemLCR-CellSyncReconfRqstTDD-ExtIEs NBAP-PROTOCOL-EXTENSION ::= {
--	...
--}

-- **************************************************************
--
-- CELL SYNCHRONISATION RECONFIGURATION RESPONSE TDD
--
-- **************************************************************

--CellSynchronisationReconfigurationResponseTDD ::= SEQUENCE {
--	protocolIEs				ProtocolIE-Container	{{CellSynchronisationReconfigurationResponseTDD-IEs}},
--	protocolExtensions		ProtocolExtensionContainer	{{CellSynchronisationReconfigurationResponseTDD-Extensions}}     OPTIONAL,
--	...
--}
CellSynchronisationReconfigurationResponseTDD ::= SEQUENCE {
	protocolIEs				ProtocolIE-Container,
	protocolExtensions		ProtocolExtensionContainer	OPTIONAL,
	...
}

--CellSynchronisationReconfigurationResponseTDD-Extensions NBAP-PROTOCOL-EXTENSION ::= {
--	...
--}

--CellSynchronisationReconfigurationResponseTDD-IEs NBAP-PROTOCOL-IES ::= {
--	{ ID	id-CriticalityDiagnostics					CRITICALITY		ignore		TYPE	CriticalityDiagnostics			PRESENCE	optional	},
--	...
--}

-- **************************************************************
--
-- CELL SYNCHRONISATION RECONFIGURATION FAILURE TDD
--
-- **************************************************************

--CellSynchronisationReconfigurationFailureTDD ::= SEQUENCE {
--	protocolIEs				ProtocolIE-Container		{{CellSynchronisationReconfigurationFailureTDD-IEs}},
--	protocolExtensions		ProtocolExtensionContainer	{{CellSynchronisationReconfigurationFailureTDD-Extensions}}     OPTIONAL,
--	...
--}
CellSynchronisationReconfigurationFailureTDD ::= SEQUENCE {
	protocolIEs				ProtocolIE-Container,
	protocolExtensions		ProtocolExtensionContainer	OPTIONAL,
	...
}

--CellSynchronisationReconfigurationFailureTDD-Extensions NBAP-PROTOCOL-EXTENSION ::= {
--	...
--}

--CellSynchronisationReconfigurationFailureTDD-IEs NBAP-PROTOCOL-IES ::= {
--	{ ID	id-Cause							CRITICALITY		ignore		TYPE	Cause							PRESENCE	mandatory	}|
--	{ ID	id-CriticalityDiagnostics			CRITICALITY		ignore		TYPE	CriticalityDiagnostics		PRESENCE	optional	},
--	...
--}

-- **************************************************************
--
-- CELL SYNCHRONISATION ADJUSTMENT REQUEST TDD
--
-- **************************************************************

--CellSynchronisationAdjustmentRequestTDD ::= SEQUENCE {
--	protocolIEs				ProtocolIE-Container		{{CellSynchronisationAdjustmentRequestTDD-IEs}},
--	protocolExtensions		ProtocolExtensionContainer	{{CellSynchronisationAdjustmentRequestTDD-Extensions}}     OPTIONAL,
--	...
--}
CellSynchronisationAdjustmentRequestTDD ::= SEQUENCE {
	protocolIEs				ProtocolIE-Container,
	protocolExtensions		ProtocolExtensionContainer	OPTIONAL,
	...
}

--CellSynchronisationAdjustmentRequestTDD-Extensions NBAP-PROTOCOL-EXTENSION ::= {
--	...
--}

--CellSynchronisationAdjustmentRequestTDD-IEs NBAP-PROTOCOL-IES ::= {
--	{ ID	id-CellAdjustmentInfo-SyncAdjustmntRqstTDD	CRITICALITY	ignore	TYPE CellAdjustmentInfo-SyncAdjustmentRqstTDD	PRESENCE mandatory	},
--	...
--}

--CellAdjustmentInfo-SyncAdjustmentRqstTDD::= SEQUENCE (SIZE (1..maxCellinNodeB)) OF ProtocolIE-Single-Container {{ CellAdjustmentInfoItemIE-SyncAdjustmntRqstTDD }}
CellAdjustmentInfo-SyncAdjustmentRqstTDD::= SEQUENCE (SIZE (1..256)) OF ProtocolIE-Single-Container

--CellAdjustmentInfoItemIE-SyncAdjustmntRqstTDD NBAP-PROTOCOL-IES ::= {
--	{ ID id-CellAdjustmentInfoItem-SyncAdjustmentRqstTDD		CRITICALITY		ignore			TYPE		CellAdjustmentInfoItem-SyncAdjustmentRqstTDD		PRESENCE	mandatory }
--}

CellAdjustmentInfoItem-SyncAdjustmentRqstTDD ::= SEQUENCE {
	c-ID									C-ID,
	frameAdjustmentValue					FrameAdjustmentValue		OPTIONAL,
	timingAdjustmentValue					TimingAdjustmentValue		OPTIONAL,
	dLTransPower							DL-Power					OPTIONAL, -- Applicable to 3.84Mcps TDD only
	sfn										SFN							OPTIONAL,
--	iE-Extensions							ProtocolExtensionContainer { { CellAdjustmentInfoItem-SyncAdjustmntRqstTDD-ExtIEs} }		OPTIONAL,
	iE-Extensions							ProtocolExtensionContainer OPTIONAL,
	...
 }

--CellAdjustmentInfoItem-SyncAdjustmntRqstTDD-ExtIEs NBAP-PROTOCOL-EXTENSION ::= {
--	{ ID id-DwPCH-Power					CRITICALITY ignore	EXTENSION DwPCH-Power			PRESENCE optional }|
 -- Applicable to 1.28Mcps TDD only
--	{ ID id-TimingAdjustmentValueLCR	CRITICALITY ignore	EXTENSION TimingAdjustmentValueLCR	PRESENCE optional },
 -- Applicable to 1.28Mcps TDD only
--	...
--}

-- **************************************************************
--
-- CELL SYNCHRONISATION ADJUSTMENT RESPONSE TDD
--
-- **************************************************************

--CellSynchronisationAdjustmentResponseTDD ::= SEQUENCE {
--	protocolIEs				ProtocolIE-Container	{{CellSynchronisationAdjustmentResponseTDD-IEs}},
--	protocolExtensions		ProtocolExtensionContainer	{{CellSynchronisationAdjustmentResponseTDD-Extensions}}     OPTIONAL,
--	...
--}
CellSynchronisationAdjustmentResponseTDD ::= SEQUENCE {
	protocolIEs				ProtocolIE-Container,
	protocolExtensions		ProtocolExtensionContainer	OPTIONAL,
	...
}

--CellSynchronisationAdjustmentResponseTDD-Extensions NBAP-PROTOCOL-EXTENSION ::= {
--	...
--}

--CellSynchronisationAdjustmentResponseTDD-IEs NBAP-PROTOCOL-IES ::= {
--	{ ID	id-CriticalityDiagnostics			CRITICALITY		ignore		TYPE	CriticalityDiagnostics					PRESENCE	optional	},
--	...
--}

-- **************************************************************
--
-- CELL SYNCHRONISATION ADJUSTMENT FAILURE TDD
--
-- **************************************************************

--CellSynchronisationAdjustmentFailureTDD ::= SEQUENCE {
--	protocolIEs				ProtocolIE-Container	{{CellSynchronisationAdjustmentFailureTDD-IEs}},
--	protocolExtensions		ProtocolExtensionContainer	{{CellSynchronisationAdjustmentFailureTDD-Extensions}}     OPTIONAL,
--	...
--}
CellSynchronisationAdjustmentFailureTDD ::= SEQUENCE {
	protocolIEs				ProtocolIE-Container,
	protocolExtensions		ProtocolExtensionContainer	OPTIONAL,
	...
}
--CellSynchronisationAdjustmentFailureTDD-Extensions NBAP-PROTOCOL-EXTENSION ::= {
--	...
--}

--CellSynchronisationAdjustmentFailureTDD-IEs NBAP-PROTOCOL-IES ::= {
--	{ ID	id-CauseLevel-SyncAdjustmntFailureTDD	CRITICALITY	ignore		TYPE	CauseLevel-SyncAdjustmntFailureTDD		PRESENCE	mandatory	}|
--	{ ID	id-CriticalityDiagnostics				CRITICALITY	ignore		TYPE	CriticalityDiagnostics						PRESENCE	optional	},
--	...
--}

CauseLevel-SyncAdjustmntFailureTDD ::= CHOICE {
	generalCause			GeneralCauseList-SyncAdjustmntFailureTDD,
	cellSpecificCause		CellSpecificCauseList-SyncAdjustmntFailureTDD,
	...
}

GeneralCauseList-SyncAdjustmntFailureTDD::= SEQUENCE {
	cause										Cause,
--	iE-Extensions								ProtocolExtensionContainer { { GeneralCauseList-SyncAdjustmntFailureTDD-ExtIEs} }		OPTIONAL,
	iE-Extensions								ProtocolExtensionContainer OPTIONAL,
	...
}

--GeneralCauseList-SyncAdjustmntFailureTDD-ExtIEs NBAP-PROTOCOL-EXTENSION ::= {
--	...
--}

CellSpecificCauseList-SyncAdjustmntFailureTDD ::= SEQUENCE {
	unsuccessful-cell-InformationRespList-SyncAdjustmntFailureTDD		Unsuccessful-cell-InformationRespList-SyncAdjustmntFailureTDD,
--	iE-Extensions								ProtocolExtensionContainer { { CellSpecificCauseList-SyncAdjustmntFailureTDD-ExtIEs} }		OPTIONAL,
	iE-Extensions								ProtocolExtensionContainer OPTIONAL,
	...
}

--CellSpecificCauseList-SyncAdjustmntFailureTDD-ExtIEs NBAP-PROTOCOL-EXTENSION ::= {
--	...
--}

--Unsuccessful-cell-InformationRespList-SyncAdjustmntFailureTDD ::= SEQUENCE (SIZE (1..maxCellinNodeB))	OF ProtocolIE-Single-Container {{ Unsuccessful-cell-InformationRespItemIE-SyncAdjustmntFailureTDD }}
Unsuccessful-cell-InformationRespList-SyncAdjustmntFailureTDD ::= SEQUENCE (SIZE (1..256))	OF ProtocolIE-Single-Container

--Unsuccessful-cell-InformationRespItemIE-SyncAdjustmntFailureTDD NBAP-PROTOCOL-IES ::= {
--	{ ID	id-Unsuccessful-cell-InformationRespItem-SyncAdjustmntFailureTDD		CRITICALITY		ignore		TYPE	Unsuccessful-cell-InformationRespItem-SyncAdjustmntFailureTDD		PRESENCE	mandatory},
--	...
--}

Unsuccessful-cell-InformationRespItem-SyncAdjustmntFailureTDD::= SEQUENCE {
	c-ID										C-ID,
	cause										Cause,
--	iE-Extensions								ProtocolExtensionContainer { { Unsuccessful-cell-InformationRespItem-SyncAdjustmntFailureTDD-ExtIEs} }		OPTIONAL,
	iE-Extensions								ProtocolExtensionContainer OPTIONAL,
	...
}

--Unsuccessful-cell-InformationRespItem-SyncAdjustmntFailureTDD-ExtIEs NBAP-PROTOCOL-EXTENSION ::= {
--	...
--}

-- **************************************************************
--
-- CELL SYNCHRONISATION TERMINATION REQUEST TDD
--
-- **************************************************************

--CellSynchronisationTerminationRequestTDD ::= SEQUENCE {
--	protocolIEs				ProtocolIE-Container	{{CellSynchronisationTerminationRequestTDD-IEs}},
--	protocolExtensions		ProtocolExtensionContainer	{{CellSynchronisationTerminationRequestTDD-Extensions}}     OPTIONAL,
--	...
--}
CellSynchronisationTerminationRequestTDD ::= SEQUENCE {
	protocolIEs				ProtocolIE-Container,
	protocolExtensions		ProtocolExtensionContainer	OPTIONAL,
	...
}
--CellSynchronisationTerminationRequestTDD-Extensions NBAP-PROTOCOL-EXTENSION ::= {
--	...
--}

--CellSynchronisationTerminationRequestTDD-IEs NBAP-PROTOCOL-IES ::= {
--	{ ID	id-C-ID							CRITICALITY		ignore		TYPE	C-ID							PRESENCE	mandatory	}|
--	{ ID	id-CSBTransmissionID			CRITICALITY		ignore		TYPE	CSBTransmissionID				PRESENCE	optional		}|
--	{ ID	id-CSBMeasurementID				CRITICALITY		ignore		TYPE	CSBMeasurementID				PRESENCE	optional		},
--	...
--}

-- **************************************************************
--
-- CELL SYNCHRONISATION FAILURE INDICATION TDD
--
-- **************************************************************

--CellSynchronisationFailureIndicationTDD ::= SEQUENCE {
--	protocolIEs				ProtocolIE-Container	{{CellSynchronisationFailureIndicationTDD-IEs}},
--	protocolExtensions		ProtocolExtensionContainer	{{CellSynchronisationFailureIndicationTDD-Extensions}}     OPTIONAL,
--	...
--}
CellSynchronisationFailureIndicationTDD ::= SEQUENCE {
	protocolIEs				ProtocolIE-Container,
	protocolExtensions		ProtocolExtensionContainer	OPTIONAL,
	...
}

--CellSynchronisationFailureIndicationTDD-Extensions NBAP-PROTOCOL-EXTENSION ::= {
--	...
--}

--CellSynchronisationFailureIndicationTDD-IEs NBAP-PROTOCOL-IES ::= {
--	{ ID	id-C-ID							CRITICALITY		ignore		TYPE	C-ID							PRESENCE	mandatory	}|
--	{ ID	id-CSBTransmissionID			CRITICALITY		ignore		TYPE	CSBTransmissionID				PRESENCE	optional		}|
--	{ ID	id-CSBMeasurementID				CRITICALITY		ignore		TYPE	CSBMeasurementID				PRESENCE	optional		}|
--	{ ID	id-Cause						CRITICALITY		ignore		TYPE	Cause							PRESENCE	mandatory	},
--	...
--}

-- **************************************************************
--
-- CELL SYNCHRONISATION REPORT TDD
--
-- **************************************************************
--CellSynchronisationReportTDD ::= SEQUENCE {
--	protocolIEs				ProtocolIE-Container	{{CellSynchronisationReportTDD-IEs}},
--	protocolExtensions		ProtocolExtensionContainer	{{CellSynchronisationReportTDD-Extensions}}     OPTIONAL,
--	...
--}
CellSynchronisationReportTDD ::= SEQUENCE {
	protocolIEs				ProtocolIE-Container,
	protocolExtensions		ProtocolExtensionContainer	OPTIONAL,
	...
}

--CellSynchronisationReportTDD-Extensions NBAP-PROTOCOL-EXTENSION ::= {
--	...
--}

--CellSynchronisationReportTDD-IEs NBAP-PROTOCOL-IES ::= {
--	{ ID	id-CellSyncInfo-CellSyncReprtTDD		CRITICALITY	ignore		TYPE	CellSyncInfo-CellSyncReprtTDD			PRESENCE	mandatory	},
--	...
--}


--CellSyncInfo-CellSyncReprtTDD ::= SEQUENCE (SIZE (1..maxCellinNodeB))	OF CellSyncInfoItemIE-CellSyncReprtTDD
CellSyncInfo-CellSyncReprtTDD ::= SEQUENCE (SIZE (1..256))	OF CellSyncInfoItemIE-CellSyncReprtTDD

CellSyncInfoItemIE-CellSyncReprtTDD ::= SEQUENCE {
	c-ID-CellSyncReprtTDD				C-ID-IE-CellSyncReprtTDD,
	syncReportType-CellSyncReprtTDD		SyncReportTypeIE-CellSyncReprtTDD		OPTIONAL,
	...
}

--C-ID-IE-CellSyncReprtTDD ::= ProtocolIE-Single-Container {{ C-ID-IEs-CellSyncReprtTDD }}
C-ID-IE-CellSyncReprtTDD ::= ProtocolIE-Single-Container

--C-ID-IEs-CellSyncReprtTDD NBAP-PROTOCOL-IES ::= {
--	{ ID	id-C-ID											CRITICALITY	ignore	TYPE C-ID													PRESENCE	mandatory}
--}

--SyncReportTypeIE-CellSyncReprtTDD::= ProtocolIE-Single-Container {{ SyncReportTypeIEs-CellSyncReprtTDD }}
SyncReportTypeIE-CellSyncReprtTDD::= ProtocolIE-Single-Container

--SyncReportTypeIEs-CellSyncReprtTDD NBAP-PROTOCOL-IES ::= {
--	{ ID	id-SyncReportType-CellSyncReprtTDD		CRITICALITY	ignore		TYPE SyncReportType-CellSyncReprtTDD		PRESENCE	mandatory}
--}


SyncReportType-CellSyncReprtTDD ::= CHOICE {
	intStdPhSyncInfo-CellSyncReprtTDD		IntStdPhCellSyncInfo-CellSyncReprtTDD,
	lateEntrantCell				NULL,
	frequencyAcquisition		NULL,
	...
}

IntStdPhCellSyncInfo-CellSyncReprtTDD ::= SEQUENCE {
	cellSyncBurstMeasuredInfo					CellSyncBurstMeasInfoList-CellSyncReprtTDD,
--	iE-Extensions								ProtocolExtensionContainer { { IntStdPhCellSyncInfoList-CellSyncReprtTDD-ExtIEs} }		OPTIONAL,
	iE-Extensions								ProtocolExtensionContainer OPTIONAL,
	...
}

--IntStdPhCellSyncInfoList-CellSyncReprtTDD-ExtIEs NBAP-PROTOCOL-EXTENSION ::= {
--	{ ID id-AccumulatedClockupdate-CellSyncReprtTDD		CRITICALITY	ignore	EXTENSION	TimingAdjustmentValue	PRESENCE	optional	}|
--	{ ID id-SyncDLCodeIdsMeasInfoList-CellSyncReprtTDD CRITICALITY	ignore EXTENSION	SyncDLCodeIdsMeasInfoList-CellSyncReprtTDD		PRESENCE optional },
 -- Mandatory for 1.28Mcps TDD. Not Applicable to 3.84Mcps TDD.
--	...
--}

--CellSyncBurstMeasInfoList-CellSyncReprtTDD ::= SEQUENCE (SIZE (0.. maxNrOfCellSyncBursts)) OF CellSyncBurstMeasInfoItem-CellSyncReprtTDD
 -- Mandatory for 3.84Mcps TDD. Not Applicable to 1.28Mcps TDD.
CellSyncBurstMeasInfoList-CellSyncReprtTDD ::= SEQUENCE (SIZE (0.. 10)) OF CellSyncBurstMeasInfoItem-CellSyncReprtTDD
 -- Mandatory for 3.84Mcps TDD. Not Applicable to 1.28Mcps TDD.

CellSyncBurstMeasInfoItem-CellSyncReprtTDD ::= SEQUENCE {
	sFN										SFN,
	cellSyncBurstInfo-CellSyncReprtTDD		SEQUENCE (SIZE (1..16)) OF CellSyncBurstInfo-CellSyncReprtTDD,
--	iE-Extensions							ProtocolExtensionContainer { { CellSyncBurstMeasInfoItem-CellSyncReprtTDD-ExtIEs} }		OPTIONAL,
	iE-Extensions							ProtocolExtensionContainer OPTIONAL,
	...
}

--CellSyncBurstMeasInfoItem-CellSyncReprtTDD-ExtIEs NBAP-PROTOCOL-EXTENSION ::= {
--	...
--}

CellSyncBurstInfo-CellSyncReprtTDD ::= CHOICE {
	cellSyncBurstAvailable		CellSyncBurstAvailable-CellSyncReprtTDD,
	cellSyncBurstNotAvailable	NULL,
	...
}

CellSyncBurstAvailable-CellSyncReprtTDD ::= SEQUENCE {
	cellSyncBurstTiming			CellSyncBurstTiming,
	cellSyncBurstSIR			CellSyncBurstSIR,
--	iE-Extensions				ProtocolExtensionContainer { { CellSyncBurstAvailable-CellSyncReprtTDD-ExtIEs} }		OPTIONAL,
	iE-Extensions				ProtocolExtensionContainer OPTIONAL,
	...
}

--CellSyncBurstAvailable-CellSyncReprtTDD-ExtIEs NBAP-PROTOCOL-EXTENSION ::= {
--	...
--}

--SyncDLCodeIdsMeasInfoList-CellSyncReprtTDD ::= SEQUENCE (SIZE (0..maxNrOfSyncFramesLCR)) OF SyncDLCodeIdsMeasInfoItem-CellSyncReprtTDD
SyncDLCodeIdsMeasInfoList-CellSyncReprtTDD ::= SEQUENCE (SIZE (0..512)) OF SyncDLCodeIdsMeasInfoItem-CellSyncReprtTDD
-- Mandatory for 1.28Mcps TDD. Not Applicable to 3.84Mcps TDD.

SyncDLCodeIdsMeasInfoItem-CellSyncReprtTDD ::= SEQUENCE {
	sFN										SFN,
	syncDLCodeIdInfo-CellSyncReprtTDD		SyncDLCodeIdInfo-CellSyncReprtTDD,
--	iE-Extensions							ProtocolExtensionContainer { { SyncDLCodeIdsMeasInfoItem-CellSyncReprtTDD-ExtIEs } }		OPTIONAL,
	iE-Extensions							ProtocolExtensionContainer OPTIONAL,
	...
}

--SyncDLCodeIdsMeasInfoItem-CellSyncReprtTDD-ExtIEs NBAP-PROTOCOL-EXTENSION ::= {
--	...
--}

--SyncDLCodeIdInfo-CellSyncReprtTDD ::= SEQUENCE (SIZE (1..maxNrOfReceptionsperSyncFrameLCR)) OF SyncDLCodeIdItem-CellSyncReprtTDD
SyncDLCodeIdInfo-CellSyncReprtTDD ::= SEQUENCE (SIZE (1..8)) OF SyncDLCodeIdItem-CellSyncReprtTDD

SyncDLCodeIdItem-CellSyncReprtTDD ::= CHOICE {
	syncDLCodeIdAvailable				SyncDLCodeIdAvailable-CellSyncReprtTDD,
	syncDLCodeIDNotAvailable			NULL,
	...
}

SyncDLCodeIdAvailable-CellSyncReprtTDD ::= SEQUENCE {
	syncDLCodeIdTiming			CellSyncBurstTimingLCR,
	syncDLCodeIdSIR				CellSyncBurstSIR,
--	iE-Extensions				ProtocolExtensionContainer { { SyncDLCodeIdAvailable-CellSyncReprtTDD-ExtIEs } }		OPTIONAL,
	iE-Extensions				ProtocolExtensionContainer OPTIONAL,
	...
}

--SyncDLCodeIdAvailable-CellSyncReprtTDD-ExtIEs NBAP-PROTOCOL-EXTENSION ::= {
--	...
--}

-- **************************************************************
--
-- BEARER REARRANGEMENT INDICATION
--
-- **************************************************************

--BearerRearrangementIndication ::= SEQUENCE {
--	protocolIEs                     ProtocolIE-Container       {{BearerRearrangementIndication-IEs}},
--	protocolExtensions              ProtocolExtensionContainer {{BearerRearrangementIndication-Extensions}}                   OPTIONAL,
--	...
--}
BearerRearrangementIndication ::= SEQUENCE {
	protocolIEs                     ProtocolIE-Container,
	protocolExtensions              ProtocolExtensionContainer OPTIONAL,
	...
}

--BearerRearrangementIndication-IEs NBAP-PROTOCOL-IES ::= {
--	{ ID id-CRNC-CommunicationContextID					CRITICALITY ignore	TYPE CRNC-CommunicationContextID				PRESENCE mandatory } |
--	{ ID id-SignallingBearerRequestIndicator			CRITICALITY ignore	TYPE SignallingBearerRequestIndicator				PRESENCE optional } |
--	{ ID id-DCH-RearrangeList-Bearer-RearrangeInd		CRITICALITY ignore	TYPE DCH-RearrangeList-Bearer-RearrangeInd			PRESENCE optional } |
--	{ ID id-DSCH-RearrangeList-Bearer-RearrangeInd		CRITICALITY ignore	TYPE DSCH-RearrangeList-Bearer-RearrangeInd		PRESENCE optional } |
	-- TDD only.
--	{ ID id-USCH-RearrangeList-Bearer-RearrangeInd		CRITICALITY ignore	TYPE USCH-RearrangeList-Bearer-RearrangeInd		PRESENCE optional } |
	-- TDD only.
--	{ ID id-HSDSCH-RearrangeList-Bearer-RearrangeInd	CRITICALITY ignore	TYPE HSDSCH-RearrangeList-Bearer-RearrangeInd		PRESENCE optional },
--	...
--}

--BearerRearrangementIndication-Extensions NBAP-PROTOCOL-EXTENSION ::= {
--	{ ID id-E-DCH-RearrangeList-Bearer-RearrangeInd		CRITICALITY ignore	EXTENSION E-DCH-RearrangeList-Bearer-RearrangeInd		PRESENCE optional },
--	...
--}

--DCH-RearrangeList-Bearer-RearrangeInd ::= SEQUENCE (SIZE (1..maxNrOfDCHs)) OF DCH-RearrangeItem-Bearer-RearrangeInd
DCH-RearrangeList-Bearer-RearrangeInd ::= SEQUENCE (SIZE (1..128)) OF DCH-RearrangeItem-Bearer-RearrangeInd

DCH-RearrangeItem-Bearer-RearrangeInd ::= SEQUENCE {
	dCH-ID											DCH-ID,
--	iE-Extensions									ProtocolExtensionContainer { { DCH-RearrangeItem-Bearer-RearrangeInd-ExtIEs} }		OPTIONAL,
	iE-Extensions									ProtocolExtensionContainer OPTIONAL,
	...
}

--DCH-RearrangeItem-Bearer-RearrangeInd-ExtIEs  NBAP-PROTOCOL-EXTENSION ::= {
--	...
--}

--DSCH-RearrangeList-Bearer-RearrangeInd ::= SEQUENCE (SIZE (1..maxNrOfDSCHs)) OF DSCH-RearrangeItem-Bearer-RearrangeInd
DSCH-RearrangeList-Bearer-RearrangeInd ::= SEQUENCE (SIZE (1..128)) OF DSCH-RearrangeItem-Bearer-RearrangeInd

DSCH-RearrangeItem-Bearer-RearrangeInd ::= SEQUENCE {
	dSCH-ID											DSCH-ID,
--	iE-Extensions									ProtocolExtensionContainer { { DSCH-RearrangeItem-Bearer-RearrangeInd-ExtIEs} }		OPTIONAL,
	iE-Extensions									ProtocolExtensionContainer OPTIONAL,
	...
}

--DSCH-RearrangeItem-Bearer-RearrangeInd-ExtIEs  NBAP-PROTOCOL-EXTENSION ::= {
--	...
--}

--USCH-RearrangeList-Bearer-RearrangeInd ::= SEQUENCE (SIZE (1..maxNrOfUSCHs)) OF USCH-RearrangeItem-Bearer-RearrangeInd
USCH-RearrangeList-Bearer-RearrangeInd ::= SEQUENCE (SIZE (1..32)) OF USCH-RearrangeItem-Bearer-RearrangeInd

USCH-RearrangeItem-Bearer-RearrangeInd ::= SEQUENCE {
	uSCH-ID											USCH-ID,
--	iE-Extensions									ProtocolExtensionContainer { { USCH-RearrangeItem-Bearer-RearrangeInd-ExtIEs} }		OPTIONAL,
	iE-Extensions									ProtocolExtensionContainer OPTIONAL,
	...
}

--USCH-RearrangeItem-Bearer-RearrangeInd-ExtIEs  NBAP-PROTOCOL-EXTENSION ::= {
--	...
--}

--HSDSCH-RearrangeList-Bearer-RearrangeInd ::= SEQUENCE (SIZE (1..maxNrOfMACdFlows)) OF HSDSCH-RearrangeItem-Bearer-RearrangeInd
HSDSCH-RearrangeList-Bearer-RearrangeInd ::= SEQUENCE (SIZE (1..8)) OF HSDSCH-RearrangeItem-Bearer-RearrangeInd

HSDSCH-RearrangeItem-Bearer-RearrangeInd ::= SEQUENCE {
	hsDSCH-MACdFlow-ID								HSDSCH-MACdFlow-ID,
--	iE-Extensions									ProtocolExtensionContainer { { HSDSCH-RearrangeItem-Bearer-RearrangeInd-ExtIEs} }		OPTIONAL,
	iE-Extensions									ProtocolExtensionContainer OPTIONAL,
	...
}

--HSDSCH-RearrangeItem-Bearer-RearrangeInd-ExtIEs  NBAP-PROTOCOL-EXTENSION ::= {
--	...
--}

--E-DCH-RearrangeList-Bearer-RearrangeInd ::= SEQUENCE (SIZE (1.. maxNrOfEDCHMACdFlows)) OF E-DCH-RearrangeItem-Bearer-RearrangeInd
E-DCH-RearrangeList-Bearer-RearrangeInd ::= SEQUENCE (SIZE (1.. 8)) OF E-DCH-RearrangeItem-Bearer-RearrangeInd

E-DCH-RearrangeItem-Bearer-RearrangeInd ::= SEQUENCE {
	e-DCH-MACdFlow-ID								E-DCH-MACdFlow-ID,
--	iE-Extensions									ProtocolExtensionContainer { { E-DCH-RearrangeItem-Bearer-RearrangeInd-ExtIEs} }		OPTIONAL,
	iE-Extensions									ProtocolExtensionContainer OPTIONAL,
	...
}

--E-DCH-RearrangeItem-Bearer-RearrangeInd-ExtIEs  NBAP-PROTOCOL-EXTENSION ::= {
--	...
--}

-- **************************************************************
--
-- RADIO LINK ACTIVATION COMMAND FDD
--
-- **************************************************************


--RadioLinkActivationCommandFDD ::= SEQUENCE {
--	protocolIEs				ProtocolIE-Container	{{RadioLinkActivationCommandFDD-IEs}},
--	protocolExtensions		ProtocolExtensionContainer	{{RadioLinkActivationCommandFDD-Extensions}}			OPTIONAL,
--	...
--}
RadioLinkActivationCommandFDD ::= SEQUENCE {
	protocolIEs				ProtocolIE-Container,
	protocolExtensions		ProtocolExtensionContainer	OPTIONAL,
	...
}
--RadioLinkActivationCommandFDD-IEs NBAP-PROTOCOL-IES ::= {
--	{ ID	id-NodeB-CommunicationContextID						CRITICALITY	ignore	TYPE	NodeB-CommunicationContextID								PRESENCE	mandatory	}|
--	{ ID	id-DelayedActivationList-RL-ActivationCmdFDD		CRITICALITY	ignore	TYPE	DelayedActivationInformationList-RL-ActivationCmdFDD			PRESENCE	mandatory	},
--	...
--}

--RadioLinkActivationCommandFDD-Extensions NBAP-PROTOCOL-EXTENSION ::= {
--	...
--}

--DelayedActivationInformationList-RL-ActivationCmdFDD ::= SEQUENCE (SIZE (1..maxNrOfRLs)) OF ProtocolIE-Single-Container { 
DelayedActivationInformationList-RL-ActivationCmdFDD ::= SEQUENCE (SIZE (1..16)) OF ProtocolIE-Single-Container

--DelayedActivationInformation-RL-ActivationCmdFDD-IEs NBAP-PROTOCOL-IES ::= {
--	{ ID id-DelayedActivationInformation-RL-ActivationCmdFDD	CRITICALITY ignore	TYPE DelayedActivationInformation-RL-ActivationCmdFDD	PRESENCE optional	}
--}

DelayedActivationInformation-RL-ActivationCmdFDD ::= SEQUENCE {
	rL-ID						RL-ID,
	delayed-activation-update	DelayedActivationUpdate,
--	iE-Extensions				ProtocolExtensionContainer { { DelayedActivationInformation-RL-ActivationCmdFDD-ExtIEs} } OPTIONAL,
	iE-Extensions				ProtocolExtensionContainer OPTIONAL,
	...
}

--DelayedActivationInformation-RL-ActivationCmdFDD-ExtIEs NBAP-PROTOCOL-EXTENSION ::= {
--	...
--}

-- **************************************************************
--
-- RADIO LINK ACTIVATION COMMAND TDD
--
-- **************************************************************

--RadioLinkActivationCommandTDD ::= SEQUENCE {
--	protocolIEs				ProtocolIE-Container	{{RadioLinkActivationCommandTDD-IEs}},
--	protocolExtensions		ProtocolExtensionContainer	{{RadioLinkActivationCommandTDD-Extensions}}			OPTIONAL,
--	...
--}
RadioLinkActivationCommandTDD ::= SEQUENCE {
	protocolIEs				ProtocolIE-Container,
	protocolExtensions		ProtocolExtensionContainer	OPTIONAL,
	...
}
--RadioLinkActivationCommandTDD-IEs NBAP-PROTOCOL-IES ::= {
--	{ ID	id-NodeB-CommunicationContextID						CRITICALITY	ignore	TYPE	NodeB-CommunicationContextID								PRESENCE	mandatory	}|
--	{ ID	id-DelayedActivationList-RL-ActivationCmdTDD		CRITICALITY	ignore	TYPE	DelayedActivationInformationList-RL-ActivationCmdTDD			PRESENCE	mandatory	},
--	...
--}

--RadioLinkActivationCommandTDD-Extensions NBAP-PROTOCOL-EXTENSION ::= {
--	...
--}

--DelayedActivationInformationList-RL-ActivationCmdTDD ::= SEQUENCE (SIZE (1..maxNrOfRLs)) OF ProtocolIE-Single-Container { 
DelayedActivationInformationList-RL-ActivationCmdTDD ::= SEQUENCE (SIZE (1..16)) OF ProtocolIE-Single-Container 

--DelayedActivationInformation-RL-ActivationCmdTDD-IEs NBAP-PROTOCOL-IES ::= {
--	{ ID id-DelayedActivationInformation-RL-ActivationCmdTDD	CRITICALITY ignore	TYPE DelayedActivationInformation-RL-ActivationCmdTDD	PRESENCE optional	}
--}

DelayedActivationInformation-RL-ActivationCmdTDD ::= SEQUENCE {
	rL-ID						RL-ID,
	delayed-activation-update	DelayedActivationUpdate,
--	iE-Extensions				ProtocolExtensionContainer { { DelayedActivationInformation-RL-ActivationCmdTDD-ExtIEs} } OPTIONAL,
	iE-Extensions				ProtocolExtensionContainer OPTIONAL,
	...
}

--DelayedActivationInformation-RL-ActivationCmdTDD-ExtIEs NBAP-PROTOCOL-EXTENSION ::= {
--	...
--}

-- **************************************************************
--
-- RADIO LINK PARAMETER UPDATE INDICATION FDD
--
-- **************************************************************

--RadioLinkParameterUpdateIndicationFDD ::= SEQUENCE {
--	protocolIEs				ProtocolIE-Container	{{RadioLinkParameterUpdateIndicationFDD-IEs}},
--	protocolExtensions		ProtocolExtensionContainer	{{RadioLinkParameterUpdateIndicationFDD-Extensions}}		OPTIONAL,
--	...
--}
RadioLinkParameterUpdateIndicationFDD ::= SEQUENCE {
	protocolIEs				ProtocolIE-Container,
	protocolExtensions		ProtocolExtensionContainer OPTIONAL,
	...
}

--RadioLinkParameterUpdateIndicationFDD-IEs NBAP-PROTOCOL-IES ::= {
--	{ ID id-CRNC-CommunicationContextID			CRITICALITY		ignore		TYPE	CRNC-CommunicationContextID			PRESENCE	mandatory	} |
--	{ ID id-HSDSCH-FDD-Update-Information		CRITICALITY		ignore		TYPE	HSDSCH-FDD-Update-Information			PRESENCE	optional	},
--	...
--}

--RadioLinkParameterUpdateIndicationFDD-Extensions NBAP-PROTOCOL-EXTENSION ::= {
--	...
--}

-- **************************************************************
--
-- RADIO LINK PARAMETER UPDATE INDICATION TDD
--
-- **************************************************************

--RadioLinkParameterUpdateIndicationTDD ::= SEQUENCE {
--	protocolIEs				ProtocolIE-Container	{{RadioLinkParameterUpdateIndicationTDD-IEs}},
--	protocolExtensions		ProtocolExtensionContainer	{{RadioLinkParameterUpdateIndicationTDD-Extensions}}		OPTIONAL,
--	...
--}
RadioLinkParameterUpdateIndicationTDD ::= SEQUENCE {
	protocolIEs				ProtocolIE-Container,
	protocolExtensions		ProtocolExtensionContainer	OPTIONAL,
	...
}

--RadioLinkParameterUpdateIndicationTDD-IEs NBAP-PROTOCOL-IES ::= {
--	{ ID id-CRNC-CommunicationContextID			CRITICALITY		ignore		TYPE	CRNC-CommunicationContextID			PRESENCE	mandatory	} |
--	{ ID id-HSDSCH-TDD-Update-Information		CRITICALITY		ignore		TYPE	HSDSCH-TDD-Update-Information			PRESENCE	optional	},
--	...
--}

--RadioLinkParameterUpdateIndicationTDD-Extensions NBAP-PROTOCOL-EXTENSION ::= {
--	...
--}

-- **************************************************************
--
-- MBMS NOTIFICATION UPDATE COMMAND
--
-- **************************************************************

--MBMSNotificationUpdateCommand ::= SEQUENCE {
--	protocolIEs				ProtocolIE-Container	{{ MBMSNotificationUpdateCommand-IEs}},
--	protocolExtensions		ProtocolExtensionContainer	{{ MBMSNotificationUpdateCommand-Extensions}}		OPTIONAL,
--	...
--}
MBMSNotificationUpdateCommand ::= SEQUENCE {
	protocolIEs				ProtocolIE-Container,
	protocolExtensions		ProtocolExtensionContainer	OPTIONAL,
	...
}
--MBMSNotificationUpdateCommand-IEs NBAP-PROTOCOL-IES ::= {
--	{ ID id-C-ID								CRITICALITY ignore	TYPE C-ID								PRESENCE mandatory	}|
--	{ ID id-CommonPhysicalChannelID				CRITICALITY ignore	TYPE CommonPhysicalChannelID			PRESENCE mandatory	}|
--	{ ID id-Modification-Period					CRITICALITY ignore	TYPE Modification-Period				PRESENCE optional		}|
--	{ ID id-MICH-CFN							CRITICALITY ignore	TYPE MICH-CFN							PRESENCE mandatory	}|
--	{ ID id-NI-Information-NotifUpdateCmd		CRITICALITY ignore	TYPE NI-Information						PRESENCE mandatory	},
--	...
--}

--MBMSNotificationUpdateCommand-Extensions NBAP-PROTOCOL-EXTENSION ::= {
--	...
--}

--END

-- **************************************************************
--
-- COMMON MEASUREMENT REPORT
--
-- **************************************************************

--CommonMeasurementReport ::= SEQUENCE {
--	protocolIEs				ProtocolIE-Container	{{CommonMeasurementReport-IEs}},
--	protocolExtensions		ProtocolExtensionContainer	{{CommonMeasurementReport-Extensions}}		OPTIONAL,
--	...
--}

CommonMeasurementReport ::= SEQUENCE {
	protocolIEs				ProtocolIE-Container,
	protocolExtensions		ProtocolExtensionContainer OPTIONAL,
	...
}

--CommonMeasurementReport-IEs NBAP-PROTOCOL-IES ::= {
--	{ ID id-MeasurementID							CRITICALITY ignore		TYPE MeasurementID				PRESENCE	mandatory	}|
--	{ ID id-CommonMeasurementObjectType-CM-Rprt		CRITICALITY ignore		TYPE CommonMeasurementObjectType-CM-Rprt		PRESENCE	mandatory	}|
--	{ ID id-SFN										CRITICALITY ignore		TYPE SFN						PRESENCE	optional	},
--	...
--}

--CommonMeasurementReport-Extensions NBAP-PROTOCOL-EXTENSION ::= {
--	{ ID	id-MeasurementRecoveryReportingIndicator		CRITICALITY ignore		EXTENSION	MeasurementRecoveryReportingIndicator		PRESENCE optional },
--	...
--}

CommonMeasurementObjectType-CM-Rprt ::= CHOICE {
	cell							Cell-CM-Rprt,
	rACH							RACH-CM-Rprt,
	notUsed-cPCH					NULL,
	...,
	extension-CommonMeasurementObjectType-CM-Rprt		Extension-CommonMeasurementObjectType-CM-Rprt
}

--Extension-CommonMeasurementObjectType-CM-Rprt	::= ProtocolIE-Single-Container {{ Extension-CommonMeasurementObjectType-CM-RprtIE }}
Extension-CommonMeasurementObjectType-CM-Rprt	::= ProtocolIE-Single-Container 

--Extension-CommonMeasurementObjectType-CM-RprtIE NBAP-PROTOCOL-IES ::= {
--	{ ID id-Power-Local-Cell-Group-choice-CM-Rprt	CRITICALITY ignore		TYPE PowerLocalCellGroup-CM-Rprt	PRESENCE mandatory }
--}

Cell-CM-Rprt ::= SEQUENCE {
	commonMeasurementValueInformation	CommonMeasurementValueInformation,
--	iE-Extensions					ProtocolExtensionContainer  {{ CellItem-CM-Rprt-ExtIEs }}		OPTIONAL,
	iE-Extensions					ProtocolExtensionContainer  OPTIONAL,
	...

}

--CellItem-CM-Rprt-ExtIEs NBAP-PROTOCOL-EXTENSION ::= {
--	...
--}


RACH-CM-Rprt ::= SEQUENCE {
	commonMeasurementValueInformation	CommonMeasurementValueInformation,
--	iE-Extensions					ProtocolExtensionContainer {{ RACHItem-CM-Rprt-ExtIEs }}			OPTIONAL,
	iE-Extensions					ProtocolExtensionContainer OPTIONAL,
	...
}

--RACHItem-CM-Rprt-ExtIEs NBAP-PROTOCOL-EXTENSION ::= {
--	...
--}

PowerLocalCellGroup-CM-Rprt ::= SEQUENCE {
	commonMeasurementValueInformation	CommonMeasurementValueInformation,
--	iE-Extensions						ProtocolExtensionContainer {{ PowerLocalCellGroup-CM-Rprt-ExtIEs}}	OPTIONAL,
	iE-Extensions						ProtocolExtensionContainer OPTIONAL,
	...
}

--PowerLocalCellGroup-CM-Rprt-ExtIEs NBAP-PROTOCOL-EXTENSION ::= {
--	...
--}

-- **************************************************************
--
-- COMMON MEASUREMENT TERMINATION REQUEST
--
-- **************************************************************

--CommonMeasurementTerminationRequest ::= SEQUENCE {
--	protocolIEs				ProtocolIE-Container	{{CommonMeasurementTerminationRequest-IEs}},
--	protocolExtensions		ProtocolExtensionContainer	{{CommonMeasurementTerminationRequest-Extensions}}		OPTIONAL,
--	...
--}

CommonMeasurementTerminationRequest ::= SEQUENCE {
	protocolIEs				ProtocolIE-Container,
	protocolExtensions		ProtocolExtensionContainer OPTIONAL,
	...
}

--CommonMeasurementTerminationRequest-IEs NBAP-PROTOCOL-IES ::= {
--	{ ID	id-MeasurementID			CRITICALITY		ignore				TYPE	MeasurementID			PRESENCE	mandatory},
--	...
--}

--CommonMeasurementTerminationRequest-Extensions NBAP-PROTOCOL-EXTENSION ::= {
--	...
--}
-- **************************************************************
--
-- COMMON MEASUREMENT FAILURE INDICATION
--
-- **************************************************************

--CommonMeasurementFailureIndication ::= SEQUENCE {
--	protocolIEs				ProtocolIE-Container	{{CommonMeasurementFailureIndication-IEs}},
--	protocolExtensions			ProtocolExtensionContainer	{{CommonMeasurementFailureIndication-Extensions}}				OPTIONAL,
--	...
--}
CommonMeasurementFailureIndication ::= SEQUENCE {
	protocolIEs				ProtocolIE-Container,
	protocolExtensions			ProtocolExtensionContainer OPTIONAL,
	...
}
--CommonMeasurementFailureIndication-IEs NBAP-PROTOCOL-IES ::= {
--	{ ID	id-MeasurementID			CRITICALITY	ignore			TYPE	MeasurementID			PRESENCE	mandatory	}|
--	{ ID	id-Cause					CRITICALITY	ignore			TYPE	Cause					PRESENCE	mandatory	},
--	...
--}

--CommonMeasurementFailureIndication-Extensions NBAP-PROTOCOL-EXTENSION ::= {
--	...
--}

-- **************************************************************
--
-- CELL SETUP REQUEST FDD
--
-- **************************************************************


--9.3.4	Information Elements Definitions
--******************************************************************************
--
-- Information Element Definitions
--
--******************************************************************************

--NBAP-IEs {
--itu-t (0) identified-organization (4) etsi (0) mobileDomain (0) 
--umts-Access (20) modules (3) nbap (2) version1 (1) nbap-IEs (2) }

--DEFINITIONS AUTOMATIC TAGS ::=
--BEGIN

--IMPORTS
--	maxNrOfRLs,
--	maxNrOfTFCs,
--	maxNrOfErrors,
--	maxCTFC,
--	maxNrOfTFs,
--	maxTTI-count,
--	maxRateMatching,
--	maxHS-PDSCHCodeNrComp-1,
--	maxHS-SCCHCodeNrComp-1,
--	maxNrOfCellSyncBursts,
--	maxNrOfEDCH-HARQ-PO-QUANTSTEPs,
--	maxNrOfEDCHHARQProcesses2msEDCH,
--	maxNrOfBits-MACe-PDU-non-scheduled,
--	8,
--	maxNrOfRefETFCI-PO-QUANTSTEPs,
--	maxNrOfRefETFCIs,
--	maxNrOfMeasNCell,
--	maxNrOfMeasNCell-1,
--	maxNrOfReceptsPerSyncFrame,
--	8,
--	6,
--	maxNrOfUSCHs,
--	maxNrOfULTSs,
--	maxNrOfULTSLCRs,
--	maxNrOfDPCHs,
--	maxNrOfDPCHLCRs,
--	maxNrOfCodes,
--	maxNrOfDSCHs,
--	15,
--	6,
--	128,
--	maxNrOfLevels,
--	maxNoGPSItems,
--	maxNoSat,
--	64,
--	64-1,
--	maxNrOfHSSCCHs,
--	maxNrOfHSSCCHCodes,
--	maxNrOfMACdFlows,
--	maxNrOfMACdFlows-1,
--	maxNrOfMACdPDUIndexes,
--	maxNrOfMACdPDUIndexes-1,
--	maxNrOfNIs,
--	maxNrOfPriorityQueues,
--	maxNrOfPriorityQueues-1,
--	8,
--	maxNrOfSyncDLCodesLCR,
--	maxNrOfSyncFramesLCR,
--	maxNrOfContextsOnUeList,
--	16,
--	maxNrOfSatAlmanac-maxNoSat,
--	64,
--	maxNrOfE-AGCHs,
--	8,
--	8-1,
--	maxNrOfE-RGCHs-E-HICHs,
--	maxNrofSigSeqRGHI-1,
--	16,



--	id-MessageStructure,
--	id-ReportCharacteristicsType-OnModification,
--	id-Rx-Timing-Deviation-Value-LCR,
--	id-SFNSFNMeasurementValueInformation,
--	id-SFNSFNMeasurementThresholdInformation,
--	id-TUTRANGPSMeasurementValueInformation,
--	id-TUTRANGPSMeasurementThresholdInformation,
--	id-TypeOfError,
--	id-transportlayeraddress,
--	id-bindingID,
--	id-Angle-Of-Arrival-Value-LCR,
--	id-SyncDLCodeIdThreInfoLCR,
--	id-neighbouringTDDCellMeasurementInformationLCR,
--	id-HS-SICH-Reception-Quality,
--	id-HS-SICH-Reception-Quality-Measurement-Value,
--	id-Initial-DL-Power-TimeslotLCR-InformationItem,
--	id-Maximum-DL-Power-TimeslotLCR-InformationItem,
--	id-Minimum-DL-Power-TimeslotLCR-InformationItem,
--	id-Received-total-wide-band-power-For-CellPortion,
--	id-Received-total-wide-band-power-For-CellPortion-Value,
--	id-Transmitted-Carrier-Power-For-CellPortion,
--	id-Transmitted-Carrier-Power-For-CellPortion-Value,
--	id-TransmittedCarrierPowerOfAllCodesNotUsedForHSTransmission,
--	id-TransmittedCarrierPowerOfAllCodesNotUsedForHS-PDSCH-HS-SCCH-E-AGCH-E-RGCHOrE-HICHTransmissionCellPortion,
--	id-TransmittedCarrierPowerOfAllCodesNotUsedForHS-PDSCH-HS-SCCH-E-AGCH-E-RGCHOrE-HICHTransmissionCellPortionValue,
--	id-HS-DSCHRequiredPowerValueInformation,
--	id-HS-DSCHProvidedBitRateValueInformation,
--	id-HS-DSCHRequiredPowerValue,
--	id-HS-DSCHRequiredPowerValue-For-Cell-Portion,
--	id-HS-DSCHRequiredPowerValueInformation-For-CellPortion,
--	id-HS-DSCHProvidedBitRateValueInformation-For-CellPortion,
--	id-Best-Cell-Portions-Value,
--	id-Unidirectional-DCH-Indicator,
--	id-SAT-Info-Almanac-ExtItem,
--	id-TnlQos,
--	id-UpPTSInterferenceValue,
--	id-HARQ-Preamble-Mode,
--	id-HARQ-Preamble-Mode-Activation-Indicator,
--	id-DLTransmissionBranchLoadValue,
--	id-E-DCHProvidedBitRateValueInformation
--FROM NBAP-Constants
--
--	Criticality,
--	ProcedureID,
--	ProtocolIE-ID,
--	TransactionID,
--	TriggeringMessage
--FROM NBAP-CommonDataTypes

--	NBAP-PROTOCOL-IES,
---	ProtocolExtensionContainer{},
--	ProtocolIE-Single-Container{},
--	NBAP-PROTOCOL-EXTENSION		
--FROM NBAP-Containers;

-- ==========================================
--	A
-- ==========================================

AckNack-RepetitionFactor ::= INTEGER (1..4,...)
-- Step: 1

Ack-Power-Offset ::= INTEGER (0..8,...)
-- According to mapping in ref. [9] subclause 4.2.1

Acknowledged-PRACH-preambles-Value ::= INTEGER(0..240,...)
-- According to mapping in [22].

AddorDeleteIndicator ::= ENUMERATED {
	add,
	delete
}

Active-Pattern-Sequence-Information ::= SEQUENCE {
	cMConfigurationChangeCFN								CFN,
	transmission-Gap-Pattern-Sequence-Status	Transmission-Gap-Pattern-Sequence-Status-List	OPTIONAL,
--	iE-Extensions								ProtocolExtensionContainer { {Active-Pattern-Sequence-Information-ExtIEs} } OPTIONAL,
	iE-Extensions								ProtocolExtensionContainer OPTIONAL,
	...
}

--Active-Pattern-Sequence-Information-ExtIEs NBAP-PROTOCOL-EXTENSION ::= {
--	...
--}

Transmission-Gap-Pattern-Sequence-Status-List ::= SEQUENCE (SIZE (0..6)) OF
	SEQUENCE {
		tGPSID			TGPSID,
		tGPRC			TGPRC,
		tGCFN			CFN,
--		iE-Extensions		ProtocolExtensionContainer { { Transmission-Gap-Pattern-Sequence-Status-List-ExtIEs } } OPTIONAL,
		iE-Extensions		ProtocolExtensionContainer OPTIONAL,
		...
}

--Transmission-Gap-Pattern-Sequence-Status-List-ExtIEs NBAP-PROTOCOL-EXTENSION ::= {
--	...
--}

AICH-Power ::= INTEGER (-22..5)
-- Offset in dB.

AICH-TransmissionTiming ::= ENUMERATED {
	v0,
	v1
}

AllocationRetentionPriority ::= SEQUENCE {
	priorityLevel				PriorityLevel,
	pre-emptionCapability		Pre-emptionCapability,
	pre-emptionVulnerability	Pre-emptionVulnerability,
--	iE-Extensions				ProtocolExtensionContainer { {AllocationRetentionPriority-ExtIEs} } OPTIONAL,
	iE-Extensions				ProtocolExtensionContainer OPTIONAL,
	...
}

--AllocationRetentionPriority-ExtIEs NBAP-PROTOCOL-EXTENSION ::= {
--	...
--}

Angle-Of-Arrival-Value-LCR ::= SEQUENCE {
	aOA-LCR						AOA-LCR,
	aOA-LCR-Accuracy-Class		AOA-LCR-Accuracy-Class,
--	iE-Extensions				ProtocolExtensionContainer { {Angle-Of-Arrival-Value-LCR-ExtIEs} } OPTIONAL,
	iE-Extensions				ProtocolExtensionContainer OPTIONAL,
...
}

--Angle-Of-Arrival-Value-LCR-ExtIEs NBAP-PROTOCOL-EXTENSION ::= {
--	...
--}

AOA-LCR ::= INTEGER (0..719)
-- Angle Of Arrival for 1.28Mcps TDD

AOA-LCR-Accuracy-Class	::= ENUMERATED {a,b,c,d,e,f,g,h,...}

AvailabilityStatus ::= ENUMERATED {
	empty,
	in-test,
	failed,
	power-off,
	off-line,
	off-duty,
	dependency,
	degraded,
	not-installed,
	log-full,
	...
}

-- ==========================================
--	B
-- ==========================================
BCCH-ModificationTime ::= INTEGER  (0..511)
-- Time = BCCH-ModificationTime * 8
-- Range 0 to 4088, step 8
-- All SFN values in which MIB may be mapped are allowed

Best-Cell-Portions-Value::= SEQUENCE (SIZE (1..64)) OF Best-Cell-Portions-Item

Best-Cell-Portions-Item ::= SEQUENCE {
	cellPortionID				CellPortionID,
	sIRValue					SIR-Value,
--	iE-Extensions				ProtocolExtensionContainer { { Best-Cell-Portions-Item-ExtIEs} }	OPTIONAL,
	iE-Extensions				ProtocolExtensionContainer OPTIONAL,
	...
}

--Best-Cell-Portions-Item-ExtIEs NBAP-PROTOCOL-EXTENSION ::= {
--	...
--}

BindingID ::= OCTET STRING (SIZE (1..4, ...))
-- If the Binding ID includes a UDP port, the UDP port is included in octet 1 and 2.The first octet of
-- the UDP port field is included in the first octet of the Binding ID.

BetaCD ::= INTEGER (0..15)

BlockingPriorityIndicator ::= ENUMERATED {
	high,
	normal,
	low,
	...
}
-- High priority: Block resource immediately.
-- Normal priority: Block resource when idle or upon timer expiry.
-- Low priority: Block resource when idle.

SCTD-Indicator ::= ENUMERATED {
	active,
	inactive
}

BundlingModeIndicator ::= ENUMERATED {
	bundling,
	no-bundling
}

-- ==========================================
--	C
-- ==========================================

Cause ::= CHOICE {
	radioNetwork			CauseRadioNetwork,
	transport			CauseTransport,
	protocol				CauseProtocol,
	misc					CauseMisc,
	...
}

CauseMisc ::= ENUMERATED {
	control-processing-overload,
	hardware-failure,
	oam-intervention,
	not-enough-user-plane-processing-resources,
	unspecified,
	...
}

CauseProtocol ::= ENUMERATED {
	transfer-syntax-error,
	abstract-syntax-error-reject,
	abstract-syntax-error-ignore-and-notify,
	message-not-compatible-with-receiver-state,
	semantic-error,
	unspecified,
	abstract-syntax-error-falsely-constructed-message,
	...
}

CauseRadioNetwork ::= ENUMERATED {
	unknown-C-ID,
	cell-not-available,
	power-level-not-supported, 
	dl-radio-resources-not-available,
	ul-radio-resources-not-available,
	rl-already-ActivatedOrAllocated,
	nodeB-Resources-unavailable,
	measurement-not-supported-for-the-object,
	combining-resources-not-available,
	requested-configuration-not-supported,
	synchronisation-failure,
	priority-transport-channel-established,
	sIB-Origination-in-Node-B-not-Supported,
	requested-tx-diversity-mode-not-supported,
	unspecified,
	bCCH-scheduling-error,
	measurement-temporarily-not-available,
	invalid-CM-settings,
	reconfiguration-CFN-not-elapsed,
	number-of-DL-codes-not-supported,
	s-cipch-not-supported,
	combining-not-supported,
	ul-sf-not-supported,
	dl-SF-not-supported, 
	common-transport-channel-type-not-supported,
	dedicated-transport-channel-type-not-supported,
	downlink-shared-channel-type-not-supported,
	uplink-shared-channel-type-not-supported,
	cm-not-supported,
	tx-diversity-no-longer-supported,
	unknown-Local-Cell-ID,
	...,
    number-of-UL-codes-not-supported,
    information-temporarily-not-available,
    information-provision-not-supported-for-the-object,
	cell-synchronisation-not-supported,
	cell-synchronisation-adjustment-not-supported,
	dpc-mode-change-not-supported,
	iPDL-already-activated,
	iPDL-not-supported,
	iPDL-parameters-not-available,
	frequency-acquisition-not-supported,
	power-balancing-status-not-compatible,
	requested-typeofbearer-re-arrangement-not-supported,
	signalling-Bearer-Re-arrangement-not-supported,
	bearer-Re-arrangement-needed,
	delayed-activation-not-supported,
	rl-timing-adjustment-not-supported,
	mich-not-supported,
	f-DPCH-not-supported
}

CauseTransport ::= ENUMERATED {
	transport-resource-unavailable,
	unspecified,
	...
}

CCTrCH-ID ::= INTEGER (0..15)

CellParameterID ::= INTEGER (0..127,...)

CellPortionID	::= INTEGER (0..63,...)

CellSyncBurstCode ::= INTEGER(0..7, ...)

CellSyncBurstCodeShift ::= INTEGER(0..7)

CellSyncBurstRepetitionPeriod ::= INTEGER (0..4095)

CellSyncBurstSIR ::= INTEGER (0..31)

CellSyncBurstTiming ::= CHOICE {
	initialPhase			INTEGER (0..1048575,...),
	steadyStatePhase		INTEGER (0..255,...)
}

CellSyncBurstTimingLCR ::= CHOICE {
	initialPhase			INTEGER (0..524287,...),
	steadyStatePhase		INTEGER (0..127,...)
}

CellSyncBurstTimingThreshold ::= INTEGER(0..254)

CFN ::= INTEGER (0..255)

ChipOffset ::= INTEGER (0..38399)
-- Unit Chip

C-ID ::= INTEGER (0..65535)

Closedlooptimingadjustmentmode	::= ENUMERATED {
	adj-1-slot,
	adj-2-slot,
	...
}

CommonChannelsCapacityConsumptionLaw ::= SEQUENCE (SIZE(1..8)) OF
	SEQUENCE {
		dl-Cost		INTEGER (0..65535),
		ul-Cost		INTEGER (0..65535),
--		iE-Extensions		ProtocolExtensionContainer { { CommonChannelsCapacityConsumptionLaw-ExtIEs } }		OPTIONAL,
		iE-Extensions		ProtocolExtensionContainer OPTIONAL,
		...
}

--CommonChannelsCapacityConsumptionLaw-ExtIEs NBAP-PROTOCOL-EXTENSION ::= {
--	...
--}

CommonMeasurementAccuracy ::= CHOICE {
	tUTRANGPSMeasurementAccuracyClass		TUTRANGPSAccuracyClass,
	...
}

CommonMeasurementType ::= ENUMERATED  {
	received-total-wide-band-power,
	transmitted-carrier-power,
	acknowledged-prach-preambles,
	ul-timeslot-iscp,
	notUsed-1-acknowledged-PCPCH-access-preambles,
	notUsed-2-detected-PCPCH-access-preambles,
	...,
	uTRAN-GPS-Timing-of-Cell-Frames-for-UE-Positioning, 
	sFN-SFN-Observed-Time-Difference,
	transmittedCarrierPowerOfAllCodesNotUsedForHSTransmission,
	hS-DSCH-Required-Power,
	hS-DSCH-Provided-Bit-Rate,
	received-total-wide-band-power-for-cellPortion,
	transmitted-carrier-power-for-cellPortion,
	transmittedCarrierPowerOfAllCodesNotUsedForHS-PDSCH-HS-SCCH-E-AGCH-E-RGCHOrE-HICHTransmission-for-cellPortion,
	upPTS-Interference,
	dLTransmissionBranchLoad,
	hS-DSCH-Required-Power-for-cell-portion,
	hS-DSCH-Provided-Bit-Rate-for-cell-portion,
	e-DCH-Provided-Bit-Rate
}

CommonMeasurementValue ::= CHOICE {
	transmitted-carrier-power							Transmitted-Carrier-Power-Value,
	received-total-wide-band-power						Received-total-wide-band-power-Value,
	acknowledged-prach-preambles						Acknowledged-PRACH-preambles-Value,
	uL-TimeslotISCP										UL-TimeslotISCP-Value,
	notUsed-1-acknowledged-PCPCH-access-preambles		NULL,
	notUsed-2-detected-PCPCH-access-preambles			NULL,
	...,
	extension-CommonMeasurementValue		Extension-CommonMeasurementValue
}

--Extension-CommonMeasurementValue	::= ProtocolIE-Single-Container {{ Extension-CommonMeasurementValueIE }}
Extension-CommonMeasurementValue	::= ProtocolIE-Single-Container

--Extension-CommonMeasurementValueIE NBAP-PROTOCOL-IES ::= {
--	{ ID id-TUTRANGPSMeasurementValueInformation			CRITICALITY ignore	TYPE TUTRANGPSMeasurementValueInformation		PRESENCE mandatory }|
--	{ ID id-SFNSFNMeasurementValueInformation				CRITICALITY ignore	TYPE SFNSFNMeasurementValueInformation			PRESENCE mandatory }|
--	{ ID id-TransmittedCarrierPowerOfAllCodesNotUsedForHSTransmission	CRITICALITY ignore	TYPE TransmittedCarrierPowerOfAllCodesNotUsedForHSTransmissionValue		PRESENCE mandatory }|
--	{ ID id-HS-DSCHRequiredPowerValueInformation			CRITICALITY ignore	TYPE HS-DSCHRequiredPower							PRESENCE mandatory }|
--	{ ID id-HS-DSCHProvidedBitRateValueInformation			CRITICALITY ignore	TYPE HS-DSCHProvidedBitRate						PRESENCE mandatory }|
--	{ ID id-Transmitted-Carrier-Power-For-CellPortion-Value	CRITICALITY ignore	TYPE Transmitted-Carrier-Power-For-CellPortion-Value	PRESENCE mandatory }|
--	{ ID id-Received-total-wide-band-power-For-CellPortion-Value	CRITICALITY ignore	TYPE Received-total-wide-band-power-For-CellPortion-Value	PRESENCE mandatory }|
--	{ ID id-TransmittedCarrierPowerOfAllCodesNotUsedForHS-PDSCH-HS-SCCH-E-AGCH-E-RGCHOrE-HICHTransmissionCellPortionValue	CRITICALITY ignore	TYPE TransmittedCarrierPowerOfAllCodesNotUsedForHS-PDSCH-HS-SCCH-E-AGCH-E-RGCHOrE-HICHTransmissionCellPortionValue		PRESENCE mandatory }|
--	{ ID id-UpPTSInterferenceValue									CRITICALITY ignore	TYPE UpPTSInterferenceValue									PRESENCE mandatory }|
--	{ ID id-DLTransmissionBranchLoadValue							CRITICALITY ignore	TYPE DLTransmissionBranchLoadValue							PRESENCE mandatory }|
--	{ ID id-HS-DSCHRequiredPowerValueInformation-For-CellPortion	CRITICALITY ignore	TYPE HS-DSCHRequiredPowerValueInformation-For-CellPortion	PRESENCE mandatory }|
--	{ ID id-HS-DSCHProvidedBitRateValueInformation-For-CellPortion	CRITICALITY ignore	TYPE HS-DSCHProvidedBitRateValueInformation-For-CellPortion	PRESENCE mandatory }|
--	{ ID id-E-DCHProvidedBitRateValueInformation			CRITICALITY ignore	TYPE E-DCHProvidedBitRate						PRESENCE mandatory }
--}

CommonMeasurementValueInformation ::= CHOICE {
	measurementAvailable		CommonMeasurementAvailable,
	measurementnotAvailable		CommonMeasurementnotAvailable
}

CommonMeasurementAvailable::= SEQUENCE {
	commonmeasurementValue		CommonMeasurementValue,
--	ie-Extensions					ProtocolExtensionContainer { { CommonMeasurementAvailableItem-ExtIEs} }		OPTIONAL,
	ie-Extensions					ProtocolExtensionContainer OPTIONAL,
	...
}

--CommonMeasurementAvailableItem-ExtIEs NBAP-PROTOCOL-EXTENSION ::= {
--	...
--}
CommonMeasurementnotAvailable ::= NULL

CommonPhysicalChannelID ::= INTEGER (0..255)

Common-PhysicalChannel-Status-Information ::= SEQUENCE {
	commonPhysicalChannelID			CommonPhysicalChannelID,
	resourceOperationalState			ResourceOperationalState,
	availabilityStatus					AvailabilityStatus,
--	iE-Extensions						ProtocolExtensionContainer  { { Common-PhysicalChannel-Status-Information-ExtIEs} }		OPTIONAL,
	iE-Extensions						ProtocolExtensionContainer OPTIONAL,
	...
}

--Common-PhysicalChannel-Status-Information-ExtIEs NBAP-PROTOCOL-EXTENSION ::= {
--	...
--}

CommonTransportChannelID ::= INTEGER (0..255)

CommonTransportChannel-InformationResponse ::= SEQUENCE {
	commonTransportChannelID			CommonTransportChannelID,
	bindingID							BindingID				OPTIONAL,
	transportLayerAddress				TransportLayerAddress	OPTIONAL,
--	iE-Extensions						ProtocolExtensionContainer  { { CommonTransportChannel-InformationResponse-ExtIEs} }		OPTIONAL,
	iE-Extensions						ProtocolExtensionContainer OPTIONAL,
	...
}

--CommonTransportChannel-InformationResponse-ExtIEs NBAP-PROTOCOL-EXTENSION ::= {
--	...
--}

Common-TransportChannel-Status-Information ::= SEQUENCE {
	commonTransportChannelID			CommonTransportChannelID,
	resourceOperationalState			ResourceOperationalState,
	availabilityStatus					AvailabilityStatus,
--	iE-Extensions						ProtocolExtensionContainer  { { Common-TransportChannel-Status-Information-ExtIEs} }		OPTIONAL,
	iE-Extensions						ProtocolExtensionContainer OPTIONAL,
	...
}

--Common-TransportChannel-Status-Information-ExtIEs NBAP-PROTOCOL-EXTENSION ::= {
--	...
--}

CommunicationControlPortID ::= INTEGER (0..65535)

Compressed-Mode-Deactivation-Flag::= ENUMERATED {
	deactivate,
	maintain-Active
}

ConfigurationGenerationID ::= INTEGER (0..255)
-- Value '0' means "No configuration" 

ConstantValue ::= INTEGER (-10..10,...)
-- -10 dB - +10 dB
-- unit dB
-- step 1 dB

CQI-Feedback-Cycle ::= ENUMERATED {v0, v2, v4, v8, v10, v20, v40, v80, v160,...}

CQI-Power-Offset ::= INTEGER (0..8,...)
-- According to mapping in ref. [9] subclause 4.2.1

CQI-RepetitionFactor ::= INTEGER (1..4,...)
-- Step: 1

CriticalityDiagnostics ::= SEQUENCE {
	procedureID					ProcedureID				OPTIONAL,
	triggeringMessage			TriggeringMessage			OPTIONAL,
	procedureCriticality		Criticality				OPTIONAL,
	transactionID				TransactionID				OPTIONAL,
	iEsCriticalityDiagnostics	CriticalityDiagnostics-IE-List	OPTIONAL,
--	iE-Extensions				ProtocolExtensionContainer { {CriticalityDiagnostics-ExtIEs} }		OPTIONAL,
	iE-Extensions				ProtocolExtensionContainer OPTIONAL,
	...
}

--CriticalityDiagnostics-ExtIEs NBAP-PROTOCOL-EXTENSION ::= {
--	...
--}

CriticalityDiagnostics-IE-List ::= SEQUENCE (SIZE (1..256)) OF
	SEQUENCE {
		iECriticality		Criticality,
		iE-ID				ProtocolIE-ID,
		repetitionNumber	RepetitionNumber0		OPTIONAL,
--		iE-Extensions		ProtocolExtensionContainer { {CriticalityDiagnostics-IE-List-ExtIEs} }		OPTIONAL,
		iE-Extensions		ProtocolExtensionContainer OPTIONAL,
		...
	}

--CriticalityDiagnostics-IE-List-ExtIEs NBAP-PROTOCOL-EXTENSION ::= {
--	{	ID id-MessageStructure		CRITICALITY ignore		EXTENSION MessageStructure		PRESENCE optional	}|
--	{	ID id-TypeOfError			CRITICALITY ignore		EXTENSION TypeOfError			PRESENCE mandatory	},
--	...
--}

CRNC-CommunicationContextID ::= INTEGER (0..1048575)

CSBMeasurementID ::= INTEGER (0..65535)

CSBTransmissionID ::= INTEGER (0..65535)

-- ==========================================
--	D
-- ==========================================


--Data-Description-Indicator-Item-ExtIEs NBAP-PROTOCOL-EXTENSION ::= {
--	...
--}

DATA-ID ::= INTEGER (0..3)

DCH-ID ::= INTEGER (0..255)

DCH-FDD-Information ::= SEQUENCE (SIZE (1..128)) OF DCH-FDD-InformationItem

DCH-FDD-InformationItem ::= SEQUENCE {
	payloadCRC-PresenceIndicator		PayloadCRC-PresenceIndicator,
	ul-FP-Mode							UL-FP-Mode,
	toAWS								ToAWS,
	toAWE								ToAWE,
	dCH-SpecificInformationList			DCH-Specific-FDD-InformationList,
--	iE-Extensions						ProtocolExtensionContainer { { DCH-FDD-InformationItem-ExtIEs} }	OPTIONAL,
	iE-Extensions						ProtocolExtensionContainer OPTIONAL,
	...
}

--DCH-FDD-InformationItem-ExtIEs NBAP-PROTOCOL-EXTENSION ::= {
--	{ ID id-TnlQos						CRITICALITY ignore		EXTENSION TnlQos		PRESENCE optional	},
--	...
--}

DCH-Specific-FDD-InformationList ::= SEQUENCE (SIZE (1..128)) OF DCH-Specific-FDD-Item

DCH-Specific-FDD-Item ::=	SEQUENCE {
	dCH-ID								DCH-ID,
	ul-TransportFormatSet				TransportFormatSet,
	dl-TransportFormatSet				TransportFormatSet,
	allocationRetentionPriority			AllocationRetentionPriority,
	frameHandlingPriority				FrameHandlingPriority,
	qE-Selector							QE-Selector,
--	iE-Extensions						ProtocolExtensionContainer { { DCH-Specific-FDD-Item-ExtIEs} }	OPTIONAL,
	iE-Extensions						ProtocolExtensionContainer OPTIONAL,
	...
}

--DCH-Specific-FDD-Item-ExtIEs NBAP-PROTOCOL-EXTENSION ::= {
--	{ ID id-Unidirectional-DCH-Indicator	CRITICALITY reject	EXTENSION Unidirectional-DCH-Indicator	PRESENCE optional	},
--	...
--}

DCH-InformationResponse ::= SEQUENCE (SIZE (1..128)) OF DCH-InformationResponseItem

DCH-InformationResponseItem ::= SEQUENCE {
	dCH-ID											DCH-ID,
	bindingID										BindingID				OPTIONAL,
	transportLayerAddress							TransportLayerAddress	OPTIONAL,
--	iE-Extensions									ProtocolExtensionContainer { { DCH-InformationResponseItem-ExtIEs} }		OPTIONAL,
	iE-Extensions									ProtocolExtensionContainer OPTIONAL,
	...
}

--DCH-InformationResponseItem-ExtIEs NBAP-PROTOCOL-EXTENSION ::= {
--	...
--}

DCH-TDD-Information ::= SEQUENCE (SIZE (1..128)) OF DCH-TDD-InformationItem

DCH-TDD-InformationItem ::= SEQUENCE {
	payloadCRC-PresenceIndicator		PayloadCRC-PresenceIndicator,
	ul-FP-Mode							UL-FP-Mode,
	toAWS								ToAWS,
	toAWE								ToAWE,
	dCH-SpecificInformationList			DCH-Specific-TDD-InformationList,
--	iE-Extensions							ProtocolExtensionContainer { { DCH-TDD-InformationItem-ExtIEs} }		OPTIONAL,
	iE-Extensions						ProtocolExtensionContainer OPTIONAL,
	...
}

--DCH-TDD-InformationItem-ExtIEs NBAP-PROTOCOL-EXTENSION ::= {
--	{ID id-TnlQos						CRITICALITY ignore		EXTENSION TnlQos		PRESENCE optional},
--	...
--}

DCH-Specific-TDD-InformationList ::= SEQUENCE (SIZE (1..128)) OF DCH-Specific-TDD-Item

DCH-Specific-TDD-Item ::=	SEQUENCE {
	dCH-ID									DCH-ID,
	ul-CCTrCH-ID							CCTrCH-ID,
	dl-CCTrCH-ID							CCTrCH-ID,
	ul-TransportFormatSet					TransportFormatSet,
	dl-TransportFormatSet					TransportFormatSet,
	allocationRetentionPriority				AllocationRetentionPriority,
	frameHandlingPriority					FrameHandlingPriority,
	qE-Selector								QE-Selector						OPTIONAL,
	-- This IE shall be present if DCH is part of set of Coordinated DCHs
--	iE-Extensions							ProtocolExtensionContainer { { DCH-Specific-TDD-Item-ExtIEs} }		OPTIONAL,
	iE-Extensions							ProtocolExtensionContainer OPTIONAL,
	...
}

--DCH-Specific-TDD-Item-ExtIEs NBAP-PROTOCOL-EXTENSION ::= {
--	{ ID id-Unidirectional-DCH-Indicator	CRITICALITY reject	EXTENSION Unidirectional-DCH-Indicator	PRESENCE optional	},
--	...
--}

FDD-DCHs-to-Modify ::= SEQUENCE (SIZE (1..128)) OF FDD-DCHs-to-ModifyItem

FDD-DCHs-to-ModifyItem	 ::= SEQUENCE {
	ul-FP-Mode							UL-FP-Mode		OPTIONAL,
	toAWS								ToAWS			OPTIONAL,
	toAWE								ToAWE			OPTIONAL,
	transportBearerRequestIndicator		TransportBearerRequestIndicator,
	dCH-SpecificInformationList			DCH-ModifySpecificInformation-FDD,
--	iE-Extensions						ProtocolExtensionContainer { { FDD-DCHs-to-ModifyItem-ExtIEs} }		OPTIONAL,
	iE-Extensions						ProtocolExtensionContainer OPTIONAL,
	...
}

--FDD-DCHs-to-ModifyItem-ExtIEs  NBAP-PROTOCOL-EXTENSION ::= {
--	{ID id-TnlQos						CRITICALITY ignore		EXTENSION TnlQos		PRESENCE optional},
--	...
--}

DCH-ModifySpecificInformation-FDD::= SEQUENCE (SIZE (1..128)) OF DCH-ModifySpecificItem-FDD

DCH-ModifySpecificItem-FDD::=	SEQUENCE {
	dCH-ID											DCH-ID,
	ul-TransportFormatSet							TransportFormatSet			OPTIONAL,
	dl-TransportFormatSet							TransportFormatSet			OPTIONAL,
	allocationRetentionPriority						AllocationRetentionPriority	OPTIONAL,
	frameHandlingPriority							FrameHandlingPriority		OPTIONAL,
--	iE-Extensions									ProtocolExtensionContainer { { DCH-ModifySpecificItem-FDD-ExtIEs} }		OPTIONAL,
	iE-Extensions									ProtocolExtensionContainer OPTIONAL,
	...
}

--DCH-ModifySpecificItem-FDD-ExtIEs  NBAP-PROTOCOL-EXTENSION ::= {
--	...
--}


TDD-DCHs-to-Modify ::= SEQUENCE (SIZE (1..128)) OF DCH-ModifyItem-TDD

DCH-ModifyItem-TDD ::= SEQUENCE {
	ul-FP-Mode							UL-FP-Mode		OPTIONAL,
	toAWS								ToAWS			OPTIONAL,
	toAWE								ToAWE			OPTIONAL,
	transportBearerRequestIndicator		TransportBearerRequestIndicator,
	dCH-SpecificInformationList			DCH-ModifySpecificInformation-TDD,
--	iE-Extensions						ProtocolExtensionContainer { { TDD-DCHs-to-ModifyItem-ExtIEs} }			OPTIONAL,
	iE-Extensions						ProtocolExtensionContainer OPTIONAL,
	...
}

--TDD-DCHs-to-ModifyItem-ExtIEs  NBAP-PROTOCOL-EXTENSION ::= {
--	{ID id-TnlQos						CRITICALITY ignore		EXTENSION TnlQos		PRESENCE optional},
--	...
--}

DCH-ModifySpecificInformation-TDD ::= SEQUENCE (SIZE (1..128)) OF DCH-ModifySpecificItem-TDD

DCH-ModifySpecificItem-TDD ::=	SEQUENCE {
	dCH-ID											DCH-ID,
	ul-CCTrCH-ID									CCTrCH-ID					OPTIONAL,
	dl-CCTrCH-ID									CCTrCH-ID					OPTIONAL,
	ul-TransportFormatSet							TransportFormatSet			OPTIONAL,
	dl-TransportFormatSet							TransportFormatSet			OPTIONAL,
	allocationRetentionPriority						AllocationRetentionPriority	OPTIONAL,
	frameHandlingPriority							FrameHandlingPriority		OPTIONAL,
--	iE-Extensions									ProtocolExtensionContainer { { DCH-ModifySpecificItem-TDD-ExtIEs} }			OPTIONAL,
	iE-Extensions									ProtocolExtensionContainer OPTIONAL,
	...
}

--DCH-ModifySpecificItem-TDD-ExtIEs  NBAP-PROTOCOL-EXTENSION ::= {
--	...
--}

DedicatedChannelsCapacityConsumptionLaw ::= SEQUENCE ( SIZE(1..8) ) OF
	SEQUENCE {
		dl-Cost-1		INTEGER (0..65535),
		dl-Cost-2		INTEGER (0..65535),
		ul-Cost-1		INTEGER (0..65535),
		ul-Cost-2		INTEGER (0..65535),
--		iE-Extensions		ProtocolExtensionContainer { { DedicatedChannelsCapacityConsumptionLaw-ExtIEs } }		OPTIONAL,
		iE-Extensions		ProtocolExtensionContainer OPTIONAL,
	...
}

--DedicatedChannelsCapacityConsumptionLaw-ExtIEs NBAP-PROTOCOL-EXTENSION ::= {
--	...
--}

DedicatedMeasurementType ::= ENUMERATED {
	sir,
	sir-error,
	transmitted-code-power,
	rscp,
	rx-timing-deviation,
	round-trip-time,
	...,
	rx-timing-deviation-LCR,
	angle-Of-Arrival-LCR,
	hs-sich-quality,
	best-Cell-Portions

}

DedicatedMeasurementValue ::= CHOICE {
	sIR-Value						SIR-Value,
	sIR-ErrorValue					SIR-Error-Value,
	transmittedCodePowerValue			Transmitted-Code-Power-Value,
	rSCP								RSCP-Value,
	rxTimingDeviationValue				Rx-Timing-Deviation-Value,
	roundTripTime						Round-Trip-Time-Value,
	...,
	extension-DedicatedMeasurementValue		Extension-DedicatedMeasurementValue
}

--Extension-DedicatedMeasurementValue	::= ProtocolIE-Single-Container {{ Extension-DedicatedMeasurementValueIE }}
Extension-DedicatedMeasurementValue	::= ProtocolIE-Single-Container

--Extension-DedicatedMeasurementValueIE NBAP-PROTOCOL-IES ::= {
--	{ ID id-Rx-Timing-Deviation-Value-LCR	CRITICALITY reject	TYPE Rx-Timing-Deviation-Value-LCR	PRESENCE mandatory }|
--	{ ID id-Angle-Of-Arrival-Value-LCR	CRITICALITY reject	TYPE Angle-Of-Arrival-Value-LCR	PRESENCE mandatory }|
--	{ ID id-HS-SICH-Reception-Quality	CRITICALITY reject	TYPE HS-SICH-Reception-Quality-Value	PRESENCE mandatory }|
--	{ ID id-Best-Cell-Portions-Value	CRITICALITY reject	TYPE Best-Cell-Portions-Value	PRESENCE mandatory },
--	...
--}

DedicatedMeasurementValueInformation ::= CHOICE {
	measurementAvailable		DedicatedMeasurementAvailable,
	measurementnotAvailable		DedicatedMeasurementnotAvailable
}

DedicatedMeasurementAvailable::= SEQUENCE {
	dedicatedmeasurementValue		DedicatedMeasurementValue,
    cFN                             CFN							OPTIONAL,
--	ie-Extensions					ProtocolExtensionContainer { { DedicatedMeasurementAvailableItem-ExtIEs} }		OPTIONAL,
	ie-Extensions					ProtocolExtensionContainer OPTIONAL,
	...
}

--DedicatedMeasurementAvailableItem-ExtIEs NBAP-PROTOCOL-EXTENSION ::= {
--	...
--}

DedicatedMeasurementnotAvailable ::= NULL

DelayedActivation ::= CHOICE {
	cfn						CFN,
	separate-indication		NULL
}

DelayedActivationUpdate ::= CHOICE {
	activate		Activate-Info,
	deactivate		Deactivate-Info
}

Activate-Info ::= SEQUENCE {
	activation-type  		Execution-Type,
	initial-dl-tx-power 	DL-Power,
	firstRLS-Indicator		FirstRLS-Indicator											OPTIONAL, 
	--FDD Only
	propagation-delay		PropagationDelay 											OPTIONAL, 
	--FDD Only
--	iE-Extensions			ProtocolExtensionContainer { { Activate-Info-ExtIEs} }		OPTIONAL,
	iE-Extensions			ProtocolExtensionContainer OPTIONAL,
	...
}

--Activate-Info-ExtIEs NBAP-PROTOCOL-EXTENSION ::= {
--	...
--}

Deactivate-Info ::= SEQUENCE {
	deactivation-type  		Execution-Type,
--	iE-Extensions			ProtocolExtensionContainer { { Deactivate-Info-ExtIEs} }		OPTIONAL,
	iE-Extensions			ProtocolExtensionContainer OPTIONAL,
	...
}

--Deactivate-Info-ExtIEs NBAP-PROTOCOL-EXTENSION ::= {
--	...
--}

Execution-Type ::= CHOICE {
	synchronised 	CFN,
	unsynchronised	NULL
}

DeltaSIR				::= INTEGER (0..30)
-- Unit dB, Step 0.1 dB, Range 0..3 dB.

DGPSCorrections ::= SEQUENCE {
   gpstow                GPSTOW,
   status-health         GPS-Status-Health,
   satelliteinfo         SAT-Info-DGPSCorrections,
--   ie-Extensions		 ProtocolExtensionContainer { { DGPSCorrections-ExtIEs} }		OPTIONAL,
   ie-Extensions		 ProtocolExtensionContainer OPTIONAL,
   ...
}

--DGPSCorrections-ExtIEs NBAP-PROTOCOL-EXTENSION ::= {
--	...
--}

DGPSThresholds ::= SEQUENCE {
   prcdeviation         PRCDeviation,
-- ie-Extensions		ProtocolExtensionContainer { { DGPSThresholds-ExtIEs} }		OPTIONAL,
   ie-Extensions		ProtocolExtensionContainer OPTIONAL,
   ...
}

--DGPSThresholds-ExtIEs NBAP-PROTOCOL-EXTENSION ::= {
--	...
--}

DiscardTimer ::= ENUMERATED {v20,v40,v60,v80,v100,v120,v140,v160,v180,v200,v250,v300,v400,v500,v750,v1000,v1250,v1500,v1750,v2000,v2500,v3000,v3500,v4000,v4500,v5000,v7500,
 ...
}

DiversityControlField ::= ENUMERATED {
	may,
	must,
	must-not,
	...
}

DiversityMode ::= ENUMERATED {
	none, 
	sTTD,
	closed-loop-mode1,
	not-used-closed-loop-mode2,
	...
}

DL-DPCH-SlotFormat ::= INTEGER (0..16,...)

DL-DPCH-TimingAdjustment ::= ENUMERATED {
	timing-advance,
	timing-delay
}

DL-Timeslot-Information ::= SEQUENCE (SIZE (1.. 15)) OF DL-Timeslot-InformationItem

DL-Timeslot-InformationItem	 ::= SEQUENCE {
	timeSlot								TimeSlot,
	midambleShiftAndBurstType				MidambleShiftAndBurstType,
	tFCI-Presence							TFCI-Presence,
	dL-Code-Information						TDD-DL-Code-Information,
--	iE-Extensions							ProtocolExtensionContainer { { DL-Timeslot-InformationItem-ExtIEs} }		OPTIONAL,
	iE-Extensions							ProtocolExtensionContainer OPTIONAL,
	...
}

--DL-Timeslot-InformationItem-ExtIEs NBAP-PROTOCOL-EXTENSION ::= {
--	...
--}

DL-TimeslotLCR-Information ::= SEQUENCE (SIZE (1.. 6)) OF DL-TimeslotLCR-InformationItem

DL-TimeslotLCR-InformationItem	 ::= SEQUENCE {
	timeSlotLCR								TimeSlotLCR,
	midambleShiftLCR						MidambleShiftLCR,
	tFCI-Presence							TFCI-Presence,
	dL-Code-LCR-Information					TDD-DL-Code-LCR-Information,
--	iE-Extensions							ProtocolExtensionContainer { { DL-TimeslotLCR-InformationItem-ExtIEs} }		OPTIONAL,
	iE-Extensions							ProtocolExtensionContainer OPTIONAL,
	...
}

--DL-TimeslotLCR-InformationItem-ExtIEs NBAP-PROTOCOL-EXTENSION ::= {
--	{ ID id-Initial-DL-Power-TimeslotLCR-InformationItem	CRITICALITY ignore   EXTENSION DL-Power		PRESENCE optional	}|
	-- Applicable to 1.28Mcps TDD only
--	{ ID id-Maximum-DL-Power-TimeslotLCR-InformationItem	CRITICALITY ignore   EXTENSION DL-Power		PRESENCE optional	}|
	-- Applicable to 1.28Mcps TDD only
--	{ ID id-Minimum-DL-Power-TimeslotLCR-InformationItem	CRITICALITY ignore 	EXTENSION DL-Power		PRESENCE optional	},
	-- Applicable to 1.28Mcps TDD only
--	...
--}

DL-FrameType ::= ENUMERATED {
	typeA,
	typeB,
	...
}

DL-or-Global-CapacityCredit ::= INTEGER (0..65535)

DL-Power ::= INTEGER (-350..150)
-- Value = DL-Power/10
-- Unit dB, Range -35dB .. +15dB, Step +0.1dB

DLPowerAveragingWindowSize ::= INTEGER (1..60)

DL-PowerBalancing-Information ::= SEQUENCE {
	powerAdjustmentType					PowerAdjustmentType,
    dLReferencePower					DL-Power		OPTIONAL,
	-- This IE shall be present if Power Adjustment Type IE equals to 'Common'
	dLReferencePowerList-DL-PC-Rqst		DL-ReferencePowerInformationList		OPTIONAL,
	-- This IE shall be present if Power Adjustment Type IE equals to 'Individual'
	maxAdjustmentStep					MaxAdjustmentStep		OPTIONAL,
	-- This IE shall be present if Power Adjustment Type IE equals to 'Common' or 'Individual'
	adjustmentPeriod					AdjustmentPeriod		OPTIONAL,
	-- This IE shall be present if Power Adjustment Type IE equals to 'Common' or 'Individual'
	adjustmentRatio						ScaledAdjustmentRatio	OPTIONAL,
	-- This IE shall be present if Power Adjustment Type IE equals to 'Common' or 'Individual'
--	iE-Extensions						ProtocolExtensionContainer { { DL-PowerBalancing-Information-ExtIEs } } OPTIONAL,
	iE-Extensions						ProtocolExtensionContainer OPTIONAL,
	...
}

--DL-PowerBalancing-Information-ExtIEs NBAP-PROTOCOL-EXTENSION ::= {
--	...
--}

DL-ReferencePowerInformationList 		::= SEQUENCE (SIZE (1..16)) OF DL-ReferencePowerInformationItem

DL-ReferencePowerInformationItem ::= SEQUENCE {
	rL-ID						RL-ID,
	dl-Reference-Power			DL-Power,
--	iE-Extensions				ProtocolExtensionContainer { {DL-ReferencePowerInformationItem-ExtIEs} } OPTIONAL,
	iE-Extensions				ProtocolExtensionContainer OPTIONAL,
	...
}

--DL-ReferencePowerInformationItem-ExtIEs NBAP-PROTOCOL-EXTENSION ::= {
--	...
--}

DL-PowerBalancing-ActivationIndicator	::= ENUMERATED {
	dL-PowerBalancing-Activated
}

DL-PowerBalancing-UpdatedIndicator	::= ENUMERATED {
	dL-PowerBalancing-Updated
}

DL-ScramblingCode ::= INTEGER (0..15)
-- 0= Primary scrambling code of the cell, 1..15= Secondary scrambling code --

DL-TimeslotISCP ::= INTEGER (0..91)

DL-TimeslotISCPInfo ::= SEQUENCE (SIZE (1..15)) OF DL-TimeslotISCPInfoItem

DL-TimeslotISCPInfoItem ::= SEQUENCE {
	timeSlot					TimeSlot,
	dL-TimeslotISCP				DL-TimeslotISCP,
--	iE-Extensions				ProtocolExtensionContainer { {DL-TimeslotISCPInfoItem-ExtIEs} }			OPTIONAL,
	iE-Extensions				ProtocolExtensionContainer OPTIONAL,
	...
	}

--DL-TimeslotISCPInfoItem-ExtIEs  NBAP-PROTOCOL-EXTENSION ::= {
--	...
--}

DL-TimeslotISCPInfoLCR ::= SEQUENCE (SIZE (1..6)) OF DL-TimeslotISCPInfoItemLCR

DL-TimeslotISCPInfoItemLCR ::= SEQUENCE {
	timeSlotLCR					TimeSlotLCR,
	dL-TimeslotISCP				DL-TimeslotISCP,
--	iE-Extensions				ProtocolExtensionContainer { {DL-TimeslotISCPInfoItemLCR-ExtIEs} }			OPTIONAL,
	iE-Extensions				ProtocolExtensionContainer OPTIONAL,
	...
	}

--DL-TimeslotISCPInfoItemLCR-ExtIEs  NBAP-PROTOCOL-EXTENSION ::= {
--	...
--}

DL-TPC-Pattern01Count ::= INTEGER (0..30,...)

DLTransmissionBranchLoadValue ::= INTEGER (0..101,...)

Downlink-Compressed-Mode-Method 	::= ENUMERATED {
	not-Used-puncturing,
	sFdiv2,
	higher-layer-scheduling,
	...
}

DPC-Mode ::= ENUMERATED {
	mode0,
	mode1,
	...
}

DPCH-ID ::= INTEGER (0..239)

DSCH-ID ::= INTEGER (0..255)

DSCH-InformationResponse ::= SEQUENCE (SIZE (1..32)) OF DSCH-InformationResponseItem

DSCH-InformationResponseItem ::= SEQUENCE {
	dSCH-ID											DSCH-ID,
	bindingID										BindingID					OPTIONAL,
	transportLayerAddress							TransportLayerAddress		OPTIONAL,
--	iE-Extensions									ProtocolExtensionContainer { { DSCH-InformationResponseItem-ExtIEs } }		OPTIONAL,
	iE-Extensions									ProtocolExtensionContainer OPTIONAL,
	...
}

--DSCH-InformationResponseItem-ExtIEs NBAP-PROTOCOL-EXTENSION ::= {
--	...
--}

DSCH-TDD-Information ::= SEQUENCE (SIZE (1..32)) OF DSCH-TDD-InformationItem

DSCH-TDD-InformationItem ::= SEQUENCE {
	dSCH-ID									DSCH-ID,
	cCTrCH-ID								CCTrCH-ID,
	transportFormatSet						TransportFormatSet,
	allocationRetentionPriority				AllocationRetentionPriority,
	frameHandlingPriority					FrameHandlingPriority,
	toAWS									ToAWS,
	toAWE									ToAWE,
--	iE-Extensions							ProtocolExtensionContainer { { DSCH-TDD-InformationItem-ExtIEs} }		OPTIONAL,
	iE-Extensions							ProtocolExtensionContainer OPTIONAL,
	...
}

--DSCH-TDD-InformationItem-ExtIEs NBAP-PROTOCOL-EXTENSION ::= {
--	{ ID id-bindingID					CRITICALITY	ignore		EXTENSION 	BindingID			PRESENCE 	optional	}|
	-- Shall be ignored if bearer establishment with ALCAP.
--	{ ID id-transportlayeraddress		CRITICALITY	ignore		EXTENSION 	TransportLayerAddress	PRESENCE 	optional	},
	-- Shall be ignored if bearer establishment with ALCAP.
--	...
--}

DsField ::= BIT STRING (SIZE (8))

DwPCH-Power ::= INTEGER (-150..400,...)
-- DwPCH-power = power * 10
-- If power <= -15 DwPCH shall be set to -150
-- If power >= 40 DwPCH shall be set to 400
-- Unit dBm, Range -15dBm .. +40 dBm, Step +0.1dB


-- ==========================================
--	E
-- ==========================================

E-AGCH-FDD-Code-Information ::= CHOICE {
	replace					E-AGCH-FDD-Code-List,
	remove					NULL,
	...
}

E-AGCH-FDD-Code-List ::= SEQUENCE (SIZE (1..32)) OF FDD-DL-ChannelisationCodeNumber


E-DCH-Capability ::= ENUMERATED {
	e-DCH-capable,
	e-DCH-non-capable
}

E-DCH-DDI-Value ::= INTEGER (0..63)

E-DCH-FDD-DL-Control-Channel-Information ::= SEQUENCE {
	e-AGCH-And-E-RGCH-E-HICH-FDD-Scrambling-Code	DL-ScramblingCode															OPTIONAL,
	e-AGCH-Channelisation-Code						FDD-DL-ChannelisationCodeNumber												OPTIONAL,
	primary-e-RNTI									E-RNTI																		OPTIONAL,
	secondary-e-RNTI								E-RNTI																		OPTIONAL,
	e-RGCH-E-HICH-Channelisation-Code				FDD-DL-ChannelisationCodeNumber												OPTIONAL,
	e-RGCH-Signature-Sequence						E-RGCH-Signature-Sequence													OPTIONAL,
	e-HICH-Signature-Sequence						E-HICH-Signature-Sequence													OPTIONAL,
	serving-Grant-Value								E-Serving-Grant-Value														OPTIONAL,
	primary-Secondary-Grant-Selector				E-Primary-Secondary-Grant-Selector											OPTIONAL,
	e-RGCH-Release-Indicator						E-RGCH-Release-Indicator														OPTIONAL,
--	iE-Extensions									ProtocolExtensionContainer { { E-DCH-FDD-DL-Control-Channel-Information-ExtIEs} }		OPTIONAL,
	iE-Extensions									ProtocolExtensionContainer OPTIONAL,
	...
}

--E-DCH-FDD-DL-Control-Channel-Information-ExtIEs NBAP-PROTOCOL-EXTENSION ::= {
--	...
--}

E-DCH-FDD-Information ::= SEQUENCE {
	e-DCH-MACdFlows-Information						E-DCH-MACdFlows-Information,
--	iE-Extensions									ProtocolExtensionContainer { { E-DCH-FDD-Information-ExtIEs} }								OPTIONAL,
	iE-Extensions									ProtocolExtensionContainer OPTIONAL,
	...
}

--E-DCH-FDD-Information-ExtIEs NBAP-PROTOCOL-EXTENSION ::= {
--	...
--}

E-DCH-FDD-Information-Response ::= SEQUENCE {
	e-DCH-MACdFlow-Specific-InformationResp			E-DCH-MACdFlow-Specific-InformationResp										OPTIONAL,
--	iE-Extensions									ProtocolExtensionContainer { { E-DCH-FDD-Information-Response-ExtIEs } }					OPTIONAL,
	iE-Extensions									ProtocolExtensionContainer OPTIONAL,
	...
}

--E-DCH-FDD-Information-Response-ExtIEs NBAP-PROTOCOL-EXTENSION ::= {
--	...
--}

E-DCH-FDD-Information-to-Modify ::= SEQUENCE {
	e-DCH-MACdFlow-Specific-Info-to-Modify			E-DCH-MACdFlow-Specific-InfoList-to-Modify															OPTIONAL,
--	iE-Extensions									ProtocolExtensionContainer { { E-DCH-FDD-Information-to-Modify-ExtIEs} }					OPTIONAL,
	iE-Extensions									ProtocolExtensionContainer OPTIONAL,
	...
}

--E-DCH-FDD-Information-to-Modify-ExtIEs NBAP-PROTOCOL-EXTENSION ::= {
--	...
--}

E-DCH-Grant-Type-Information ::= CHOICE {
	e-DCH-Non-Scheduled-Transmission-Grant		E-DCH-Non-Scheduled-Transmission-Grant-Items,
	e-DCH-Scheduled-Transmission-Grant			NULL,
	...
}

E-DCH-LogicalChannelInformation ::= SEQUENCE (SIZE (1..16)) OF E-DCH-LogicalChannelInformationItem

E-DCH-LogicalChannelInformationItem ::= SEQUENCE {
	logicalChannelId				LogicalChannelID,
	schedulingPriorityIndicator		SchedulingPriorityIndicator,
	mACesGuaranteedBitRate			MACesGuaranteedBitRate		OPTIONAL,
	e-DCH-DDI-Value					E-DCH-DDI-Value,
	mACd-PDU-Size-List				E-DCH-MACdPDU-SizeList,
--	iE-Extensions					ProtocolExtensionContainer { { E-DCH-LogicalChannelInformationItem-ExtIEs } }			OPTIONAL,
	iE-Extensions					ProtocolExtensionContainer OPTIONAL,
	...
}

--E-DCH-LogicalChannelInformationItem-ExtIEs NBAP-PROTOCOL-EXTENSION ::= {
--	...
--}

E-DCH-MACdPDU-SizeList ::= SEQUENCE (SIZE (1.. 64)) OF E-DCH-MACdPDU-SizeListItem

E-DCH-MACdPDU-SizeListItem ::= SEQUENCE {
	mACdPDU-Size					MACdPDU-Size,
--	iE-Extensions					ProtocolExtensionContainer { { E-DCH-MACdPDU-SizeListItem-ExtIEs } }			OPTIONAL,
	iE-Extensions					ProtocolExtensionContainer OPTIONAL,
	...
}

--E-DCH-MACdPDU-SizeListItem-ExtIEs NBAP-PROTOCOL-EXTENSION ::= {
--	...
--}

E-DCH-LogicalChannelToModify ::= SEQUENCE (SIZE (1..16)) OF E-DCH-LogicalChannelToModifyItem

E-DCH-LogicalChannelToModifyItem ::= SEQUENCE {
	logicalChannelId				LogicalChannelID,
	schedulingPriorityIndicator		SchedulingPriorityIndicator		OPTIONAL,
	mACesGuaranteedBitRate			MACesGuaranteedBitRate		OPTIONAL,
	e-DCH-DDI-Value					E-DCH-DDI-Value					OPTIONAL,
	mACd-PDU-Size-List				E-DCH-MACdPDU-SizeToModifyList, 
--	iE-Extensions					ProtocolExtensionContainer { { E-DCH-LogicalChannelToModifyItem-ExtIEs } }			OPTIONAL,
	iE-Extensions					ProtocolExtensionContainer OPTIONAL,
	...
}

--E-DCH-LogicalChannelToModifyItem-ExtIEs NBAP-PROTOCOL-EXTENSION ::= {
--	...
--}

E-DCH-MACdPDU-SizeToModifyList ::= SEQUENCE (SIZE (0.. 64)) OF E-DCH-MACdPDU-SizeListItem



E-DCH-LogicalChannelToDelete ::= SEQUENCE (SIZE (1..16)) OF E-DCH-LogicalChannelToDeleteItem

E-DCH-LogicalChannelToDeleteItem ::= SEQUENCE {
	logicalChannelId				LogicalChannelID,
--	iE-Extensions					ProtocolExtensionContainer { { E-DCH-LogicalChannelToDeleteItem-ExtIEs } }			OPTIONAL,
	iE-Extensions					ProtocolExtensionContainer OPTIONAL,
	...
}

--E-DCH-LogicalChannelToDeleteItem-ExtIEs NBAP-PROTOCOL-EXTENSION ::= {
--	...
--}

LogicalChannelID ::= INTEGER (1..15)


E-DCH-HARQ-PO-FDD ::= INTEGER (0.. 6)

E-DCH-MACdFlow-ID ::= INTEGER (0..7)

E-DCH-MACdFlows-Information ::= SEQUENCE {
	e-DCH-MACdFlow-Specific-Info					E-DCH-MACdFlow-Specific-InfoList,
--	iE-Extensions									ProtocolExtensionContainer { { E-DCH-MACdFlows-Information-ExtIEs} }						OPTIONAL,
	iE-Extensions									ProtocolExtensionContainer OPTIONAL,
	...
}

--E-DCH-MACdFlows-Information-ExtIEs NBAP-PROTOCOL-EXTENSION ::= {
--	...
--}

E-DCH-MACdFlow-Multiplexing-List ::= BIT STRING ( SIZE(8) )

E-DCH-MACdFlow-Specific-InfoList ::= SEQUENCE (SIZE (1..8)) OF E-DCH-MACdFlow-Specific-InfoItem

E-DCH-MACdFlow-Specific-InfoItem ::= SEQUENCE {
	e-DCH-MACdFlow-ID								E-DCH-MACdFlow-ID,
	bindingID										BindingID																	OPTIONAL,
	transportLayerAddress							TransportLayerAddress														OPTIONAL,
	allocationRetentionPriority						AllocationRetentionPriority,
	tnlQos											TnlQos																		OPTIONAL,
	payloadCRC-PresenceIndicator					PayloadCRC-PresenceIndicator,
	maximum-Number-of-Retransmissions-For-E-DCH		Maximum-Number-of-Retransmissions-For-E-DCH,
	eDCH-HARQ-PO-FDD								E-DCH-HARQ-PO-FDD,
	eDCH-MACdFlow-Multiplexing-List					E-DCH-MACdFlow-Multiplexing-List																	OPTIONAL,
	eDCH-Grant-Type-Information						E-DCH-Grant-Type-Information,
	bundlingModeIndicator							BundlingModeIndicator														OPTIONAL,
	eDCHLogicalChannelInformation					E-DCH-LogicalChannelInformation,
--	iE-Extensions									ProtocolExtensionContainer { { E-DCH-MACdFlow-Specific-InfoItem-ExtIEs} }				OPTIONAL,
	iE-Extensions									ProtocolExtensionContainer OPTIONAL,
	...
}

--E-DCH-MACdFlow-Specific-InfoItem-ExtIEs NBAP-PROTOCOL-EXTENSION ::= {
--	...
--}

E-DCH-MACdFlow-Specific-InformationResp ::= SEQUENCE (SIZE (1..8)) OF E-DCH-MACdFlow-Specific-InformationResp-Item

E-DCH-MACdFlow-Specific-InformationResp-Item ::= SEQUENCE {
	e-DCH-MACdFlow-ID								E-DCH-MACdFlow-ID,
	bindingID										BindingID																	OPTIONAL,
	transportLayerAddress							TransportLayerAddress														OPTIONAL,
--	iE-Extensions									ProtocolExtensionContainer { { E-DCH-MACdFlow-Specific-InformationResp-Item-ExtIEs} }	OPTIONAL,
	iE-Extensions									ProtocolExtensionContainer OPTIONAL,
	...
}

--E-DCH-MACdFlow-Specific-InformationResp-Item-ExtIEs NBAP-PROTOCOL-EXTENSION ::= {
--	...
--}

E-DCH-MACdFlow-Specific-InfoList-to-Modify ::= SEQUENCE (SIZE (1..8)) OF E-DCH-MACdFlow-Specific-InfoItem-to-Modify

E-DCH-MACdFlow-Specific-InfoItem-to-Modify ::= SEQUENCE {
	e-DCH-MACdFlow-ID								E-DCH-MACdFlow-ID,
	allocationRetentionPriority						AllocationRetentionPriority													OPTIONAL,
	transportBearerRequestIndicator					TransportBearerRequestIndicator,
	bindingID										BindingID																	OPTIONAL,
	transportLayerAddress							TransportLayerAddress														OPTIONAL,
	tnlQos											TnlQos																		OPTIONAL,
	maximum-Number-of-Retransmissions-For-E-DCH		Maximum-Number-of-Retransmissions-For-E-DCH									OPTIONAL,
	eDCH-HARQ-PO-FDD								E-DCH-HARQ-PO-FDD																					OPTIONAL,
	eDCH-MACdFlow-Multiplexing-List					E-DCH-MACdFlow-Multiplexing-List																	OPTIONAL,
	eDCH-Grant-Type-Information						E-DCH-Grant-Type-Information																		OPTIONAL,
	eDCH-LogicalChannelToAdd						E-DCH-LogicalChannelInformation																		OPTIONAL,
	eDCH-LogicalChannelToModify						E-DCH-LogicalChannelToModify																		OPTIONAL,
	eDCH-LogicalChannelToDelete						E-DCH-LogicalChannelToDelete																		OPTIONAL,
--	iE-Extensions									ProtocolExtensionContainer { { E-DCH-MACdFlow-Specific-InfoItem-to-Modify-ExtIEs} }		OPTIONAL,
	iE-Extensions									ProtocolExtensionContainer OPTIONAL,
	...
}

--E-DCH-MACdFlow-Specific-InfoItem-to-Modify-ExtIEs NBAP-PROTOCOL-EXTENSION ::= {
--	...
--}

E-DCH-MACdFlows-to-Delete ::= SEQUENCE (SIZE (1..8)) OF E-DCH-MACdFlow-to-Delete-Item

E-DCH-MACdFlow-to-Delete-Item ::= SEQUENCE {
	e-DCH-MACdFlow-ID								E-DCH-MACdFlow-ID,
--	iE-Extensions									ProtocolExtensionContainer { { E-DCH-MACdFlow-to-Delete-Item-ExtIEs} }					OPTIONAL,
	iE-Extensions									ProtocolExtensionContainer OPTIONAL,
	...
}

--E-DCH-MACdFlow-to-Delete-Item-ExtIEs NBAP-PROTOCOL-EXTENSION ::= {
--	...
--}

E-DCH-Non-Scheduled-Transmission-Grant-Items ::= SEQUENCE {
	maxBits-MACe-PDU-non-scheduled				Max-Bits-MACe-PDU-non-scheduled,
	hARQ-Process-Allocation-2ms					HARQ-Process-Allocation-2ms-EDCH												OPTIONAL,
--	iE-Extensions								ProtocolExtensionContainer { { E-DCH-Non-Scheduled-Transmission-Grant-Items-ExtIEs} }		OPTIONAL,
	iE-Extensions								ProtocolExtensionContainer OPTIONAL,
	...
}

--E-DCH-Non-Scheduled-Transmission-Grant-Items-ExtIEs NBAP-PROTOCOL-EXTENSION ::= {
--	...
--}

E-DCHProvidedBitRateValue ::= INTEGER(0..16777215,...)
-- Unit bit/s, Range 0..2^24-1, Step 1 bit

Maximum-Target-ReceivedTotalWideBandPower ::= INTEGER (0..621)
-- mapping as for RTWP measurement value, as specified in [22]

Target-NonServing-EDCH-To-Total-EDCH-Power-Ratio ::= INTEGER (0..100)
-- Unit %, Range 0..100%, Step 1%

E-DCH-RL-Indication ::= ENUMERATED {
	e-DCH,
	non-e-DCH
}

E-DCH-TFCI-Table-Index ::= INTEGER (0..1,...)

E-DPCCH-PO ::= INTEGER (0..8)

E-Primary-Secondary-Grant-Selector ::= ENUMERATED {
	primary,
	secondary
}

E-HICH-Signature-Sequence ::= INTEGER (0..39)

End-Of-Audit-Sequence-Indicator ::= ENUMERATED {
	end-of-audit-sequence,
	not-end-of-audit-sequence
}

E-Serving-Grant-Value ::= INTEGER (0..31,...)

E-RGCH-E-HICH-FDD-Code-Information ::= CHOICE {
	replace					E-RGCH-E-HICH-FDD-Code-List,
	remove					NULL,
	...
}

E-RGCH-E-HICH-FDD-Code-List ::= SEQUENCE (SIZE (1..32)) OF FDD-DL-ChannelisationCodeNumber

E-RGCH-Release-Indicator ::= ENUMERATED {e-RGCHreleased}

E-RGCH-Signature-Sequence ::= INTEGER (0..39)

E-RNTI ::= INTEGER (0..65535)

E-TFCI ::= INTEGER (0..127)

E-TFCS-Information ::= SEQUENCE {
	e-DCH-TFCI-Table-Index								E-DCH-TFCI-Table-Index,
	e-DCH-Min-Set-E-TFCI							E-TFCI,
	reference-E-TFCI-Information					Reference-E-TFCI-Information,
--	iE-Extensions									ProtocolExtensionContainer { {E-TFCS-Information-ExtIEs} }		OPTIONAL,
	iE-Extensions									ProtocolExtensionContainer OPTIONAL,
	...
}

--E-TFCS-Information-ExtIEs NBAP-PROTOCOL-EXTENSION ::= {
--	...
--}

E-TTI ::= ENUMERATED {
	e-TTI-2ms,
	e-TTI-10ms
}

E-DCHProvidedBitRate ::= SEQUENCE (SIZE (1..16)) OF E-DCHProvidedBitRate-Item

E-DCHProvidedBitRate-Item ::= SEQUENCE {
	schedulingPriorityIndicator			SchedulingPriorityIndicator,
	e-DCHProvidedBitRateValue			E-DCHProvidedBitRateValue,
--	iE-Extensions						ProtocolExtensionContainer { { E-DCHProvidedBitRate-Item-ExtIEs} }		OPTIONAL,
	iE-Extensions						ProtocolExtensionContainer OPTIONAL,
	...
}

--E-DCHProvidedBitRate-Item-ExtIEs NBAP-PROTOCOL-EXTENSION ::= {
--	...
--}

-- ==========================================
--	F
-- ==========================================

FDD-DL-ChannelisationCodeNumber ::= INTEGER(0.. 511)
-- According to the mapping in [9]. The maximum value is equal to the DL spreading factor -1--

FDD-DL-CodeInformation ::= SEQUENCE (SIZE (1..10)) OF FDD-DL-CodeInformationItem

FDD-DL-CodeInformationItem ::= SEQUENCE {
	dl-ScramblingCode						DL-ScramblingCode,
	fdd-DL-ChannelisationCodeNumber			FDD-DL-ChannelisationCodeNumber,
	transmissionGapPatternSequenceCodeInformation		TransmissionGapPatternSequenceCodeInformation		OPTIONAL,
--	iE-Extensions							ProtocolExtensionContainer { { FDD-DL-CodeInformationItem-ExtIEs} }	OPTIONAL,
	iE-Extensions							ProtocolExtensionContainer OPTIONAL,
	...
}

--FDD-DL-CodeInformationItem-ExtIEs NBAP-PROTOCOL-EXTENSION ::= {
--	...
--}

FDD-S-CCPCH-FrameOffset ::= ENUMERATED {
	v1, v2, v4, ...
}

FDD-S-CCPCH-Offset ::= INTEGER (0..149)
-- 0: 0 chip, 1: 256 chip, 2: 512 chip, .. ,149: 38144 chip [7] --

FDD-TPC-DownlinkStepSize ::= ENUMERATED {
	step-size0-5,
	step-size1,
	step-size1-5,
	step-size2,
	...
}

FirstRLS-Indicator ::= ENUMERATED {
	first-RLS,
	not-first-RLS,
	...
}

FNReportingIndicator ::= ENUMERATED {
 fN-reporting-required,
 fN-reporting-not-required
}

FrameHandlingPriority ::= INTEGER (0..15)
-- 0=lowest priority, 15=highest priority --

FrameAdjustmentValue ::= INTEGER(0..4095)

FrameOffset ::= INTEGER (0..255)

FPACH-Power ::= INTEGER (-150..400,...) -- FPACH-power = power * 10
-- If power <= -15 FPACH shall be set to -150
-- If power >= 40 FPACH shall be set to 400
-- Unit dBm, Range -15dBm .. +40 dBm, Step +0.1dB

-- ==========================================
--	G
-- ==========================================

GapLength				::= INTEGER (1..14)
-- Unit slot

GapDuration				::= INTEGER (1..144,...)
-- Unit frame

GenericTrafficCategory	::= BIT STRING (SIZE (8))

GPS-Almanac ::= SEQUENCE {
    wna-alm              BIT STRING (SIZE (8)),
     sat-info-almanac     SAT-Info-Almanac,
	sVGlobalHealth-alm	BIT STRING (SIZE (364))	OPTIONAL,
--    ie-Extensions		 ProtocolExtensionContainer { { GPS-Almanac-ExtIEs} }		OPTIONAL,
    ie-Extensions		 ProtocolExtensionContainer OPTIONAL,
   ...
}

--GPS-Almanac-ExtIEs NBAP-PROTOCOL-EXTENSION ::= {
--	{ ID id-SAT-Info-Almanac-ExtItem	CRITICALITY	ignore		EXTENSION 	SAT-Info-Almanac-ExtList			PRESENCE	optional},
--	...
--}

GPS-Ionospheric-Model ::= SEQUENCE {
   alpha-zero-ionos      BIT STRING (SIZE (8)),
   alpha-one-ionos       BIT STRING (SIZE (8)),
   alpha-two-ionos       BIT STRING (SIZE (8)),
   alpha-three-ionos     BIT STRING (SIZE (8)),
   beta-zero-ionos       BIT STRING (SIZE (8)),
   beta-one-ionos        BIT STRING (SIZE (8)),
   beta-two-ionos        BIT STRING (SIZE (8)),
   beta-three-ionos      BIT STRING (SIZE (8)),
--   ie-Extensions		 ProtocolExtensionContainer { { GPS-Ionospheric-Model-ExtIEs} }		OPTIONAL,
   ie-Extensions		 ProtocolExtensionContainer OPTIONAL,
   ...
}

--GPS-Ionospheric-Model-ExtIEs NBAP-PROTOCOL-EXTENSION ::= {
--	...
--}

GPS-Information ::= SEQUENCE (SIZE (0..8)) OF GPS-Information-Item
-- This IE shall be present if the Information Type Item IE indicates ‘GPS Information’

GPS-Information-Item ::= ENUMERATED {
   gps-navigation-model-and-time-recovery,
   gps-ionospheric-model,
   gps-utc-model,
   gps-almanac,
   gps-rt-integrity,
   ...
}

GPS-RealTime-Integrity ::= CHOICE {
	bad-satellites		        GPSBadSat-Info-RealTime-Integrity,
	no-bad-satellites           NULL
}

GPSBadSat-Info-RealTime-Integrity ::= SEQUENCE {
	sat-info		                SATInfo-RealTime-Integrity,
--	ie-Extensions					ProtocolExtensionContainer { { GPSBadSat-Info-RealTime-Integrity-ExtIEs} }		OPTIONAL,
	ie-Extensions					ProtocolExtensionContainer OPTIONAL,
	...
}

--GPSBadSat-Info-RealTime-Integrity-ExtIEs NBAP-PROTOCOL-EXTENSION ::= {
--	...
--}

GPS-NavigationModel-and-TimeRecovery ::= SEQUENCE (SIZE (1..16)) OF GPS-NavandRecovery-Item

GPS-NavandRecovery-Item ::= SEQUENCE {
  tx-tow-nav                       INTEGER (0..1048575),
  sat-id-nav                       SAT-ID,
  tlm-message-nav                  BIT STRING (SIZE (14)),
  tlm-revd-c-nav                   BIT STRING (SIZE (2)),
  ho-word-nav                      BIT STRING (SIZE (22)),
  w-n-nav                          BIT STRING (SIZE (10)),
  ca-or-p-on-l2-nav                BIT STRING (SIZE (2)),
  user-range-accuracy-index-nav    BIT STRING (SIZE (4)),
  sv-health-nav                    BIT STRING (SIZE (6)),
  iodc-nav                         BIT STRING (SIZE (10)),
  l2-p-dataflag-nav                BIT STRING (SIZE (1)),
  sf1-reserved-nav                 BIT STRING (SIZE (87)),
  t-gd-nav                         BIT STRING (SIZE (8)),
  t-oc-nav                         BIT STRING (SIZE (16)),
  a-f-2-nav                        BIT STRING (SIZE (8)),
  a-f-1-nav                        BIT STRING (SIZE (16)),
  a-f-zero-nav                     BIT STRING (SIZE (22)),
  c-rs-nav                         BIT STRING (SIZE (16)),
  delta-n-nav                      BIT STRING (SIZE (16)),
  m-zero-nav                       BIT STRING (SIZE (32)),
  c-uc-nav                         BIT STRING (SIZE (16)),
  gps-e-nav                        BIT STRING (SIZE (32)),
  c-us-nav                         BIT STRING (SIZE (16)),
  a-sqrt-nav                       BIT STRING (SIZE (32)),
  t-oe-nav                         BIT STRING (SIZE (16)),
  fit-interval-flag-nav            BIT STRING (SIZE (1)),
  aodo-nav                         BIT STRING (SIZE (5)),
  c-ic-nav                         BIT STRING (SIZE (16)),
  omega-zero-nav                   BIT STRING (SIZE (32)),
  c-is-nav                         BIT STRING (SIZE (16)),
  i-zero-nav                       BIT STRING (SIZE (32)),
  c-rc-nav                         BIT STRING (SIZE (16)),
  gps-omega-nav                    BIT STRING (SIZE (32)),
  omegadot-nav                     BIT STRING (SIZE (24)),
  idot-nav                         BIT STRING (SIZE (14)),
  spare-zero-fill                  BIT STRING (SIZE (20)),
--  ie-Extensions		               ProtocolExtensionContainer { { GPS-NavandRecovery-Item-ExtIEs} }		OPTIONAL,
  ie-Extensions		               ProtocolExtensionContainer OPTIONAL,
   ...
}

--GPS-NavandRecovery-Item-ExtIEs NBAP-PROTOCOL-EXTENSION ::= {
--	...
--}


GPS-RX-POS ::= SEQUENCE {
    latitudeSign		    ENUMERATED {north, south},
	latitude			    INTEGER (0..8388607),
	longitude			    INTEGER (-8388608..8388607),
	directionOfAltitude		ENUMERATED {height, depth},
	altitude				INTEGER (0..32767),
--	iE-Extensions			ProtocolExtensionContainer { { GPS-RX-POS-ExtIEs} } OPTIONAL,
	iE-Extensions			ProtocolExtensionContainer OPTIONAL,
	...
}

--GPS-RX-POS-ExtIEs NBAP-PROTOCOL-EXTENSION ::= {
--	...
--}

GPS-Status-Health ::= ENUMERATED {
   udre-scale-1dot0,
   udre-scale-0dot75,
   udre-scale-0dot5,
   udre-scale-0dot3,
   udre-scale-0dot1,
   no-data,
   invalid-data
}

GPSTOW ::= INTEGER (0..604799)

GPS-UTC-Model ::= SEQUENCE {
   a-one-utc             BIT STRING (SIZE (24)),
   a-zero-utc            BIT STRING (SIZE (32)),
   t-ot-utc              BIT STRING (SIZE (8)),
   delta-t-ls-utc        BIT STRING (SIZE (8)),
   w-n-t-utc             BIT STRING (SIZE (8)),
   w-n-lsf-utc           BIT STRING (SIZE (8)),
   dn-utc                BIT STRING (SIZE (8)),
   delta-t-lsf-utc       BIT STRING (SIZE (8)),
--   ie-Extensions		 ProtocolExtensionContainer { { GPS-UTC-Model-ExtIEs} }		OPTIONAL,
   ie-Extensions		 ProtocolExtensionContainer OPTIONAL,
   ...
}

--GPS-UTC-Model-ExtIEs NBAP-PROTOCOL-EXTENSION ::= {
--	...
--}

-- ==========================================
--	H
-- ==========================================
HARQ-MemoryPartitioning	::= CHOICE {
	implicit		HARQ-MemoryPartitioning-Implicit,
	explicit		HARQ-MemoryPartitioning-Explicit,
	...
	}

HARQ-MemoryPartitioning-Implicit	::= SEQUENCE {
	number-of-Processes			INTEGER (1..8,...),
--	iE-Extensions				ProtocolExtensionContainer { { HARQ-MemoryPartitioning-Implicit-ExtIEs } }			OPTIONAL,
	iE-Extensions				ProtocolExtensionContainer OPTIONAL,
	...
}

--HARQ-MemoryPartitioning-Implicit-ExtIEs NBAP-PROTOCOL-EXTENSION ::= {
--	...
--}

HARQ-MemoryPartitioning-Explicit	::= SEQUENCE {
	hARQ-MemoryPartitioningList			HARQ-MemoryPartitioningList,
--	iE-Extensions						ProtocolExtensionContainer { { HARQ-MemoryPartitioning-Explicit-ExtIEs } }			OPTIONAL,
	iE-Extensions						ProtocolExtensionContainer OPTIONAL,
	...
}

--HARQ-MemoryPartitioning-Explicit-ExtIEs NBAP-PROTOCOL-EXTENSION ::= {
--	...
--}

--HARQ-MemoryPartitioningList	::= SEQUENCE (SIZE (1..maxNrOfHARQProcesses)) OF HARQ-MemoryPartitioningItem
HARQ-MemoryPartitioningList	::= SEQUENCE (SIZE (1..8)) OF HARQ-MemoryPartitioningItem

HARQ-MemoryPartitioningItem ::= SEQUENCE {
	process-Memory-Size					ENUMERATED {
										hms800, hms1600, hms2400, hms3200, hms4000,
										hms4800, hms5600, hms6400, hms7200, hms8000,
										hms8800, hms9600, hms10400, hms11200, hms12000,
										hms12800, hms13600, hms14400, hms15200, hms16000,
										hms17600, hms19200, hms20800, hms22400, hms24000,
										hms25600, hms27200, hms28800, hms30400, hms32000,
										hms36000, hms40000, hms44000, hms48000, hms52000,
										hms56000, hms60000, hms64000, hms68000, hms72000,
										hms76000, hms80000, hms88000, hms96000, hms104000,
										hms112000, hms120000, hms128000, hms136000, hms144000,
										hms152000, hms160000, hms176000, hms192000, hms208000,
										hms224000, hms240000, hms256000, hms272000, hms288000,
										hms304000,...},
--	iE-Extensions						ProtocolExtensionContainer { { HARQ-MemoryPartitioningItem-ExtIEs } }			OPTIONAL,
	iE-Extensions						ProtocolExtensionContainer OPTIONAL,
	...
}

--HARQ-MemoryPartitioningItem-ExtIEs NBAP-PROTOCOL-EXTENSION ::= {
--	...
--}

HARQ-Preamble-Mode ::= ENUMERATED {
mode0,
mode1
}


--HARQ-Process-Allocation-2ms-EDCH ::= BIT STRING ( SIZE(maxNrOfEDCHHARQProcesses2msEDCH) )
HARQ-Process-Allocation-2ms-EDCH ::= BIT STRING ( SIZE(8) )

HARQ-Preamble-Mode-Activation-Indicator	::=ENUMERATED	{
	harqPreambleModeActivated
}

HSDPA-Capability ::= ENUMERATED {hsdpa-capable, hsdpa-non-capable}

HS-DSCHProvidedBitRate ::= SEQUENCE (SIZE (1..16)) OF HS-DSCHProvidedBitRate-Item

HS-DSCHProvidedBitRate-Item ::= SEQUENCE {
	schedulingPriorityIndicator			SchedulingPriorityIndicator,
	hS-DSCHProvidedBitRateValue			HS-DSCHProvidedBitRateValue,
--	iE-Extensions						ProtocolExtensionContainer { { HS-DSCHProvidedBitRate-Item-ExtIEs} }		OPTIONAL,
	iE-Extensions						ProtocolExtensionContainer OPTIONAL,
	...
}

--HS-DSCHProvidedBitRate-Item-ExtIEs NBAP-PROTOCOL-EXTENSION ::= {
--	...
--}

HS-DSCHProvidedBitRateValue ::= INTEGER(0..16777215,...)
-- Unit bit/s, Range 0..2^24-1, Step 1 bit

--HS-DSCHProvidedBitRateValueInformation-For-CellPortion ::= SEQUENCE (SIZE (1..maxNrOfCellPortionsPerCell)) OF HS-DSCHProvidedBitRateValueInformation-For-CellPortion-Item
HS-DSCHProvidedBitRateValueInformation-For-CellPortion ::= SEQUENCE (SIZE (1..64)) OF HS-DSCHProvidedBitRateValueInformation-For-CellPortion-Item

HS-DSCHProvidedBitRateValueInformation-For-CellPortion-Item ::= SEQUENCE{
	cellPortionID					CellPortionID,
	hS-DSCHProvidedBitRateValue		HS-DSCHProvidedBitRate,
--	iE-Extensions					ProtocolExtensionContainer { {HS-DSCHProvidedBitRateValueInformation-For-CellPortion-Item-ExtIEs} }	OPTIONAL,
	iE-Extensions					ProtocolExtensionContainer OPTIONAL,
	...
}

--HS-DSCHProvidedBitRateValueInformation-For-CellPortion-Item-ExtIEs NBAP-PROTOCOL-EXTENSION ::= {
--	...
--}

HS-DSCHRequiredPower ::= SEQUENCE (SIZE (1..16)) OF HS-DSCHRequiredPower-Item

HS-DSCHRequiredPower-Item ::= SEQUENCE {
	schedulingPriorityIndicator				SchedulingPriorityIndicator,
	hS-DSCHRequiredPowerValue				HS-DSCHRequiredPowerValue,
	hS-DSCHRequiredPowerPerUEInformation	HS-DSCHRequiredPowerPerUEInformation						OPTIONAL,
--	iE-Extensions							ProtocolExtensionContainer { { HS-DSCHRequiredPower-Item-ExtIEs} }		OPTIONAL,
	iE-Extensions							ProtocolExtensionContainer OPTIONAL,
	...
}

--HS-DSCHRequiredPower-Item-ExtIEs NBAP-PROTOCOL-EXTENSION ::= {
--	...
--}

HS-DSCHRequiredPowerValue ::= INTEGER(0..1000)
-- Unit %, Range 0 ..1000, Step 0.1%

--HS-DSCHRequiredPowerPerUEInformation ::= SEQUENCE (SIZE (1.. maxNrOfContextsOnUeList)) OF HS-DSCHRequiredPowerPerUEInformation-Item
HS-DSCHRequiredPowerPerUEInformation ::= SEQUENCE (SIZE (1.. 16)) OF HS-DSCHRequiredPowerPerUEInformation-Item


HS-DSCHRequiredPowerPerUEInformation-Item ::= SEQUENCE {
	cRNC-CommunicationContextID				CRNC-CommunicationContextID,
	hS-DSCHRequiredPowerPerUEWeight			HS-DSCHRequiredPowerPerUEWeight		OPTIONAL,
--	iE-Extensions							ProtocolExtensionContainer { { HS-DSCHRequiredPowerPerUEInformation-Item-ExtIEs} }		OPTIONAL,
	iE-Extensions							ProtocolExtensionContainer OPTIONAL,
	...
}

--HS-DSCHRequiredPowerPerUEInformation-Item-ExtIEs NBAP-PROTOCOL-EXTENSION ::= {
--	...
--}

HS-DSCHRequiredPowerPerUEWeight ::= INTEGER(0..100)
-- Unit %, Range 0 ..100, Step 1%

--HS-DSCHRequiredPowerValueInformation-For-CellPortion ::= SEQUENCE (SIZE (1..maxNrOfCellPortionsPerCell)) OF HS-DSCHRequiredPowerValueInformation-For-CellPortion-Item
HS-DSCHRequiredPowerValueInformation-For-CellPortion ::= SEQUENCE (SIZE (1..64)) OF HS-DSCHRequiredPowerValueInformation-For-CellPortion-Item

HS-DSCHRequiredPowerValueInformation-For-CellPortion-Item ::= SEQUENCE{
	cellPortionID				CellPortionID,
	hS-DSCHRequiredPowerValue	HS-DSCHRequiredPower,
--	iE-Extensions				ProtocolExtensionContainer { { HS-DSCHRequiredPowerValueInformation-For-CellPortion-Item-ExtIEs} }		OPTIONAL,
	iE-Extensions				ProtocolExtensionContainer OPTIONAL,
	...
}

--HS-DSCHRequiredPowerValueInformation-For-CellPortion-Item-ExtIEs NBAP-PROTOCOL-EXTENSION ::= {
--	...
--}

HSDSCH-FDD-Information ::= SEQUENCE {
	hSDSCH-MACdFlows-Information				HSDSCH-MACdFlows-Information,
	ueCapability-Info							UE-Capability-Information,
	mAChs-Reordering-Buffer-Size-for-RLC-UM		MAChsReorderingBufferSize-for-RLC-UM,
	cqiFeedback-CycleK							CQI-Feedback-Cycle,
	cqiRepetitionFactor							CQI-RepetitionFactor						OPTIONAL,
	-- This IE shall be present if the CQI Feedback Cycle k is greater than 0
	ackNackRepetitionFactor						AckNack-RepetitionFactor,
	cqiPowerOffset								CQI-Power-Offset,
	ackPowerOffset								Ack-Power-Offset,
	nackPowerOffset								Nack-Power-Offset,
	hsscch-PowerOffset							HSSCCH-PowerOffset							OPTIONAL,
	measurement-Power-Offset					Measurement-Power-Offset					OPTIONAL,
--	iE-Extensions								ProtocolExtensionContainer { { HSDSCH-FDD-Information-ExtIEs} }		OPTIONAL,
	iE-Extensions								ProtocolExtensionContainer OPTIONAL,
	...
}

--HSDSCH-FDD-Information-ExtIEs NBAP-PROTOCOL-EXTENSION ::= {
--	{ ID id-HARQ-Preamble-Mode 	CRITICALITY reject		EXTENSION	HARQ-Preamble-Mode	PRESENCE optional},
--	...
--}

HSDSCH-TDD-Information ::= SEQUENCE {
	hSDSCH-MACdFlows-Information				HSDSCH-MACdFlows-Information,
	ueCapability-Info							UE-Capability-Information,
	mAChs-Reordering-Buffer-Size-for-RLC-UM		MAChsReorderingBufferSize-for-RLC-UM,
	tDD-AckNack-Power-Offset					TDD-AckNack-Power-Offset,
--	iE-Extensions								ProtocolExtensionContainer { { HSDSCH-TDD-Information-ExtIEs} }		OPTIONAL,
	iE-Extensions								ProtocolExtensionContainer OPTIONAL,
	...
}

--HSDSCH-TDD-Information-ExtIEs NBAP-PROTOCOL-EXTENSION ::= {
--	...
--}


HSDSCH-Information-to-Modify ::= SEQUENCE {
	hsDSCH-MACdFlow-Specific-Info-to-Modify			HSDSCH-MACdFlow-Specific-InfoList-to-Modify		OPTIONAL,
	priorityQueueInfotoModify						PriorityQueue-InfoList-to-Modify				OPTIONAL,
	mAChs-Reordering-Buffer-Size-for-RLC-UM			MAChsReorderingBufferSize-for-RLC-UM			OPTIONAL,
	cqiFeedback-CycleK								CQI-Feedback-Cycle								OPTIONAL,	-- For FDD only
	cqiRepetitionFactor								CQI-RepetitionFactor							OPTIONAL,	-- For FDD only
	ackNackRepetitionFactor							AckNack-RepetitionFactor						OPTIONAL,	-- For FDD only
	cqiPowerOffset									CQI-Power-Offset								OPTIONAL,	-- For FDD only
	ackPowerOffset									Ack-Power-Offset								OPTIONAL,	-- For FDD only
	nackPowerOffset									Nack-Power-Offset								OPTIONAL,	-- For FDD only
	hsscch-PowerOffset								HSSCCH-PowerOffset								OPTIONAL,	-- For FDD only
	measurement-Power-Offset						Measurement-Power-Offset						OPTIONAL,	-- For FDD only
	hSSCCHCodeChangeGrant							HSSCCH-Code-Change-Grant						OPTIONAL,
	tDDAckNackPowerOffset							TDD-AckNack-Power-Offset						OPTIONAL,	-- For TDD only
--	iE-Extensions									ProtocolExtensionContainer { { HSDSCH-Information-to-Modify-ExtIEs} }		OPTIONAL,
	iE-Extensions									ProtocolExtensionContainer OPTIONAL,
	...
}

--HSDSCH-Information-to-Modify-ExtIEs NBAP-PROTOCOL-EXTENSION ::= {
--	{ ID id-HARQ-Preamble-Mode	CRITICALITY reject		EXTENSION	HARQ-Preamble-Mode	PRESENCE optional},
--	...
--}

--HSDSCH-MACdFlow-Specific-InfoList-to-Modify ::= SEQUENCE (SIZE (1..maxNrOfMACdFlows)) OF HSDSCH-MACdFlow-Specific-InfoItem-to-Modify
HSDSCH-MACdFlow-Specific-InfoList-to-Modify ::= SEQUENCE (SIZE (1..8)) OF HSDSCH-MACdFlow-Specific-InfoItem-to-Modify

HSDSCH-MACdFlow-Specific-InfoItem-to-Modify ::= SEQUENCE {
	hsDSCH-MACdFlow-ID					HSDSCH-MACdFlow-ID,
	allocationRetentionPriority			AllocationRetentionPriority					OPTIONAL,
	transportBearerRequestIndicator		TransportBearerRequestIndicator,
	bindingID							BindingID									OPTIONAL,
	transportLayerAddress				TransportLayerAddress						OPTIONAL,
--	iE-Extensions						ProtocolExtensionContainer { { HSDSCH-MACdFlow-Specific-InfoItem-to-Modify-ExtIEs} }		OPTIONAL,
	iE-Extensions						ProtocolExtensionContainer OPTIONAL,
	...
}

--HSDSCH-MACdFlow-Specific-InfoItem-to-Modify-ExtIEs NBAP-PROTOCOL-EXTENSION ::= {
--	...
--}

HSDSCH-Information-to-Modify-Unsynchronised ::= SEQUENCE {
	hsDSCH-MACdFlow-Specific-Info-to-Modify			HSDSCH-MACdFlow-Specific-InfoList-to-Modify		OPTIONAL,
	priorityQueueInfotoModifyUnsynchronised			PriorityQueue-InfoList-to-Modify-Unsynchronised	OPTIONAL,
	cqiPowerOffset									CQI-Power-Offset								OPTIONAL,	-- For FDD only
	ackPowerOffset									Ack-Power-Offset								OPTIONAL,	-- For FDD only
	nackPowerOffset									Nack-Power-Offset								OPTIONAL,	-- For FDD only
	hsscch-PowerOffset								HSSCCH-PowerOffset								OPTIONAL,	-- For FDD only
	tDDAckNackPowerOffset							TDD-AckNack-Power-Offset						OPTIONAL,	-- For TDD only
--	iE-Extensions									ProtocolExtensionContainer { { HSDSCH-Information-to-Modify-Unsynchronised-ExtIEs} }		OPTIONAL,
	iE-Extensions									ProtocolExtensionContainer OPTIONAL,
	...
}

--HSDSCH-Information-to-Modify-Unsynchronised-ExtIEs NBAP-PROTOCOL-EXTENSION ::= {
--	{ ID id-HARQ-Preamble-Mode	CRITICALITY reject		EXTENSION	HARQ-Preamble-Mode	PRESENCE optional},
--	...
--}

HSDSCH-FDD-Information-Response ::= SEQUENCE {
	hsDSCH-MACdFlow-Specific-InformationResp		HSDSCH-MACdFlow-Specific-InformationResp							OPTIONAL,
	hsSCCH-Specific-Information-ResponseFDD			HSSCCH-Specific-InformationRespListFDD								OPTIONAL,
	hARQ-MemoryPartitioning							HARQ-MemoryPartitioning												OPTIONAL,
--	iE-Extensions									ProtocolExtensionContainer { { HSDSCH-FDD-Information-Response-ExtIEs } }		OPTIONAL,
	iE-Extensions									ProtocolExtensionContainer OPTIONAL,
	...
}

--HSDSCH-FDD-Information-Response-ExtIEs NBAP-PROTOCOL-EXTENSION ::= {
--{	ID id-HARQ-Preamble-Mode-Activation-Indicator		CRITICALITY	ignore	EXTENSION	HARQ-Preamble-Mode-Activation-Indicator	PRESENCE	optional},
--	...
--}

HSDSCH-TDD-Information-Response ::= SEQUENCE {
	hsDSCH-MACdFlow-Specific-InformationResp		HSDSCH-MACdFlow-Specific-InformationResp	OPTIONAL,
	hsSCCH-Specific-Information-ResponseTDD			HSSCCH-Specific-InformationRespListTDD		OPTIONAL, -- Not Applicable to 1.28Mcps TDD
	hsSCCH-Specific-Information-ResponseTDDLCR		HSSCCH-Specific-InformationRespListTDDLCR	OPTIONAL, -- Not Applicable to 3.84Mcps TDD
	hARQ-MemoryPartitioning							HARQ-MemoryPartitioning						OPTIONAL,
--	iE-Extensions									ProtocolExtensionContainer { { HSDSCH-TDD-Information-Response-ExtIEs } }		OPTIONAL,
	iE-Extensions									ProtocolExtensionContainer OPTIONAL,
	...
}

--HSDSCH-TDD-Information-Response-ExtIEs NBAP-PROTOCOL-EXTENSION ::= {
--	...
--}

--HSDSCH-MACdFlow-Specific-InformationResp ::= SEQUENCE (SIZE (1..maxNrOfMACdFlows)) OF HSDSCH-MACdFlow-Specific-InformationResp-Item
HSDSCH-MACdFlow-Specific-InformationResp ::= SEQUENCE (SIZE (1..8)) OF HSDSCH-MACdFlow-Specific-InformationResp-Item

HSDSCH-MACdFlow-Specific-InformationResp-Item ::= SEQUENCE {
	hsDSCHMacdFlow-Id								HSDSCH-MACdFlow-ID,
	bindingID										BindingID					OPTIONAL,
	transportLayerAddress							TransportLayerAddress		OPTIONAL,
	hSDSCH-Initial-Capacity-Allocation				HSDSCH-Initial-Capacity-Allocation OPTIONAL,
--	iE-Extensions									ProtocolExtensionContainer { { HSDSCH-MACdFlow-Specific-InformationRespItem-ExtIEs } }		OPTIONAL,
	iE-Extensions									ProtocolExtensionContainer OPTIONAL,
	...
}

--HSDSCH-MACdFlow-Specific-InformationRespItem-ExtIEs NBAP-PROTOCOL-EXTENSION ::= {
--	...
--}

HSDSCH-MACdFlows-Information ::= SEQUENCE {
	hSDSCH-MACdFlow-Specific-Info					HSDSCH-MACdFlow-Specific-InfoList,
	priorityQueue-Info								PriorityQueue-InfoList,
--	iE-Extensions									ProtocolExtensionContainer { { HSDSCH-MACdFlows-Information-ExtIEs } }			OPTIONAL,
	iE-Extensions									ProtocolExtensionContainer OPTIONAL,
	...
}

--HSDSCH-MACdFlows-Information-ExtIEs NBAP-PROTOCOL-EXTENSION ::= {
--	...
--}

HSDSCH-MACdFlow-Specific-InfoList ::= SEQUENCE (SIZE (1..8)) OF HSDSCH-MACdFlow-Specific-InfoItem

HSDSCH-MACdFlow-Specific-InfoItem ::= SEQUENCE {
	hsDSCH-MACdFlow-ID					HSDSCH-MACdFlow-ID,
	allocationRetentionPriority			AllocationRetentionPriority,
	bindingID							BindingID					OPTIONAL,
	transportLayerAddress				TransportLayerAddress		OPTIONAL,
--	iE-Extensions						ProtocolExtensionContainer { { HSDSCH-MACdFlow-Specific-InfoItem-ExtIEs} }		OPTIONAL,
	iE-Extensions						ProtocolExtensionContainer OPTIONAL,
	...
}

--HSDSCH-MACdFlow-Specific-InfoItem-ExtIEs NBAP-PROTOCOL-EXTENSION ::= {
--	...
--}

HSDSCH-MACdFlows-to-Delete ::= SEQUENCE (SIZE (1..8)) OF HSDSCH-MACdFlows-to-Delete-Item

HSDSCH-MACdFlows-to-Delete-Item ::= SEQUENCE {
	hsDSCH-MACdFlow-ID					HSDSCH-MACdFlow-ID,
--	iE-Extensions						ProtocolExtensionContainer { { HSDSCH-MACdFlows-to-Delete-Item-ExtIEs} }		OPTIONAL,
	iE-Extensions						ProtocolExtensionContainer OPTIONAL,
	...
}

--HSDSCH-MACdFlows-to-Delete-Item-ExtIEs NBAP-PROTOCOL-EXTENSION ::= {
--	...
--}

HSSCCH-PowerOffset ::= INTEGER (0..255)
-- PowerOffset = -32 + offset * 0.25
-- Unit dB, Range -32dB .. +31.75dB, Step +0.25dB

--HSDSCH-Initial-Capacity-Allocation::= SEQUENCE (SIZE (1..maxNrOfPriorityQueues)) OF HSDSCH-Initial-Capacity-AllocationItem
HSDSCH-Initial-Capacity-Allocation::= SEQUENCE (SIZE (1..8)) OF HSDSCH-Initial-Capacity-AllocationItem

HSDSCH-Initial-Capacity-AllocationItem ::= SEQUENCE {
	schedulingPriorityIndicator		SchedulingPriorityIndicator,
	maximum-MACdPDU-Size			MACdPDU-Size,
	hSDSCH-InitialWindowSize		HSDSCH-InitialWindowSize,
--	iE-Extensions					ProtocolExtensionContainer { { HSDSCH-Initial-Capacity-AllocationItem-ExtIEs } } OPTIONAL,
	iE-Extensions					ProtocolExtensionContainer OPTIONAL,
	...
}

--HSDSCH-Initial-Capacity-AllocationItem-ExtIEs NBAP-PROTOCOL-EXTENSION ::= {
--	...
--}

HSDSCH-InitialWindowSize			::= INTEGER (1..255)
-- Number of MAC-d PDUs.

--HSSCCH-Specific-InformationRespListFDD ::= SEQUENCE (SIZE (1..maxNrOfHSSCCHCodes)) OF HSSCCH-Codes
HSSCCH-Specific-InformationRespListFDD ::= SEQUENCE (SIZE (1..4)) OF HSSCCH-Codes

HSSCCH-Codes ::= SEQUENCE {
	codeNumber										INTEGER (0..127),
--	iE-Extensions									ProtocolExtensionContainer { { HSSCCH-Specific-InformationRespItemFDD-ExtIEs } }		OPTIONAL,
	iE-Extensions									ProtocolExtensionContainer OPTIONAL,
	...
}

--HSSCCH-Specific-InformationRespItemFDD-ExtIEs NBAP-PROTOCOL-EXTENSION ::= {
--	...
--}

--HSSCCH-Specific-InformationRespListTDD ::= SEQUENCE (SIZE (1..maxNrOfHSSCCHCodes)) OF HSSCCH-Specific-InformationRespItemTDD
HSSCCH-Specific-InformationRespListTDD ::= SEQUENCE (SIZE (1..8)) OF HSSCCH-Specific-InformationRespItemTDD

HSSCCH-Specific-InformationRespItemTDD ::= SEQUENCE {
	timeslot										TimeSlot,
	midambleShiftAndBurstType						MidambleShiftAndBurstType,
	tDD-ChannelisationCode							TDD-ChannelisationCode,
	hSSICH-Info										HSSICH-Info,
--	iE-Extensions									ProtocolExtensionContainer { { HSSCCH-Specific-InformationRespItemTDD-ExtIEs } }			OPTIONAL,
	iE-Extensions									ProtocolExtensionContainer OPTIONAL,
	...
}

--HSSCCH-Specific-InformationRespItemTDD-ExtIEs NBAP-PROTOCOL-EXTENSION ::= {
--	...
--}

--HSSCCH-Specific-InformationRespListTDDLCR ::= SEQUENCE (SIZE (1..maxNrOfHSSCCHCodes)) OF HSSCCH-Specific-InformationRespItemTDDLCR
HSSCCH-Specific-InformationRespListTDDLCR ::= SEQUENCE (SIZE (1..8)) OF HSSCCH-Specific-InformationRespItemTDDLCR

HSSCCH-Specific-InformationRespItemTDDLCR ::= SEQUENCE {
	timeslotLCR									TimeSlotLCR,
	midambleShiftLCR							MidambleShiftLCR,
	first-TDD-ChannelisationCode					TDD-ChannelisationCode,
	second-TDD-ChannelisationCode			TDD-ChannelisationCode,
	hSSICH-InfoLCR								HSSICH-InfoLCR,
--	iE-Extensions								ProtocolExtensionContainer { { HSSCCH-Specific-InformationRespItemTDDLCR-ExtIEs } }			OPTIONAL,
	iE-Extensions								ProtocolExtensionContainer OPTIONAL,
	...
}

--HSSCCH-Specific-InformationRespItemTDDLCR-ExtIEs NBAP-PROTOCOL-EXTENSION ::= {
--	...
--}

HSSICH-Info ::= SEQUENCE {
	hsSICH-ID										HS-SICH-ID,
	timeslot										TimeSlot,
	midambleShiftAndBurstType						MidambleShiftAndBurstType,
	tDD-ChannelisationCode							TDD-ChannelisationCode,
--	iE-Extensions									ProtocolExtensionContainer { { HSSICH-Info-ExtIEs } }			OPTIONAL,
	iE-Extensions									ProtocolExtensionContainer OPTIONAL,
	...
}

--HSSICH-Info-ExtIEs NBAP-PROTOCOL-EXTENSION ::= {
--	...
--}

HSSICH-InfoLCR ::= SEQUENCE {
	hsSICH-ID										HS-SICH-ID,
	timeslotLCR										TimeSlotLCR,
	midambleShiftLCR								MidambleShiftLCR,
	tDD-ChannelisationCode						TDD-ChannelisationCode,
--	iE-Extensions									ProtocolExtensionContainer { { HSSICH-Info-LCR-ExtIEs } }			OPTIONAL,
	iE-Extensions									ProtocolExtensionContainer OPTIONAL,
	...
}

--HSSICH-Info-LCR-ExtIEs NBAP-PROTOCOL-EXTENSION ::= {
--	...
--}

HS-SICH-Reception-Quality-Value ::= SEQUENCE {
	failed-HS-SICH				HS-SICH-failed,
	missed-HS-SICH				HS-SICH-missed,
	total-HS-SICH				HS-SICH-total,
--	iE-Extensions				ProtocolExtensionContainer { { HS-SICH-Reception-Quality-Value-ExtIEs} } OPTIONAL,
	iE-Extensions				ProtocolExtensionContainer OPTIONAL,
	...
}

--HS-SICH-Reception-Quality-Value-ExtIEs NBAP-PROTOCOL-EXTENSION ::= {
--	...
--}

HS-SICH-failed ::= INTEGER (0..20)

HS-SICH-missed ::= INTEGER (0..20)

HS-SICH-total ::= INTEGER (0..20)

HS-SICH-Reception-Quality-Measurement-Value ::= INTEGER (0..20)
-- According to mapping in [23]

--HSDSCH-MACdFlow-ID ::= INTEGER (0..maxNrOfMACdFlows-1)
HSDSCH-MACdFlow-ID ::= INTEGER (0..7)

HSDSCH-RNTI ::= INTEGER (0..65535)

HS-PDSCH-FDD-Code-Information ::= SEQUENCE {
--	number-of-HS-PDSCH-codes						INTEGER (0..maxHS-PDSCHCodeNrComp-1),
	number-of-HS-PDSCH-codes						INTEGER (0..15),
	hS-PDSCH-Start-code-number 					HS-PDSCH-Start-code-number		OPTIONAL, 
-- Only included when number of HS-DSCH codes > 0
--	iE-Extensions				ProtocolExtensionContainer { { HS-PDSCH-FDD-Code-Information-ExtIEs} } OPTIONAL,
	iE-Extensions				ProtocolExtensionContainer OPTIONAL,
	...
}

--HS-PDSCH-FDD-Code-Information-ExtIEs NBAP-PROTOCOL-EXTENSION ::= {
--	...
--}

--HS-PDSCH-Start-code-number ::=	INTEGER (1..maxHS-PDSCHCodeNrComp-1)
HS-PDSCH-Start-code-number ::=	INTEGER (1..15)

HS-SCCH-ID ::= INTEGER (0..31)
HS-SICH-ID ::= INTEGER (0..31)

HS-SCCH-FDD-Code-Information::= CHOICE {
	replace					HS-SCCH-FDD-Code-List,
	remove					NULL,
	...
}

--HS-SCCH-FDD-Code-List ::= SEQUENCE (SIZE (1..maxNrOfHSSCCHs)) OF HS-SCCH-FDD-Code-Information-Item
HS-SCCH-FDD-Code-List ::= SEQUENCE (SIZE (1..32)) OF HS-SCCH-FDD-Code-Information-Item

--HS-SCCH-FDD-Code-Information-Item ::= INTEGER (0..maxHS-SCCHCodeNrComp-1)
HS-SCCH-FDD-Code-Information-Item ::= INTEGER (0..127)

HSSCCH-CodeChangeIndicator	::= ENUMERATED {
	hsSCCHCodeChangeNeeded
}

HSSCCH-Code-Change-Grant	::= ENUMERATED {
	changeGranted
}

HSDSCH-FDD-Update-Information ::= SEQUENCE {
	hsSCCHCodeChangeIndicator						HSSCCH-CodeChangeIndicator					OPTIONAL,
	cqiFeedback-CycleK								CQI-Feedback-Cycle							OPTIONAL, 
	cqiRepetitionFactor								CQI-RepetitionFactor						OPTIONAL,
	ackNackRepetitionFactor							AckNack-RepetitionFactor					OPTIONAL,
	cqiPowerOffset									CQI-Power-Offset 							OPTIONAL,
	ackPowerOffset									Ack-Power-Offset							OPTIONAL,
	nackPowerOffset									Nack-Power-Offset							OPTIONAL,
--	iE-Extensions									ProtocolExtensionContainer { { HSDSCH-FDD-Update-Information-ExtIEs } }		OPTIONAL,
	iE-Extensions									ProtocolExtensionContainer OPTIONAL,
	...
}

--HSDSCH-FDD-Update-Information-ExtIEs NBAP-PROTOCOL-EXTENSION ::= {
--	...
--}

HSDSCH-TDD-Update-Information ::= SEQUENCE {
	hsSCCHCodeChangeIndicator						HSSCCH-CodeChangeIndicator					OPTIONAL,
	tDDAckNackPowerOffset							TDD-AckNack-Power-Offset					OPTIONAL,
--	iE-Extensions									ProtocolExtensionContainer { { HSDSCH-TDD-Update-Information-ExtIEs } }		OPTIONAL,
	iE-Extensions									ProtocolExtensionContainer OPTIONAL,
	...
}

--HSDSCH-TDD-Update-Information-ExtIEs NBAP-PROTOCOL-EXTENSION ::= {
--	...
--}

-- ==========================================
--	I
-- ==========================================

IB-OC-ID ::= INTEGER (1..16)

IB-SG-DATA ::= BIT STRING
-- Contains SIB data fixed" or "SIB data variable" in segment as encoded in ref.[18].

IB-SG-POS ::= INTEGER (0..4094)
-- Only even positions allowed

IB-SG-REP ::= ENUMERATED {rep4, rep8, rep16, rep32, rep64, rep128, rep256, rep512, rep1024, rep2048, rep4096}

IB-Type ::= ENUMERATED {
	mIB, 
	sB1,
	sB2,
	sIB1, 
	sIB2,
	sIB3,
	sIB4,
	sIB5,
	sIB6,
	sIB7,
	sIB8,
	sIB9,
	sIB10,
	sIB11,
	sIB12,
	sIB13,
	sIB13dot1,
	sIB13dot2,
	sIB13dot3,
	sIB13dot4,
	sIB14,
	sIB15,
	sIB15dot1,
	sIB15dot2,
	sIB15dot3,
	sIB16,
	...,
	sIB17,
	sIB15dot4,
	sIB18,
	sIB15dot5,
	sIB5bis
}

InformationReportCharacteristics ::= CHOICE {
	onDemand				NULL,
	periodic				InformationReportCharacteristicsType-ReportPeriodicity,
	onModification          InformationReportCharacteristicsType-OnModification,
	...
}

InformationReportCharacteristicsType-ReportPeriodicity ::= CHOICE {
	min 				ReportPeriodicity-Scaledmin,
	hours				ReportPeriodicity-Scaledhour,
	...
}

InformationReportCharacteristicsType-OnModification ::= SEQUENCE {
    information-thresholds        InformationThresholds		OPTIONAL,
--  ie-Extensions		          ProtocolExtensionContainer { { InformationReportCharacteristicsType-OnModification-ExtIEs} }	OPTIONAL,
    ie-Extensions		          ProtocolExtensionContainer OPTIONAL,
   ...
}

--InformationReportCharacteristicsType-OnModification-ExtIEs NBAP-PROTOCOL-EXTENSION ::= {
--	...
--}

InformationThresholds ::= CHOICE {
    dgps                DGPSThresholds,
   	...
} 

InformationExchangeID ::= INTEGER (0..1048575)

InformationType ::= SEQUENCE {
	information-Type-Item		Information-Type-Item,
	gPSInformation  			GPS-Information  OPTIONAL,
	-- The IE shall be present if the Information Type Item IE indicates "GPS Information".
--	iE-Extensions				ProtocolExtensionContainer { { Information-Type-ExtIEs} }		OPTIONAL,
	iE-Extensions				ProtocolExtensionContainer OPTIONAL,
	...
}

--Information-Type-ExtIEs NBAP-PROTOCOL-EXTENSION ::= {
--	...
--}

Information-Type-Item ::= ENUMERATED {
    gpsinformation,
    dgpscorrections,
    gpsrxpos,
    ...
}

Initial-DL-DPCH-TimingAdjustment-Allowed ::= ENUMERATED {
	initial-DL-DPCH-TimingAdjustment-Allowed
}

InnerLoopDLPCStatus ::= ENUMERATED {
	active,
	inactive
}

IPDL-Indicator ::= ENUMERATED {
	active,
	inactive
}


IPDL-FDD-Parameters ::= SEQUENCE {
	iP-SpacingFDD					ENUMERATED{sp5,sp7,sp10,sp15,sp20,sp30,sp40,sp50,...},
	iP-Length						ENUMERATED{len5, len10},
	seed							INTEGER(0..63),
	burstModeParams					BurstModeParams		OPTIONAL,
	iP-Offset						INTEGER(0..9),
--	iE-Extensions					ProtocolExtensionContainer { { IPDLFDDParameter-ExtIEs} }	OPTIONAL,
	iE-Extensions					ProtocolExtensionContainer OPTIONAL,
	...
}

--IPDLFDDParameter-ExtIEs NBAP-PROTOCOL-EXTENSION ::= {
--	...
--}

IPDL-TDD-Parameters ::= SEQUENCE {
	iP-SpacingTDD					ENUMERATED{sp30,sp40,sp50,sp70,sp100,...},
	iP-Start						INTEGER(0..4095),
	iP-Slot							INTEGER(0..14),
	iP-PCCPCH						ENUMERATED{switchOff-1-Frame,switchOff-2-Frames},
	burstModeParams					BurstModeParams		OPTIONAL,
--	iE-Extensions			ProtocolExtensionContainer { { IPDLTDDParameter-ExtIEs} }	OPTIONAL,
	iE-Extensions			ProtocolExtensionContainer OPTIONAL,
	...
}

IPDL-TDD-Parameters-LCR ::= SEQUENCE {
	iP-SpacingTDD					ENUMERATED{sp30,sp40,sp50,sp70,sp100,...},
	iP-Start						INTEGER(0..4095),
	iP-Sub							ENUMERATED{first,second,both},
	burstModeParams					BurstModeParams		OPTIONAL,
--	iE-Extensions			ProtocolExtensionContainer { { IPDLTDDParameterLCR-ExtIEs} }	OPTIONAL,
	iE-Extensions			ProtocolExtensionContainer OPTIONAL,
	...
}

BurstModeParams ::= SEQUENCE {
	burstStart							INTEGER(0..15),
	burstLength							INTEGER(10..25),
	burstFreq							INTEGER(1..16),
	...
}

--IPDLTDDParameter-ExtIEs NBAP-PROTOCOL-EXTENSION ::= {
--	...
--}

--IPDLTDDParameterLCR-ExtIEs NBAP-PROTOCOL-EXTENSION ::= {
--	...
--}

-- ==========================================
--	J
-- ==========================================

-- ==========================================
--	K
-- ==========================================

-- ==========================================
--	L
-- ==========================================

LimitedPowerIncrease ::= ENUMERATED {
	used,
	not-used
}

Local-Cell-ID ::= INTEGER (0..268435455)

-- ==========================================
--	M
-- ==========================================

MACdPDU-Size ::= INTEGER (1..5000,...)

--MACdPDU-Size-Indexlist ::= SEQUENCE (SIZE (1..maxNrOfMACdPDUIndexes)) OF MACdPDU-Size-IndexItem
MACdPDU-Size-Indexlist ::= SEQUENCE (SIZE (1..8)) OF MACdPDU-Size-IndexItem

MACdPDU-Size-IndexItem ::= SEQUENCE {
	sID									SID,
	macdPDU-Size						MACdPDU-Size,
--	iE-Extensions						ProtocolExtensionContainer { { MACdPDU-Size-IndexItem-ExtIEs} }		OPTIONAL,
	iE-Extensions						ProtocolExtensionContainer OPTIONAL,
	...
}

--MACdPDU-Size-IndexItem-ExtIEs NBAP-PROTOCOL-EXTENSION ::= {
--	...
--}

--MACdPDU-Size-Indexlist-to-Modify ::= SEQUENCE (SIZE (1..maxNrOfMACdPDUIndexes)) OF MACdPDU-Size-IndexItem-to-Modify
MACdPDU-Size-Indexlist-to-Modify ::= SEQUENCE (SIZE (1..8)) OF MACdPDU-Size-IndexItem-to-Modify

MACdPDU-Size-IndexItem-to-Modify ::= SEQUENCE {
	sID									SID,
	macdPDU-Size						MACdPDU-Size,
--	iE-Extensions						ProtocolExtensionContainer { { MACdPDU-Size-IndexItem-to-Modify-ExtIEs} }		OPTIONAL,
	iE-Extensions						ProtocolExtensionContainer OPTIONAL,
	...
}

--MACdPDU-Size-IndexItem-to-Modify-ExtIEs NBAP-PROTOCOL-EXTENSION ::= {
--	...
--}

MACesGuaranteedBitRate ::= INTEGER (0..16777215,...)

MAChsGuaranteedBitRate ::= INTEGER (0..16777215,...)

MAChsReorderingBufferSize-for-RLC-UM ::= INTEGER (0..300,...)
-- Unit kBytes

MAC-hsWindowSize		::= ENUMERATED {v4, v6, v8, v12, v16, v24, v32,...}

MaximumDL-PowerCapability ::=  INTEGER(0..500)
-- Unit dBm, Range 0dBm .. 50dBm, Step +0.1dB

--Max-Bits-MACe-PDU-non-scheduled ::= INTEGER(1..maxNrOfBits-MACe-PDU-non-scheduled)
Max-Bits-MACe-PDU-non-scheduled ::= INTEGER(1..19982)

Maximum-Number-of-Retransmissions-For-E-DCH ::= INTEGER (0..15)

MaximumTransmissionPower ::=  INTEGER(0..500)
-- Unit dBm, Range 0dBm .. 50dBm, Step +0.1dB


MaxNrOfUL-DPDCHs ::= INTEGER (1..6)

MaxPRACH-MidambleShifts ::= ENUMERATED {
	shift4,
	shift8,
	...
}

Max-Set-E-DPDCHs ::= ENUMERATED {
	vN64, vN32, vN16, vN8, vN4, v2xN4, v2xN2, v2xN2plus2xN4,
	...
	}
-- Values related to [8]

MeasurementFilterCoefficient ::= ENUMERATED {k0, k1, k2, k3, k4, k5, k6, k7, k8, k9, k11, k13, k15, k17, k19,...}
-- Measurement Filter Coefficient to be used for measurement

MeasurementID ::= INTEGER (0..1048575)

Measurement-Power-Offset ::= INTEGER(-12 .. 26)
-- Actual value = IE value * 0.5

MeasurementRecoveryBehavior ::= NULL

MeasurementRecoveryReportingIndicator ::= NULL

MeasurementRecoverySupportIndicator ::= NULL

--MessageStructure ::= SEQUENCE (SIZE (1..maxNrOfLevels)) OF
--	SEQUENCE { 
--		iE-ID					ProtocolIE-ID,
--		repetitionNumber		RepetitionNumber1		OPTIONAL,
--		iE-Extensions			ProtocolExtensionContainer { {MessageStructure-ExtIEs} } OPTIONAL,
--		...
--	}

MessageStructure ::= SEQUENCE (SIZE (1..256)) OF
	SEQUENCE { 
		iE-ID					ProtocolIE-ID,
		repetitionNumber		RepetitionNumber1		OPTIONAL,
		iE-Extensions			ProtocolExtensionContainer OPTIONAL,
		...
	}

--MessageStructure-ExtIEs NBAP-PROTOCOL-EXTENSION ::= {
--	...
--}

MICH-CFN ::= INTEGER (0..4095)

MICH-Mode ::= ENUMERATED {
	v18,
	v36,
	v72,
	v144,
	...
}

MidambleConfigurationLCR ::=	ENUMERATED {v2, v4, v6, v8, v10, v12, v14, v16, ...}

MidambleConfigurationBurstType1And3 ::=		ENUMERATED {v4, v8, v16}

MidambleConfigurationBurstType2 ::=		ENUMERATED {v3, v6}

MidambleShiftAndBurstType ::=		CHOICE {	
	type1								SEQUENCE {
		midambleConfigurationBurstType1And3	MidambleConfigurationBurstType1And3,
		midambleAllocationMode 				CHOICE {
			defaultMidamble						NULL,
			commonMidamble						NULL,
			ueSpecificMidamble					MidambleShiftLong,
			...
		},
	...
	},
	type2								SEQUENCE {
		midambleConfigurationBurstType2		MidambleConfigurationBurstType2,
		midambleAllocationMode 				CHOICE {
			defaultMidamble						NULL,
			commonMidamble						NULL,
			ueSpecificMidamble					MidambleShiftShort,
			...
		},
		...
	},
	type3								SEQUENCE {
		midambleConfigurationBurstType1And3	MidambleConfigurationBurstType1And3,
		midambleAllocationMode 				CHOICE {
			defaultMidamble						NULL,
			ueSpecificMidamble					MidambleShiftLong,
		...
		},
		...
	},
	...
}

MidambleShiftLong ::=				INTEGER (0..15)

MidambleShiftShort ::=				INTEGER (0..5)

MidambleShiftLCR ::= SEQUENCE {
	midambleAllocationMode		MidambleAllocationMode,
	midambleShift				MidambleShiftLong		OPTIONAL,
	-- The IE shall be present if the Midamble Allocation Mode IE is set to "UE specific midamble".
	midambleConfigurationLCR		MidambleConfigurationLCR,
--	iE-Extensions				ProtocolExtensionContainer { {MidambleShiftLCR-ExtIEs} }		OPTIONAL,
	iE-Extensions				ProtocolExtensionContainer OPTIONAL,
	...
	}

MidambleAllocationMode ::= ENUMERATED {
	defaultMidamble,
	commonMidamble,
	uESpecificMidamble, 
	...
	}

--MidambleShiftLCR-ExtIEs  NBAP-PROTOCOL-EXTENSION ::= {
--	...
--}

MinimumDL-PowerCapability ::=  INTEGER(0..800)
-- Unit dBm, Range -30dBm .. 50dBm, Step +0.1dB

MinSpreadingFactor ::= ENUMERATED {
		v4,
		v8,
		v16,
		v32,
		v64,
		v128,
		v256,
		v512
}
--  TDD Mapping scheme for the minimum spreading factor 1 and 2: "256" means 1, "512" means 2

Modification-Period ::= ENUMERATED { v5120, v10240,...}

ModifyPriorityQueue ::= CHOICE {
	addPriorityQueue			PriorityQueue-InfoItem-to-Add,
	modifyPriorityQueue			PriorityQueue-InfoItem-to-Modify,
	deletePriorityQueue			PriorityQueue-Id,
	...
}

Modulation ::= ENUMERATED {
	qPSK,
	eightPSK,
	...
}

MinUL-ChannelisationCodeLength ::= ENUMERATED {
	v4,
	v8,
	v16,
	v32,
	v64,
	v128,
	v256,
	...
}

MultiplexingPosition ::= ENUMERATED {
	fixed,
	flexible
}

-- ==========================================
--	N
-- ==========================================
Nack-Power-Offset ::= INTEGER (0..8,...)
-- According to mapping in ref. [9] subclause 4.2.1

NCyclesPerSFNperiod ::= ENUMERATED {
	v1,
	v2,
	v4,
	v8,
	...,
	v16,
	v32,
	v64
}

NRepetitionsPerCyclePeriod ::= INTEGER (2..10)

N-INSYNC-IND ::= INTEGER (1..256)

N-OUTSYNC-IND ::= INTEGER (1..256)

--NeighbouringCellMeasurementInformation ::= SEQUENCE (SIZE (1..maxNrOfMeasNCell)) OF
--		CHOICE {
--				neighbouringFDDCellMeasurementInformation		NeighbouringFDDCellMeasurementInformation, 
				-- FDD only
--				neighbouringTDDCellMeasurementInformation		NeighbouringTDDCellMeasurementInformation,
				-- Applicable to 3.84Mcps TDD only
--				...,
--				extension-neighbouringCellMeasurementInformation	Extension-neighbouringCellMeasurementInformation
--			}

NeighbouringCellMeasurementInformation ::= SEQUENCE (SIZE (1..96)) OF
		CHOICE {
				neighbouringFDDCellMeasurementInformation		NeighbouringFDDCellMeasurementInformation, -- FDD only
				neighbouringTDDCellMeasurementInformation		NeighbouringTDDCellMeasurementInformation,
				-- Applicable to 3.84Mcps TDD only
				...,
				extension-neighbouringCellMeasurementInformation	Extension-neighbouringCellMeasurementInformation
			}

--Extension-neighbouringCellMeasurementInformation	::=	ProtocolIE-Single-Container {{ Extension-neighbouringCellMeasurementInformationIE }}
Extension-neighbouringCellMeasurementInformation	::=	ProtocolIE-Single-Container 


--Extension-neighbouringCellMeasurementInformationIE NBAP-PROTOCOL-IES ::= {
--	{ ID id-neighbouringTDDCellMeasurementInformationLCR	CRITICALITY reject	TYPE NeighbouringTDDCellMeasurementInformationLCR	PRESENCE mandatory },
	-- Applicable to 1.28Mcps TDD only
--	...
--}

NeighbouringFDDCellMeasurementInformation ::= SEQUENCE {
	uC-Id								UC-Id,
	uARFCN								UARFCN,
	primaryScramblingCode				PrimaryScramblingCode,
--	iE-Extensions						ProtocolExtensionContainer { { NeighbouringFDDCellMeasurementInformationItem-ExtIEs} } OPTIONAL,
	iE-Extensions						ProtocolExtensionContainer OPTIONAL,
	...
}

--NeighbouringFDDCellMeasurementInformationItem-ExtIEs NBAP-PROTOCOL-EXTENSION ::= {
--	...
--}

NeighbouringTDDCellMeasurementInformation ::= SEQUENCE {
	uC-Id								UC-Id,
	uARFCN								UARFCN,
	cellParameterID						CellParameterID,
	timeSlot							TimeSlot						OPTIONAL,
	midambleShiftAndBurstType			MidambleShiftAndBurstType		OPTIONAL,
--	iE-Extensions						ProtocolExtensionContainer { { NeighbouringTDDCellMeasurementInformationItem-ExtIEs} } OPTIONAL,
	iE-Extensions						ProtocolExtensionContainer OPTIONAL,
	...
}

--NeighbouringTDDCellMeasurementInformationItem-ExtIEs NBAP-PROTOCOL-EXTENSION ::= {
--	...
--}

NeighbouringTDDCellMeasurementInformationLCR ::= SEQUENCE {
	uC-Id								UC-Id,
	uARFCN								UARFCN,
	cellParameterID						CellParameterID,
	timeSlotLCR							TimeSlotLCR				OPTIONAL,
	midambleShiftLCR					MidambleShiftLCR		OPTIONAL,
--	iE-Extensions						ProtocolExtensionContainer { { NeighbouringTDDCellMeasurementInformationLCRItem-ExtIEs} } OPTIONAL,
	iE-Extensions						ProtocolExtensionContainer OPTIONAL,
	...
}

--NeighbouringTDDCellMeasurementInformationLCRItem-ExtIEs NBAP-PROTOCOL-EXTENSION ::= {
--	...
--}

--NI-Information ::= SEQUENCE (SIZE (1..maxNrOfNIs)) OF Notification-Indicator
NI-Information ::= SEQUENCE (SIZE (1..256)) OF Notification-Indicator

Notification-Indicator ::= INTEGER (0..65535)

NodeB-CommunicationContextID ::= INTEGER (0..1048575)

NotificationIndicatorLength ::= ENUMERATED {
	v2,
	v4,
	v8,
	...
}


--NumberOfReportedCellPortions ::= INTEGER (1..maxNrOfCellPortionsPerCell,...)
NumberOfReportedCellPortions ::= INTEGER (1..64,...)

NSubCyclesPerCyclePeriod ::= INTEGER (1..16,...)

-- ==========================================
--	O
-- ==========================================

-- ==========================================
--	P
-- ==========================================

PagingIndicatorLength ::= ENUMERATED {
	v2,
	v4,
	v8,
	...
}

PayloadCRC-PresenceIndicator ::= ENUMERATED {
	cRC-Included,
	cRC-NotIncluded,
	...
}

PCCPCH-Power ::= INTEGER (-150..400,...)
-- PCCPCH-power = power * 10
-- If power <= -15 PCCPCH shall be set to -150
-- If power >= 40 PCCPCH shall be set to 400
-- Unit dBm, Range -15dBm .. +40 dBm, Step +0.1dB

PDSCH-ID ::= INTEGER (0..255)

PDSCHSet-ID ::= INTEGER (0..255)

PICH-Mode ::= ENUMERATED {
	v18,
	v36,
	v72,
	v144,
	...
}

PICH-Power ::= INTEGER (-10..5)
-- Unit dB, Range -10dB .. +5dB, Step +1dB

PowerAdjustmentType ::= ENUMERATED {
	none,
	common,
	individual
}

PowerOffset ::= INTEGER (0..24)
-- PowerOffset = offset * 0.25
-- Unit dB, Range 0dB .. +6dB, Step +0.25dB

PowerRaiseLimit ::= INTEGER (0..10)

PRACH-Midamble ::= ENUMERATED {
	inverted,
	direct,
	...
}

PRC ::= INTEGER (-2047..2047)
--pseudo range correction; scaling factor 0.32 meters

PRCDeviation ::= ENUMERATED {
   one,
   two,
   five,
   ten,
   ...
}

PreambleSignatures ::= BIT STRING {
									signature15(0),
									signature14(1),
									signature13(2),
									signature12(3),
									signature11(4),
									signature10(5),
									signature9(6),
									signature8(7),
									signature7(8),
									signature6(9),
									signature5(10),
									signature4(11),
									signature3(12),
									signature2(13),
									signature1(14),
									signature0(15)
									} (SIZE (16))

PreambleThreshold ::= INTEGER (0..72)
-- 0= -36.0dB, 1= -35.5dB, ... , 72= 0.0dB

PredictedSFNSFNDeviationLimit ::=INTEGER (1..256)
-- Unit chip, Step 1/16 chip, Range 1/16..16 chip

PredictedTUTRANGPSDeviationLimit ::= INTEGER (1..256)
-- Unit chip, Step 1/16 chip, Range 1/16..16 chip

Pre-emptionCapability ::= ENUMERATED {
	shall-not-trigger-pre-emption,
	may-trigger-pre-emption
}

Pre-emptionVulnerability ::= ENUMERATED {
	not-pre-emptable,
	pre-emptable
}

PrimaryCPICH-Power ::= INTEGER(-100..500)
-- step 0.1 (Range –10.0..50.0) Unit is dBm

Primary-CPICH-Usage-for-Channel-Estimation ::= ENUMERATED {
primary-CPICH-may-be-used,
primary-CPICH-shall-not-be-used
}

PrimaryScramblingCode ::= INTEGER (0..511)

PriorityLevel				::= INTEGER (0..15)
-- 0 = spare, 1 = highest priority, ...14 = lowest priority and 15 = no priority

--PriorityQueue-Id ::= INTEGER (0..maxNrOfPriorityQueues-1)
PriorityQueue-Id ::= INTEGER (0..7)

--PriorityQueue-InfoList ::= SEQUENCE (SIZE (1..maxNrOfPriorityQueues)) OF PriorityQueue-InfoItem
PriorityQueue-InfoList ::= SEQUENCE (SIZE (1..8)) OF PriorityQueue-InfoItem

PriorityQueue-InfoItem ::= SEQUENCE {
	priorityQueueId						PriorityQueue-Id,
	associatedHSDSCH-MACdFlow			HSDSCH-MACdFlow-ID,
	schedulingPriorityIndicator			SchedulingPriorityIndicator,
	t1									T1,
	discardTimer						DiscardTimer				OPTIONAL,
	mAC-hsWindowSize					MAC-hsWindowSize,
	mAChsGuaranteedBitRate				MAChsGuaranteedBitRate										OPTIONAL,
	macdPDU-Size-Index					MACdPDU-Size-Indexlist,
	rLC-Mode							RLC-Mode,
--	iE-Extensions						ProtocolExtensionContainer { { PriorityQueue-InfoItem-ExtIEs} }		OPTIONAL,
	iE-Extensions						ProtocolExtensionContainer OPTIONAL,
	...
}

--PriorityQueue-InfoItem-ExtIEs NBAP-PROTOCOL-EXTENSION ::= {
--	...
--}

PriorityQueue-InfoList-to-Modify ::= SEQUENCE (SIZE (1..8)) OF ModifyPriorityQueue

PriorityQueue-InfoItem-to-Add ::= SEQUENCE {
	priorityQueueId						PriorityQueue-Id,
	associatedHSDSCH-MACdFlow			HSDSCH-MACdFlow-ID,
	schedulingPriorityIndicator			SchedulingPriorityIndicator,
	t1									T1,
	discardTimer						DiscardTimer												OPTIONAL,
	mAC-hsWindowSize					MAC-hsWindowSize,
	mAChsGuaranteedBitRate				MAChsGuaranteedBitRate										OPTIONAL,
	macdPDU-Size-Index					MACdPDU-Size-Indexlist,
	rLC-Mode							RLC-Mode,
--	iE-Extensions						ProtocolExtensionContainer { { PriorityQueue-InfoItem-to-Add-ExtIEs} }		OPTIONAL,
	iE-Extensions						ProtocolExtensionContainer OPTIONAL,
	...
}

--PriorityQueue-InfoItem-to-Add-ExtIEs NBAP-PROTOCOL-EXTENSION ::= {
--	...
--}

PriorityQueue-InfoItem-to-Modify ::= SEQUENCE {
	priorityQueueId						PriorityQueue-Id,
	schedulingPriorityIndicator			SchedulingPriorityIndicator									OPTIONAL,
	t1									T1															OPTIONAL,
	discardTimer						DiscardTimer												OPTIONAL,
	mAC-hsWindowSize					MAC-hsWindowSize											OPTIONAL,
	mAChsGuaranteedBitRate				MAChsGuaranteedBitRate										OPTIONAL,
	macdPDU-Size-Index-to-Modify		MACdPDU-Size-Indexlist-to-Modify							OPTIONAL,
--	iE-Extensions						ProtocolExtensionContainer { { PriorityQueue-InfoItem-to-Modify-ExtIEs} }		OPTIONAL,
	iE-Extensions						ProtocolExtensionContainer OPTIONAL,
	...
}

--PriorityQueue-InfoItem-to-Modify-ExtIEs NBAP-PROTOCOL-EXTENSION ::= {
--	...
--}

--PriorityQueue-InfoList-to-Modify-Unsynchronised ::= SEQUENCE (SIZE (1..maxNrOfPriorityQueues)) OF PriorityQueue-InfoItem-to-Modify-Unsynchronised
PriorityQueue-InfoList-to-Modify-Unsynchronised ::= SEQUENCE (SIZE (1..8)) OF PriorityQueue-InfoItem-to-Modify-Unsynchronised

PriorityQueue-InfoItem-to-Modify-Unsynchronised ::= SEQUENCE {
	priorityQueueId						PriorityQueue-Id,
	schedulingPriorityIndicator			SchedulingPriorityIndicator															OPTIONAL,
	discardTimer						DiscardTimer																		OPTIONAL,
	mAChsGuaranteedBitRate				MAChsGuaranteedBitRate																OPTIONAL,
--	iE-Extensions						ProtocolExtensionContainer { { PriorityQueue-InfoItem-to-Modify-Unsynchronised-ExtIEs} }		OPTIONAL,
	iE-Extensions						ProtocolExtensionContainer OPTIONAL,
	...
}

--PriorityQueue-InfoItem-to-Modify-Unsynchronised-ExtIEs NBAP-PROTOCOL-EXTENSION ::= {
--	...
--}

PrimaryCCPCH-RSCP ::= INTEGER (0..91)
-- Mapping of non-negative values according to [23]

PrimaryCCPCH-RSCP-Delta	::= INTEGER (-5..-1,...)
-- Mapping of negative values according to [23]

PropagationDelay ::= INTEGER (0..255)
-- Unit: chips, step size 3 chips
-- example: 0 = 0chip, 1 = 3chips

SCH-TimeSlot ::= INTEGER (0..6)

PunctureLimit ::= INTEGER (0..15)
-- 0: 40%; 1: 44%; ... 14: 96%; 15: 100%

PUSCH-ID ::= INTEGER (0..255)

PUSCHSet-ID ::= INTEGER (0..255)

-- ==========================================
--	Q
-- ==========================================

QE-Selector ::= ENUMERATED {
	selected,
	non-selected
}

-- ==========================================
--	R
-- ==========================================

RACH-SlotFormat ::= ENUMERATED {
	v0,
	v1,
	v2,
	v3,
	...
}

RACH-SubChannelNumbers ::= BIT STRING {
										subCh11(0),
										subCh10(1),
									 	subCh9(2),
									 	subCh8(3),
									 	subCh7(4),
									 	subCh6(5),
									 	subCh5(6),
									 	subCh4(7),
									 	subCh3(8),
									 	subCh2(9),
									 	subCh1(10),
									 	subCh0(11)
										} (SIZE (12))

--RL-Specific-DCH-Info ::= SEQUENCE (SIZE (1..maxNrOfDCHs)) OF RL-Specific-DCH-Info-Item
RL-Specific-DCH-Info ::= SEQUENCE (SIZE (1..128)) OF RL-Specific-DCH-Info-Item

RL-Specific-DCH-Info-Item ::= SEQUENCE {
	dCH-id					DCH-ID,
	bindingID				BindingID															OPTIONAL,
	transportlayeraddress	TransportLayerAddress												OPTIONAL,
--	iE-Extensions			ProtocolExtensionContainer { { RL-Specific-DCH-Info-Item-ExtIEs} }	OPTIONAL,
	iE-Extensions			ProtocolExtensionContainer OPTIONAL,
	...
}

--RL-Specific-DCH-Info-Item-ExtIEs NBAP-PROTOCOL-EXTENSION ::= {
--	...
--}

--RL-Specific-E-DCH-Info ::= SEQUENCE (SIZE (1..maxNrOfEDCHMACdFlows)) OF RL-Specific-E-DCH-Info-Item
RL-Specific-E-DCH-Info ::= SEQUENCE (SIZE (1..8)) OF RL-Specific-E-DCH-Info-Item

RL-Specific-E-DCH-Info-Item ::= SEQUENCE {
	e-DCH-MACdFlow-ID		E-DCH-MACdFlow-ID,
	bindingID				BindingID									OPTIONAL,
	transportlayeraddress	TransportLayerAddress						OPTIONAL,
--	iE-Extensions			ProtocolExtensionContainer { { RL-Specific-E-DCH-Info-Item-ExtIEs} }	OPTIONAL,
	iE-Extensions			ProtocolExtensionContainer OPTIONAL,
	...
}

--RL-Specific-E-DCH-Info-Item-ExtIEs NBAP-PROTOCOL-EXTENSION ::= {
--	...
--}

Range-Correction-Rate ::= INTEGER (-127..127)
-- scaling factor 0.032 m/s

Reference-ReceivedTotalWideBandPower ::= INTEGER (0..621)
-- mapping as for RTWP measurement value, as specified in [22]

ReferenceClockAvailability ::= ENUMERATED {
	available,
	notAvailable
}

ReferenceSFNoffset ::= INTEGER (0..255)

--Reference-E-TFCI-Information ::= SEQUENCE (SIZE (1..maxNrOfRefETFCIs)) OF Reference-E-TFCI-Information-Item
Reference-E-TFCI-Information ::= SEQUENCE (SIZE (1..8)) OF Reference-E-TFCI-Information-Item

Reference-E-TFCI-Information-Item ::= SEQUENCE {
	reference-E-TFCI				E-TFCI,
	reference-E-TFCI-PO				Reference-E-TFCI-PO,
--	iE-Extensions					ProtocolExtensionContainer { { Reference-E-TFCI-Information-Item-ExtIEs} }		OPTIONAL,
	iE-Extensions					ProtocolExtensionContainer OPTIONAL,
	...
}

--Reference-E-TFCI-Information-Item-ExtIEs NBAP-PROTOCOL-EXTENSION ::= {
--	...
--}

--Reference-E-TFCI-PO ::= INTEGER (0.. maxNrOfRefETFCI-PO-QUANTSTEPs)
Reference-E-TFCI-PO ::= INTEGER (0.. 29)
	-- FFS according to mapping in [21]

RepetitionLength ::= INTEGER (1..63)

RepetitionPeriod ::= ENUMERATED {
	v1,
	v2,
	v4,
	v8,
	v16,
	v32,
	v64,
	...
}

RepetitionNumber0 ::= INTEGER (0..255)

RepetitionNumber1 ::= INTEGER (1..256)

RefTFCNumber ::= INTEGER (0..3)

ReportCharacteristics ::= CHOICE {
	onDemand			NULL,
	periodic			ReportCharacteristicsType-ReportPeriodicity,
	event-a				ReportCharacteristicsType-EventA,
	event-b				ReportCharacteristicsType-EventB,
	event-c				ReportCharacteristicsType-EventC,
	event-d				ReportCharacteristicsType-EventD,
	event-e				ReportCharacteristicsType-EventE,
	event-f				ReportCharacteristicsType-EventF,
	...,
	extension-ReportCharacteristics		Extension-ReportCharacteristics
}

--Extension-ReportCharacteristics	::= ProtocolIE-Single-Container {{ Extension-ReportCharacteristicsIE }}
Extension-ReportCharacteristics	::= ProtocolIE-Single-Container


--Extension-ReportCharacteristicsIE NBAP-PROTOCOL-IES ::= {
--	{ ID id-ReportCharacteristicsType-OnModification	CRITICALITY reject	TYPE ReportCharacteristicsType-OnModification		PRESENCE mandatory }
--}

ReportCharacteristicsType-EventA ::= SEQUENCE {
	measurementThreshold			ReportCharacteristicsType-MeasurementThreshold,
	measurementHysteresisTime		ReportCharacteristicsType-ScaledMeasurementHysteresisTime			OPTIONAL,
--	iE-Extensions					ProtocolExtensionContainer { { ReportCharacteristicsType-EventA-ExtIEs} }		OPTIONAL,
	iE-Extensions					ProtocolExtensionContainer OPTIONAL,
	...
	}

--ReportCharacteristicsType-EventA-ExtIEs NBAP-PROTOCOL-EXTENSION ::= {
--	...
--}

ReportCharacteristicsType-EventB ::= SEQUENCE {
	measurementThreshold			ReportCharacteristicsType-MeasurementThreshold,
	measurementHysteresisTime		ReportCharacteristicsType-ScaledMeasurementHysteresisTime			OPTIONAL,
--	iE-Extensions					ProtocolExtensionContainer { { ReportCharacteristicsType-EventB-ExtIEs} }		OPTIONAL,
	iE-Extensions					ProtocolExtensionContainer OPTIONAL,
	...
	}

--ReportCharacteristicsType-EventB-ExtIEs NBAP-PROTOCOL-EXTENSION ::= {
--	...
--}

ReportCharacteristicsType-EventC ::= SEQUENCE {
	measurementIncreaseThreshold	ReportCharacteristicsType-MeasurementIncreaseDecreaseThreshold,
	measurementChangeTime			ReportCharacteristicsType-ScaledMeasurementChangeTime,
--	iE-Extensions					ProtocolExtensionContainer { { ReportCharacteristicsType-EventC-ExtIEs} }		OPTIONAL,
	iE-Extensions					ProtocolExtensionContainer OPTIONAL,
	...
	}

--ReportCharacteristicsType-EventC-ExtIEs NBAP-PROTOCOL-EXTENSION ::= {
--	...
--}

ReportCharacteristicsType-EventD ::= SEQUENCE {
	measurementDecreaseThreshold	ReportCharacteristicsType-MeasurementIncreaseDecreaseThreshold,
	measurementChangeTime			ReportCharacteristicsType-ScaledMeasurementChangeTime,
--	iE-Extensions					ProtocolExtensionContainer { { ReportCharacteristicsType-EventD-ExtIEs} }		OPTIONAL,
	iE-Extensions					ProtocolExtensionContainer OPTIONAL,
	...
	}

--ReportCharacteristicsType-EventD-ExtIEs NBAP-PROTOCOL-EXTENSION ::= {
--	...
--}

ReportCharacteristicsType-EventE ::= SEQUENCE {
	measurementThreshold1			ReportCharacteristicsType-MeasurementThreshold,
	measurementThreshold2			ReportCharacteristicsType-MeasurementThreshold				OPTIONAL,
	measurementHysteresisTime		ReportCharacteristicsType-ScaledMeasurementHysteresisTime	OPTIONAL,
	reportPeriodicity				ReportCharacteristicsType-ReportPeriodicity					OPTIONAL,
--	iE-Extensions					ProtocolExtensionContainer { { ReportCharacteristicsType-EventE-ExtIEs} }		OPTIONAL,
	iE-Extensions					ProtocolExtensionContainer OPTIONAL,
	...
	}

--ReportCharacteristicsType-EventE-ExtIEs NBAP-PROTOCOL-EXTENSION ::= {
--	...
--}

ReportCharacteristicsType-EventF ::= SEQUENCE {
	measurementThreshold1			ReportCharacteristicsType-MeasurementThreshold,
	measurementThreshold2			ReportCharacteristicsType-MeasurementThreshold				OPTIONAL,
	measurementHysteresisTime		ReportCharacteristicsType-ScaledMeasurementHysteresisTime	OPTIONAL,
	reportPeriodicity				ReportCharacteristicsType-ReportPeriodicity					OPTIONAL,
--	iE-Extensions					ProtocolExtensionContainer { { ReportCharacteristicsType-EventF-ExtIEs} }		OPTIONAL,
	iE-Extensions					ProtocolExtensionContainer OPTIONAL,
	...
	}

--ReportCharacteristicsType-EventF-ExtIEs NBAP-PROTOCOL-EXTENSION ::= {
--	...
--}

ReportCharacteristicsType-OnModification ::= SEQUENCE {
	measurementThreshold			ReportCharacteristicsType-MeasurementThreshold,
--	iE-Extensions					ProtocolExtensionContainer { { ReportCharacteristicsType-OnModification-ExtIEs} }		OPTIONAL,
	iE-Extensions					ProtocolExtensionContainer OPTIONAL,
		...
	}

--ReportCharacteristicsType-OnModification-ExtIEs NBAP-PROTOCOL-EXTENSION ::= {
--	...
--}

ReportCharacteristicsType-MeasurementIncreaseDecreaseThreshold ::= CHOICE {
	received-total-wide-band-power							Received-total-wide-band-power-Value-IncrDecrThres,
	transmitted-carrier-power		Transmitted-Carrier-Power-Value,
	acknowledged-prach-preambles			Acknowledged-PRACH-preambles-Value,
	uL-TimeslotISCP					UL-TimeslotISCP-Value-IncrDecrThres,
	sir							SIR-Value-IncrDecrThres,
	sir-error					SIR-Error-Value-IncrDecrThres,
	transmitted-code-power			Transmitted-Code-Power-Value-IncrDecrThres,
	rscp							RSCP-Value-IncrDecrThres,
	round-trip-time					Round-Trip-Time-IncrDecrThres,
	notUsed-1-acknowledged-PCPCH-access-preambles		NULL,
	notUsed-2-detected-PCPCH-access-preambles			NULL,
	...,
	extension-ReportCharacteristicsType-MeasurementIncreaseDecreaseThreshold		Extension-ReportCharacteristicsType-MeasurementIncreaseDecreaseThreshold
}

--Extension-ReportCharacteristicsType-MeasurementIncreaseDecreaseThreshold	::= ProtocolIE-Single-Container {{ Extension-ReportCharacteristicsType-MeasurementIncreaseDecreaseThresholdIE }}
Extension-ReportCharacteristicsType-MeasurementIncreaseDecreaseThreshold	::= ProtocolIE-Single-Container 

--Extension-ReportCharacteristicsType-MeasurementIncreaseDecreaseThresholdIE NBAP-PROTOCOL-IES ::= {
--{ ID id-TransmittedCarrierPowerOfAllCodesNotUsedForHSTransmission			CRITICALITY reject	TYPE TransmittedCarrierPowerOfAllCodesNotUsedForHSTransmissionValue PRESENCE mandatory}|
--{ ID id-Transmitted-Carrier-Power-For-CellPortion		CRITICALITY reject	TYPE Transmitted-Carrier-Power-Value		PRESENCE mandatory }|
--{ ID id-Received-total-wide-band-power-For-CellPortion	CRITICALITY reject	TYPE Received-total-wide-band-power-Value-IncrDecrThres		PRESENCE mandatory }|
--{ ID id-TransmittedCarrierPowerOfAllCodesNotUsedForHS-PDSCH-HS-SCCH-E-AGCH-E-RGCHOrE-HICHTransmissionCellPortion	CRITICALITY reject	TYPE TransmittedCarrierPowerOfAllCodesNotUsedForHSTransmissionValue		PRESENCE mandatory }|
--{ ID id-UpPTSInterferenceValue		CRITICALITY reject	TYPE 	UpPTSInterferenceValue		PRESENCE mandatory }
--}

ReportCharacteristicsType-MeasurementThreshold ::= CHOICE {
	received-total-wide-band-power							Received-total-wide-band-power-Value,
	transmitted-carrier-power		Transmitted-Carrier-Power-Value,
	acknowledged-prach-preambles			Acknowledged-PRACH-preambles-Value,
	uL-TimeslotISCP					UL-TimeslotISCP-Value,
	sir							SIR-Value,
	sir-error					SIR-Error-Value,
	transmitted-code-power			Transmitted-Code-Power-Value,
	rscp							RSCP-Value,
	rx-timing-deviation				Rx-Timing-Deviation-Value,
	round-trip-time					Round-Trip-Time-Value,
	notUsed-1-acknowledged-PCPCH-access-preambles		NULL,
	notUsed-2-detected-PCPCH-access-preambles			NULL,
	...,
	extension-ReportCharacteristicsType-MeasurementThreshold		Extension-ReportCharacteristicsType-MeasurementThreshold
}

--Extension-ReportCharacteristicsType-MeasurementThreshold	::= ProtocolIE-Single-Container {{ Extension-ReportCharacteristicsType-MeasurementThresholdIE }}
Extension-ReportCharacteristicsType-MeasurementThreshold	::= ProtocolIE-Single-Container


--Extension-ReportCharacteristicsType-MeasurementThresholdIE NBAP-PROTOCOL-IES ::= {
--	{ ID id-TUTRANGPSMeasurementThresholdInformation	CRITICALITY reject	TYPE TUTRANGPSMeasurementThresholdInformation		PRESENCE mandatory }|
--	{ ID id-SFNSFNMeasurementThresholdInformation		CRITICALITY reject	TYPE SFNSFNMeasurementThresholdInformation			PRESENCE mandatory }|
--	{ ID id-Rx-Timing-Deviation-Value-LCR				CRITICALITY reject	TYPE Rx-Timing-Deviation-Value-LCR				PRESENCE mandatory}|
--	{ ID id-HS-SICH-Reception-Quality-Measurement-Value	CRITICALITY reject	TYPE HS-SICH-Reception-Quality-Measurement-Value	PRESENCE mandatory}|
--	{ ID id-TransmittedCarrierPowerOfAllCodesNotUsedForHSTransmission CRITICALITY reject	TYPE TransmittedCarrierPowerOfAllCodesNotUsedForHSTransmissionValue PRESENCE mandatory}|
--	{ ID id-HS-DSCHRequiredPowerValue					CRITICALITY reject	TYPE HS-DSCHRequiredPowerValue				PRESENCE mandatory}|
--	{ ID id-Transmitted-Carrier-Power-For-CellPortion	CRITICALITY reject	TYPE Transmitted-Carrier-Power-Value				PRESENCE mandatory }|
--	{ ID id-Received-total-wide-band-power-For-CellPortion	CRITICALITY reject	TYPE Received-total-wide-band-power-Value 	PRESENCE mandatory }|
--	{ ID id-TransmittedCarrierPowerOfAllCodesNotUsedForHS-PDSCH-HS-SCCH-E-AGCH-E-RGCHOrE-HICHTransmissionCellPortion	 CRITICALITY reject	TYPE TransmittedCarrierPowerOfAllCodesNotUsedForHSTransmissionValue		PRESENCE mandatory }|
--	{ ID id-UpPTSInterferenceValue						CRITICALITY reject	TYPE UpPTSInterferenceValue				PRESENCE mandatory }|
--	{ ID id-DLTransmissionBranchLoadValue				CRITICALITY reject	TYPE DLTransmissionBranchLoadValue					PRESENCE mandatory }|
--	{ ID id-HS-DSCHRequiredPowerValue-For-Cell-Portion	CRITICALITY reject	TYPE HS-DSCHRequiredPowerValue							PRESENCE mandatory }
--}

ReportCharacteristicsType-ScaledMeasurementChangeTime ::= CHOICE {
	msec				MeasurementChangeTime-Scaledmsec,
	...
}

MeasurementChangeTime-Scaledmsec ::= INTEGER (1..6000,...)
-- MeasurementChangeTime-Scaledmsec = Time * 10
-- Unit ms, Range 10ms .. 60000ms(1min), Step 10ms

ReportCharacteristicsType-ScaledMeasurementHysteresisTime ::= CHOICE {
	msec				MeasurementHysteresisTime-Scaledmsec,
	...
}

MeasurementHysteresisTime-Scaledmsec ::= INTEGER (1..6000,...)
-- MeasurementHysteresisTime-Scaledmsec = Time * 10
-- Unit ms, Range 10ms .. 60000ms(1min), Step 10ms

ReportCharacteristicsType-ReportPeriodicity ::= CHOICE {
	msec 				ReportPeriodicity-Scaledmsec,
	min					ReportPeriodicity-Scaledmin,
	...
}

ReportPeriodicity-Scaledmsec ::= INTEGER (1..6000,...)
-- ReportPeriodicity-msec = ReportPeriodicity * 10
-- Unit ms, Range 10ms .. 60000ms(1min), Step 10ms

ReportPeriodicity-Scaledmin ::= INTEGER (1..60,...)
-- Unit min, Range 1min .. 60min(hour), Step 1min

ReportPeriodicity-Scaledhour ::= INTEGER (1..24,...)
-- Unit hour, Range 1hour .. 24hours(day), Step 1hour

ResourceOperationalState ::= ENUMERATED {
	enabled,
	disabled
}

RL-ID ::= INTEGER (0..31)

RL-Set-ID				::= INTEGER (0..31)

RLC-Mode	::= ENUMERATED {
	rLC-AM,
	rLC-UM,
	...
}

Round-Trip-Time-IncrDecrThres ::= INTEGER(0..32766)

RNC-ID					::= INTEGER (0..4095)

Round-Trip-Time-Value ::= INTEGER(0..32767)
-- According to mapping in [22]

RSCP-Value ::= INTEGER (0..127)
-- According to mapping in [23]

RSCP-Value-IncrDecrThres ::= INTEGER (0..126)

--Received-total-wide-band-power-For-CellPortion-Value ::= SEQUENCE (SIZE (1..maxNrOfCellPortionsPerCell)) OF Received-total-wide-band-power-For-CellPortion-Value-Item
Received-total-wide-band-power-For-CellPortion-Value ::= SEQUENCE (SIZE (1..64)) OF Received-total-wide-band-power-For-CellPortion-Value-Item

Received-total-wide-band-power-For-CellPortion-Value-Item ::= SEQUENCE{
	cellPortionID							CellPortionID, 
	received-total-wide-band-power-value	Received-total-wide-band-power-Value,
--	iE-Extensions							ProtocolExtensionContainer { { Received-total-wide-band-power-For-CellPortion-Value-Item-ExtIEs} }		OPTIONAL,
	iE-Extensions							ProtocolExtensionContainer OPTIONAL,
...
}

--Received-total-wide-band-power-For-CellPortion-Value-Item-ExtIEs NBAP-PROTOCOL-EXTENSION ::= {
--	...
--}

Received-total-wide-band-power-Value ::= INTEGER(0..621)
-- According to mapping in [22]/[23]

Received-total-wide-band-power-Value-IncrDecrThres ::= INTEGER (0..620)

RequestedDataValueInformation ::= CHOICE {
	informationAvailable		InformationAvailable,
	informationnotAvailable		InformationnotAvailable
}

InformationAvailable::= SEQUENCE {
	requesteddataValue		RequestedDataValue,
--	ie-Extensions			ProtocolExtensionContainer { { InformationAvailableItem-ExtIEs} }		OPTIONAL,
	ie-Extensions			ProtocolExtensionContainer OPTIONAL,
	...
}

--InformationAvailableItem-ExtIEs NBAP-PROTOCOL-EXTENSION ::= {
--	...
--}

InformationnotAvailable ::= NULL

RequestedDataValue ::= SEQUENCE {
	dgps-corrections		DGPSCorrections													OPTIONAL,
	gps-navandrecovery		GPS-NavigationModel-and-TimeRecovery								OPTIONAL,
	gps-ionos-model			GPS-Ionospheric-Model												OPTIONAL,
	gps-utc-model			GPS-UTC-Model													OPTIONAL,
	gps-almanac				GPS-Almanac														OPTIONAL,
	gps-rt-integrity		GPS-RealTime-Integrity											OPTIONAL,
	gpsrxpos				GPS-RX-POS														OPTIONAL,
--	iE-Extensions			ProtocolExtensionContainer { { RequestedDataValue-ExtIEs} }		OPTIONAL,
	iE-Extensions			ProtocolExtensionContainer OPTIONAL,
	...
}

--RequestedDataValue-ExtIEs NBAP-PROTOCOL-EXTENSION ::= {
--	...
--}

Rx-Timing-Deviation-Value ::= INTEGER (0..8191)
-- According to mapping in [23]

Rx-Timing-Deviation-Value-LCR ::= INTEGER (0..511)
-- According to mapping in [23]

-- ==========================================
--	S
-- ==========================================

AdjustmentPeriod			::= INTEGER(1..256)
-- Unit Frame

SAT-ID ::= INTEGER (0..63) 

--SAT-Info-Almanac ::= SEQUENCE (SIZE (1..maxNoSat)) OF SAT-Info-Almanac-Item
SAT-Info-Almanac ::= SEQUENCE (SIZE (1..16)) OF SAT-Info-Almanac-Item

SAT-Info-Almanac-Item ::= SEQUENCE {
	data-id			   DATA-ID,
    sat-id             SAT-ID,
    gps-e-alm          BIT STRING (SIZE (16)),
    gps-toa-alm        BIT STRING (SIZE (8)),     
    gps-delta-I-alm    BIT STRING (SIZE (16)),
    omegadot-alm       BIT STRING (SIZE (16)),
    svhealth-alm       BIT STRING (SIZE (8)),
    gps-a-sqrt-alm     BIT STRING (SIZE (24)),
    omegazero-alm      BIT STRING (SIZE (24)),
    m-zero-alm         BIT STRING (SIZE (24)),
    gps-omega-alm      BIT STRING (SIZE (24)),
    gps-af-zero-alm    BIT STRING (SIZE (11)),
    gps-af-one-alm     BIT STRING (SIZE (11)),
--    ie-Extensions	   ProtocolExtensionContainer { { SAT-Info-Almanac-Item-ExtIEs} }		OPTIONAL,
    ie-Extensions	   ProtocolExtensionContainer OPTIONAL,
   ...
}	-- This GPS-Almanac-Information is for the 1st 16 satellites

--SAT-Info-Almanac-Item-ExtIEs NBAP-PROTOCOL-EXTENSION ::= {
--	...
--} 

--SAT-Info-Almanac-ExtList	::= SEQUENCE (SIZE (1..maxNrOfSatAlmanac-maxNoSat)) OF SAT-Info-Almanac-ExtItem
SAT-Info-Almanac-ExtList	::= SEQUENCE (SIZE (1..16)) OF SAT-Info-Almanac-ExtItem

SAT-Info-Almanac-ExtItem	::= SEQUENCE {
	data-id			   DATA-ID,
    sat-id             SAT-ID,
    gps-e-alm          BIT STRING (SIZE (16)),
    gps-toa-alm        BIT STRING (SIZE (8)),     
    gps-delta-I-alm    BIT STRING (SIZE (16)),
    omegadot-alm       BIT STRING (SIZE (16)),
    svhealth-alm       BIT STRING (SIZE (8)),
    gps-a-sqrt-alm     BIT STRING (SIZE (24)),
    omegazero-alm      BIT STRING (SIZE (24)),
    m-zero-alm         BIT STRING (SIZE (24)),
    gps-omega-alm      BIT STRING (SIZE (24)),
    gps-af-zero-alm    BIT STRING (SIZE (11)),
    gps-af-one-alm     BIT STRING (SIZE (11)),
--    ie-Extensions	   ProtocolExtensionContainer { { SAT-Info-Almanac-ExtItemIEs } }		OPTIONAL,
    ie-Extensions	   ProtocolExtensionContainer OPTIONAL,
   ...
}	--	Includes the GPS-Almanac-Information for 17th through 32nd satellites.

--SAT-Info-Almanac-ExtItemIEs NBAP-PROTOCOL-EXTENSION ::= {
--	...
--}

--SAT-Info-DGPSCorrections ::= SEQUENCE (SIZE (1..maxNoSat)) OF SAT-Info-DGPSCorrections-Item
SAT-Info-DGPSCorrections ::= SEQUENCE (SIZE (1..16)) OF SAT-Info-DGPSCorrections-Item

SAT-Info-DGPSCorrections-Item ::= SEQUENCE {
    sat-id                                	SAT-ID,
    iode-dgps                           	BIT STRING (SIZE (8)),
    udre            						UDRE,
    prc             						PRC,
    range-correction-rate             		Range-Correction-Rate,
--    ie-Extensions							ProtocolExtensionContainer { { SAT-Info-DGPSCorrections-Item-ExtIEs} }  OPTIONAL,
    ie-Extensions							ProtocolExtensionContainer OPTIONAL,
   ...
}

--SAT-Info-DGPSCorrections-Item-ExtIEs NBAP-PROTOCOL-EXTENSION ::= {
--	...
--}

--SATInfo-RealTime-Integrity ::= SEQUENCE (SIZE (1..maxNoSat)) OF SAT-Info-RealTime-Integrity-Item
SATInfo-RealTime-Integrity ::= SEQUENCE (SIZE (1..16)) OF SAT-Info-RealTime-Integrity-Item

SAT-Info-RealTime-Integrity-Item ::= SEQUENCE {
  bad-sat-id       SAT-ID,
--  ie-Extensions	   ProtocolExtensionContainer { { SAT-Info-RealTime-Integrity-Item-ExtIEs} }		OPTIONAL,
  ie-Extensions	   ProtocolExtensionContainer OPTIONAL,
   ...
}

--SAT-Info-RealTime-Integrity-Item-ExtIEs NBAP-PROTOCOL-EXTENSION ::= {
--	...
--}

ScaledAdjustmentRatio			::= INTEGER(0..100)
-- AdjustmentRatio  = ScaledAdjustmentRatio / 100

MaxAdjustmentStep			::= INTEGER(1..10)
-- Unit Slot

SchedulingPriorityIndicator 			::= INTEGER (0..15)		 -- lowest (0), highest (15)

--SID ::= INTEGER (0..maxNrOfMACdPDUIndexes-1)
SID ::= INTEGER (0..7)

ScramblingCodeNumber ::= INTEGER (0..15)

Secondary-CPICH-Information-Change ::= CHOICE {
	new-secondary-CPICH					CommonPhysicalChannelID,
	secondary-CPICH-shall-not-be-used	NULL,
...
}

SecondaryCCPCH-SlotFormat ::= INTEGER(0..17,...)

Segment-Type ::= ENUMERATED {
		first-segment, 
		first-segment-short,
		subsequent-segment,
		last-segment, 
		last-segment-short, 
		complete-SIB, 
		complete-SIB-short,
		...
}

Serving-E-DCH-RL-ID ::= CHOICE {
	serving-E-DCH-RL-in-this-NodeB				Serving-E-DCH-RL-in-this-NodeB,
	serving-E-DCH-RL-not-in-this-NodeB			NULL,
	...
}

Serving-E-DCH-RL-in-this-NodeB ::= SEQUENCE {
	rL-ID										RL-ID,
--	iE-Extensions								ProtocolExtensionContainer { { Serving-E-DCH-RL-in-this-NodeB-ExtIEs} }			OPTIONAL,
	iE-Extensions								ProtocolExtensionContainer OPTIONAL,
	...
}

--Serving-E-DCH-RL-in-this-NodeB-ExtIEs NBAP-PROTOCOL-EXTENSION ::= {
--	...
--}

SFN ::= INTEGER (0..4095)

SFNSFN-FDD ::= INTEGER (0..614399)

SFNSFN-TDD ::= INTEGER (0..40961) 

SFNSFNChangeLimit ::= INTEGER (1..256)
-- Unit chip, Step 1/16 chip, Range 1/16..16 chip

SFNSFNDriftRate ::= INTEGER (-100..100)
-- Unit chip/s, Step 1/256 chip/s, Range -100/256..+100/256 chip/s

SFNSFNDriftRateQuality ::= INTEGER (0..100)
-- Unit chip/s, Step 1/256 chip/s, Range 0..100/256 chip/s

SFNSFNMeasurementThresholdInformation::= SEQUENCE {
	sFNSFNChangeLimit					SFNSFNChangeLimit					OPTIONAL,
	predictedSFNSFNDeviationLimit		PredictedSFNSFNDeviationLimit		OPTIONAL,
--	iE-Extensions					ProtocolExtensionContainer { { SFNSFNMeasurementThresholdInformation-ExtIEs} }		OPTIONAL,
	iE-Extensions					ProtocolExtensionContainer OPTIONAL,
	...
}

--SFNSFNMeasurementThresholdInformation-ExtIEs NBAP-PROTOCOL-EXTENSION ::= {
--	...
--}

SFNSFNMeasurementValueInformation ::= SEQUENCE {
	successfullNeighbouringCellSFNSFNObservedTimeDifferenceMeasurementInformation		SEQUENCE (SIZE(1..96)) OF
		SEQUENCE {
			uC-Id						UC-Id,
			sFNSFNValue					SFNSFNValue,
			sFNSFNQuality				SFNSFNQuality				OPTIONAL,
			sFNSFNDriftRate				SFNSFNDriftRate,
			sFNSFNDriftRateQuality		SFNSFNDriftRateQuality		OPTIONAL,
			sFNSFNTimeStampInformation	SFNSFNTimeStampInformation,
--			iE-Extensions		ProtocolExtensionContainer { { SuccessfullNeighbouringCellSFNSFNObservedTimeDifferenceMeasurementInformationItem-ExtIEs} }		OPTIONAL,
			iE-Extensions		ProtocolExtensionContainer OPTIONAL,
			...
		},
--	unsuccessfullNeighbouringCellSFNSFNObservedTimeDifferenceMeasurementInformation		SEQUENCE (SIZE(0..maxNrOfMeasNCell-1)) OF
	unsuccessfullNeighbouringCellSFNSFNObservedTimeDifferenceMeasurementInformation		SEQUENCE (SIZE(0..95)) OF
		SEQUENCE {
			uC-Id						UC-Id,
--			iE-Extensions		ProtocolExtensionContainer { { UnsuccessfullNeighbouringCellSFNSFNObservedTimeDifferenceMeasurementInformationItem-ExtIEs} }		OPTIONAL,
			iE-Extensions		ProtocolExtensionContainer OPTIONAL,
				...
		},
--	iE-Extensions		ProtocolExtensionContainer { { SFNSFNMeasurementValueInformationItem-ExtIEs} }		OPTIONAL,
	iE-Extensions		ProtocolExtensionContainer OPTIONAL,
	...
}

--SFNSFNMeasurementValueInformationItem-ExtIEs NBAP-PROTOCOL-EXTENSION ::= {
--	...
--}

--SuccessfullNeighbouringCellSFNSFNObservedTimeDifferenceMeasurementInformationItem-ExtIEs NBAP-PROTOCOL-EXTENSION ::= {
--	...
--}

--UnsuccessfullNeighbouringCellSFNSFNObservedTimeDifferenceMeasurementInformationItem-ExtIEs NBAP-PROTOCOL-EXTENSION ::= {
--	...
--}

SFNSFNQuality ::= INTEGER (0..255)
-- Unit chip, Step 1/16 chip, Range 0.. 255/16 chip

ShutdownTimer ::= INTEGER (1..3600)
-- Unit sec

SIB-Originator ::= ENUMERATED {
	nodeB, 
	cRNC,
	...
}

SIR-Error-Value ::= INTEGER (0..125)
-- According to mapping in [22]

SFNSFNTimeStampInformation ::= CHOICE {
	sFNSFNTimeStamp-FDD		SFN,
	sFNSFNTimeStamp-TDD		SFNSFNTimeStamp-TDD,
	...}

SFNSFNTimeStamp-TDD::= SEQUENCE {
	sFN					SFN,
	timeSlot			TimeSlot,
--	iE-Extensions					ProtocolExtensionContainer { { SFNSFNTimeStamp-ExtIEs} }		OPTIONAL,
	iE-Extensions					ProtocolExtensionContainer OPTIONAL,
	...
}

--SFNSFNTimeStamp-ExtIEs NBAP-PROTOCOL-EXTENSION ::= {
--	...
--}

SFNSFNValue ::= CHOICE {
	sFNSFN-FDD		SFNSFN-FDD,
	sFNSFN-TDD		SFNSFN-TDD,
	...
}

SIR-Error-Value-IncrDecrThres ::= INTEGER (0..124)

SIR-Value ::= INTEGER (0..63)
-- According to mapping in [22]/[23]

SIR-Value-IncrDecrThres ::= INTEGER (0..62)

SignallingBearerRequestIndicator::= ENUMERATED {bearerRequested}

SpecialBurstScheduling ::= INTEGER (1..256)	-- Number of frames between special burst transmission during DTX

Start-Of-Audit-Sequence-Indicator ::= ENUMERATED {
	start-of-audit-sequence,
	not-start-of-audit-sequence
}

STTD-Indicator ::= ENUMERATED {
	active,
	inactive,
	...
}

SSDT-SupportIndicator ::= ENUMERATED {
	not-Used-sSDT-Supported,
	sSDT-not-supported
}

SyncCase ::= INTEGER (1..2,...)

SYNCDlCodeId ::= INTEGER (1..32,...)

SyncFrameNumber ::= INTEGER (1..10)

SynchronisationReportCharacteristics ::= SEQUENCE {
	synchronisationReportCharacteristicsType	SynchronisationReportCharacteristicsType,
	synchronisationReportCharactThreExc			SynchronisationReportCharactThreExc		OPTIONAL,
		-- This IE shall be included if the synchronisationReportCharacteristicsType IE is set to “thresholdExceeding”.
--	iE-Extensions								ProtocolExtensionContainer { { SynchronisationReportCharacteristics-ExtIEs } }	OPTIONAL,
	iE-Extensions								ProtocolExtensionContainer OPTIONAL,
	...
}

--SynchronisationReportCharacteristics-ExtIEs	NBAP-PROTOCOL-EXTENSION ::= {
--	{ ID id-SyncDLCodeIdThreInfoLCR	CRITICALITY	ignore EXTENSION	SyncDLCodeIdThreInfoLCR		PRESENCE optional },
--	...
--}

--SynchronisationReportCharactThreExc ::= 	SEQUENCE (SIZE (1..maxNrOfCellSyncBursts)) OF SynchronisationReportCharactThreInfoItem  
	-- Mandatory for 3.84Mcps TDD only. Not Applicable to 1.28Mcps TDD.
SynchronisationReportCharactThreExc ::= 	SEQUENCE (SIZE (1..10)) OF SynchronisationReportCharactThreInfoItem  -- Mandatory for 3.84Mcps TDD only. Not Applicable to 1.28Mcps TDD.

SynchronisationReportCharactThreInfoItem ::= SEQUENCE {
	syncFrameNumber				SyncFrameNumber,
--	cellSyncBurstInformation	SEQUENCE (SIZE (1.. maxNrOfReceptsPerSyncFrame)) OF SynchronisationReportCharactCellSyncBurstInfoItem,
--	iE-Extensions				ProtocolExtensionContainer { { SynchronisationReportCharactThreInfoItem-ExtIEs } }		OPTIONAL,
	cellSyncBurstInformation	SEQUENCE (SIZE (1.. 16)) OF SynchronisationReportCharactCellSyncBurstInfoItem,
	iE-Extensions				ProtocolExtensionContainer OPTIONAL,
	...
}

--SynchronisationReportCharactThreInfoItem-ExtIEs NBAP-PROTOCOL-EXTENSION ::= {
--	...
--}

SynchronisationReportCharactCellSyncBurstInfoItem ::= SEQUENCE {
	cellSyncBurstCode 				CellSyncBurstCode,
	cellSyncBurstCodeShift 			CellSyncBurstCodeShift,
	cellSyncBurstTiming 			CellSyncBurstTiming				OPTIONAL,
	cellSyncBurstTimingThreshold 	CellSyncBurstTimingThreshold	OPTIONAL,
--	iE-Extensions					ProtocolExtensionContainer { { SynchronisationReportCharactCellSyncBurstInfoItem-ExtIEs } }		OPTIONAL,
	iE-Extensions					ProtocolExtensionContainer OPTIONAL,
	...
}

--SynchronisationReportCharactCellSyncBurstInfoItem-ExtIEs NBAP-PROTOCOL-EXTENSION ::= {
--	...
--}

--SyncDLCodeIdThreInfoLCR ::= SEQUENCE (SIZE (0..maxNrOfSyncFramesLCR)) OF SyncDLCodeIdThreInfoList  
	--Mandatory for 1.28Mcps TDD only. Not Applicable to 3.84Mcps TDD.
SyncDLCodeIdThreInfoLCR ::= SEQUENCE (SIZE (0..512)) OF SyncDLCodeIdThreInfoList  
	--Mandatory for 1.28Mcps TDD only. Not Applicable to 3.84Mcps TDD.

SyncDLCodeIdThreInfoList ::= SEQUENCE {
	syncFrameNoToReceive			SyncFrameNumber,
	syncDLCodeIdInfoLCR				SyncDLCodeInfoListLCR,
--	iE-Extensions					ProtocolExtensionContainer { { SyncDLCodeIdThreInfoList-ExtIEs } }		OPTIONAL,
	iE-Extensions					ProtocolExtensionContainer OPTIONAL,
	...
}

--SyncDLCodeIdThreInfoList-ExtIEs NBAP-PROTOCOL-EXTENSION ::= {
--	...
--}

--SyncDLCodeInfoListLCR ::= SEQUENCE (SIZE (1..maxNrOfSyncDLCodesLCR)) OF SyncDLCodeInfoItemLCR
SyncDLCodeInfoListLCR ::= SEQUENCE (SIZE (1..32)) OF SyncDLCodeInfoItemLCR

SyncDLCodeInfoItemLCR ::= SEQUENCE {
	syncDLCodeId					SYNCDlCodeId,
	syncDLCodeIdArrivTime			CellSyncBurstTimingLCR				OPTIONAL,
	syncDLCodeIdTimingThre			CellSyncBurstTimingThreshold		OPTIONAL,
--	iE-Extensions					ProtocolExtensionContainer { { SyncDLCodeInfoItem-LCR-ExtIEs } }		OPTIONAL,
	iE-Extensions					ProtocolExtensionContainer OPTIONAL,
	...
}

--SyncDLCodeInfoItem-LCR-ExtIEs NBAP-PROTOCOL-EXTENSION ::= {
--	...
--}

SynchronisationReportCharacteristicsType ::= ENUMERATED {
	frameRelated,
	sFNperiodRelated,
	cycleLengthRelated,
	thresholdExceeding,
	frequencyAcquisitionCompleted,
	...
}

SynchronisationReportType ::= ENUMERATED {
	initialPhase,
	steadyStatePhase,
	lateEntrantCell,
	frequencyAcquisition,
	...
}

-- ==========================================
--	T
-- ==========================================

T1 ::= ENUMERATED {v10,v20,v30,v40,v50,v60,v70,v80,v90,v100,v120,v140,v160,v200,v300,v400,...}

T-Cell ::= ENUMERATED {
	v0,
	v1,
	v2,
	v3,
	v4,
	v5,
	v6,
	v7,
	v8,
	v9
}

T-RLFAILURE ::= INTEGER (0..255)
-- Unit seconds, Range 0s .. 25.5s, Step 0.1s

TDD-AckNack-Power-Offset ::= INTEGER (-7..8,...)
-- Unit dB, Range –7dB .. +8dB, Step 1dB

TDD-ChannelisationCode ::= ENUMERATED {
	chCode1div1,
	chCode2div1,
	chCode2div2,
	chCode4div1,
	chCode4div2,
	chCode4div3,
	chCode4div4,
	chCode8div1,
	chCode8div2,
	chCode8div3,
	chCode8div4,
	chCode8div5,
	chCode8div6,
	chCode8div7,
	chCode8div8,
	chCode16div1,
	chCode16div2,
	chCode16div3,
	chCode16div4,
	chCode16div5,
	chCode16div6,
	chCode16div7,
	chCode16div8,
	chCode16div9,
	chCode16div10,
	chCode16div11,
	chCode16div12,
	chCode16div13,
	chCode16div14,
	chCode16div15,
	chCode16div16,
	...
}

TDD-ChannelisationCodeLCR ::= SEQUENCE {
	tDD-ChannelisationCode			TDD-ChannelisationCode,
	modulation						Modulation, -- Modulation options for 1.28Mcps TDD in contrast to 3.84Mcps TDD
--	iE-Extensions							ProtocolExtensionContainer { { TDD-ChannelisationCodeLCR-ExtIEs} }		OPTIONAL,
	iE-Extensions							ProtocolExtensionContainer OPTIONAL,
	...
}

--TDD-ChannelisationCodeLCR-ExtIEs NBAP-PROTOCOL-EXTENSION ::= {
--	...
--}

--TDD-DL-Code-Information ::= SEQUENCE (SIZE (1..maxNrOfDPCHs)) OF TDD-DL-Code-InformationItem
TDD-DL-Code-Information ::= SEQUENCE (SIZE (1..240)) OF TDD-DL-Code-InformationItem

TDD-DL-Code-InformationItem	 ::= SEQUENCE {
	dPCH-ID									DPCH-ID,
	tdd-ChannelisationCode					TDD-ChannelisationCode,
--	iE-Extensions							ProtocolExtensionContainer { { TDD-DL-Code-InformationItem-ExtIEs} }		OPTIONAL,
	iE-Extensions							ProtocolExtensionContainer OPTIONAL,
	...
}

--TDD-DL-Code-InformationItem-ExtIEs NBAP-PROTOCOL-EXTENSION ::= {
--	...
--}

--TDD-DL-Code-LCR-Information ::= SEQUENCE (SIZE (1..maxNrOfDPCHLCRs)) OF TDD-DL-Code-LCR-InformationItem
TDD-DL-Code-LCR-Information ::= SEQUENCE (SIZE (1..240)) OF TDD-DL-Code-LCR-InformationItem

TDD-DL-Code-LCR-InformationItem ::= SEQUENCE {
	dPCH-ID									DPCH-ID,
	tdd-ChannelisationCodeLCR				TDD-ChannelisationCodeLCR,
	tdd-DL-DPCH-TimeSlotFormat-LCR			TDD-DL-DPCH-TimeSlotFormat-LCR,
--	iE-Extensions							ProtocolExtensionContainer { { TDD-DL-Code-LCR-InformationItem-ExtIEs} }		OPTIONAL,
	iE-Extensions							ProtocolExtensionContainer OPTIONAL,
	...
}

--TDD-DL-Code-LCR-InformationItem-ExtIEs NBAP-PROTOCOL-EXTENSION ::= {
--	...
--}

TDD-DL-DPCH-TimeSlotFormat-LCR ::= CHOICE {
	qPSK						QPSK-DL-DPCH-TimeSlotFormatTDD-LCR,
	eightPSK					EightPSK-DL-DPCH-TimeSlotFormatTDD-LCR,
	...
}

QPSK-DL-DPCH-TimeSlotFormatTDD-LCR ::= INTEGER(0..24,...)

EightPSK-DL-DPCH-TimeSlotFormatTDD-LCR ::= INTEGER(0..24,...)

TDD-DPCHOffset ::= CHOICE {
	initialOffset		INTEGER (0..255),
	noinitialOffset		INTEGER (0..63)
}

TDD-PhysicalChannelOffset ::= INTEGER (0..63)

TDD-TPC-DownlinkStepSize ::= ENUMERATED {
	step-size1,
	step-size2,
	step-size3,
	...
}

TDD-TPC-UplinkStepSize-LCR ::= ENUMERATED {
	step-size1,
	step-size2,
	step-size3,
	...
}

TransportFormatCombination-Beta ::= CHOICE {
	signalledGainFactors		SEQUENCE {
		gainFactor					CHOICE {
			fdd							SEQUENCE {
				betaC						BetaCD,
				betaD						BetaCD,
--				iE-Extensions		ProtocolExtensionContainer { { GainFactorFDD-ExtIEs } }		OPTIONAL,
				iE-Extensions		ProtocolExtensionContainer OPTIONAL,
				...
			},
			tdd							BetaCD,
			...
		},
	    refTFCNumber				RefTFCNumber	OPTIONAL,
--		iE-Extensions			ProtocolExtensionContainer { { SignalledGainFactors-ExtIEs } }		OPTIONAL,
		iE-Extensions			ProtocolExtensionContainer OPTIONAL,
		...
	},
	computedGainFactors				RefTFCNumber,
	...
}

--GainFactorFDD-ExtIEs NBAP-PROTOCOL-EXTENSION ::= {
--	...
--}

--SignalledGainFactors-ExtIEs NBAP-PROTOCOL-EXTENSION ::= {
--	...
--}

--TDD-UL-Code-Information ::= SEQUENCE (SIZE (1..maxNrOfDPCHs)) OF TDD-UL-Code-InformationItem
TDD-UL-Code-Information ::= SEQUENCE (SIZE (1..240)) OF TDD-UL-Code-InformationItem

TDD-UL-Code-InformationItem ::= SEQUENCE {
	dPCH-ID									DPCH-ID,
	tdd-ChannelisationCode					TDD-ChannelisationCode,
--	iE-Extensions							ProtocolExtensionContainer { { TDD-UL-Code-InformationItem-ExtIEs} }		OPTIONAL,
	iE-Extensions							ProtocolExtensionContainer OPTIONAL,
	...
}

--TDD-UL-Code-InformationItem-ExtIEs NBAP-PROTOCOL-EXTENSION ::= {
--	...
--}

--TDD-UL-Code-LCR-Information ::= SEQUENCE (SIZE (1..maxNrOfDPCHLCRs)) OF TDD-UL-Code-LCR-InformationItem
TDD-UL-Code-LCR-Information ::= SEQUENCE (SIZE (1..240)) OF TDD-UL-Code-LCR-InformationItem

TDD-UL-Code-LCR-InformationItem ::= SEQUENCE {
	dPCH-ID									DPCH-ID,
	tdd-ChannelisationCodeLCR				TDD-ChannelisationCodeLCR,
	tdd-UL-DPCH-TimeSlotFormat-LCR			TDD-UL-DPCH-TimeSlotFormat-LCR,
--	iE-Extensions							ProtocolExtensionContainer { { TDD-UL-Code-LCR-InformationItem-ExtIEs} }		OPTIONAL,
	iE-Extensions							ProtocolExtensionContainer OPTIONAL,
	...
}

--TDD-UL-Code-LCR-InformationItem-ExtIEs NBAP-PROTOCOL-EXTENSION ::= {
--	...
--}

TDD-UL-DPCH-TimeSlotFormat-LCR ::= CHOICE {
	qPSK						QPSK-UL-DPCH-TimeSlotFormatTDD-LCR,
	eightPSK					EightPSK-UL-DPCH-TimeSlotFormatTDD-LCR,
	...
}

QPSK-UL-DPCH-TimeSlotFormatTDD-LCR ::= INTEGER(0..69,...)

EightPSK-UL-DPCH-TimeSlotFormatTDD-LCR ::= INTEGER(0..24,...)

TFCI-Coding ::= ENUMERATED {
	v4,
	v8,
	v16,
	v32,
	...
}

TFCI-Presence ::= ENUMERATED {
	present,
	not-present
}

TFCI-SignallingMode ::= SEQUENCE {
	tFCI-SignallingOption		TFCI-SignallingMode-TFCI-SignallingOption,
	not-Used-splitType			NULL				OPTIONAL,
	not-Used-lengthOfTFCI2		NULL				OPTIONAL,
--	iE-Extensions				ProtocolExtensionContainer { { TFCI-SignallingMode-ExtIEs} }		OPTIONAL,
	iE-Extensions				ProtocolExtensionContainer OPTIONAL,
	...
}

--TFCI-SignallingMode-ExtIEs NBAP-PROTOCOL-EXTENSION ::= {
--	...
--}

TFCI-SignallingMode-TFCI-SignallingOption ::= ENUMERATED {
	normal,
	not-Used-split
}
-- FIX ME
--TGD					::= INTEGER (0|15..269)
TGD					::= INTEGER (15..269)
-- 0 = Undefined, only one transmission gap in the transmission gap pattern sequence 

TGPRC 				::= INTEGER (0..511)
-- 0 = infinity

TGPSID				::= INTEGER (1.. 6)

TGSN				::= INTEGER (0..14)

TimeSlot ::= INTEGER (0..14)

TimeSlotDirection ::= ENUMERATED {
	ul,
	dl,
	...
}

TimeSlotLCR ::= INTEGER (0..6)

TimeSlotStatus ::= ENUMERATED {
	active,
	not-active,
	...
}

TimingAdjustmentValue ::= CHOICE {
	initialPhase		INTEGER (0..1048575,...),
	steadyStatePhase	INTEGER (0..255,...)
}

TimingAdjustmentValueLCR ::= CHOICE {
	initialPhase		INTEGER (0..524287,...),
	steadyStatePhase	INTEGER (0..127,...)
}

TimingAdvanceApplied ::= ENUMERATED {
	yes,
	no
}

SynchronisationIndicator ::= ENUMERATED {
	timingMaintainedSynchronisation,
	...
}

TnlQos ::= CHOICE {
	dsField					DsField,
	genericTrafficCategory	GenericTrafficCategory,
	...
}

ToAWE ::= INTEGER (0..2559)
-- Unit ms

ToAWS ::= INTEGER (0..1279)
-- Unit ms

Transmission-Gap-Pattern-Sequence-Information ::= SEQUENCE (SIZE (1..6)) OF
	SEQUENCE {
		tGPSID			TGPSID,
		tGSN			TGSN,
		tGL1			GapLength,
		tGL2			GapLength	OPTIONAL,
		tGD				TGD,
		tGPL1			GapDuration,
		not-to-be-used-1			GapDuration	OPTIONAL,
			-- This IE shall never be included in the SEQUENCE. If received it shall be ignored
		uL-DL-mode		UL-DL-mode,
		downlink-Compressed-Mode-Method		Downlink-Compressed-Mode-Method		OPTIONAL,
			-- This IE shall be present if the UL/DL mode IE is set to "DL only" or "UL/DL"
		uplink-Compressed-Mode-Method		Uplink-Compressed-Mode-Method		OPTIONAL,
			-- This IE shall be present if the UL/DL mode IE is set to "UL only" or "UL/DL"
		dL-FrameType		DL-FrameType,
		delta-SIR1			DeltaSIR,
		delta-SIR-after1	DeltaSIR,
		delta-SIR2			DeltaSIR	OPTIONAL,
		delta-SIR-after2	DeltaSIR	OPTIONAL,
--		iE-Extensions			ProtocolExtensionContainer { {Transmission-Gap-Pattern-Sequence-Information-ExtIEs} } OPTIONAL,
		iE-Extensions			ProtocolExtensionContainer OPTIONAL,
		...
	}

--Transmission-Gap-Pattern-Sequence-Information-ExtIEs NBAP-PROTOCOL-EXTENSION ::= {
--	...
--}

TransmissionGapPatternSequenceCodeInformation	::= ENUMERATED{
code-change,
nocode-change
}

--TransmittedCarrierPowerOfAllCodesNotUsedForHS-PDSCH-HS-SCCH-E-AGCH-E-RGCHOrE-HICHTransmissionCellPortionValue ::= SEQUENCE (SIZE (1..maxNrOfCellPortionsPerCell)) OF TransmittedCarrierPowerOfAllCodesNotUsedForHS-PDSCH-HS-SCCH-E-AGCH-E-RGCHOrE-HICHTransmissionCellPortionValue-Item
TransmittedCarrierPowerOfAllCodesNotUsedForHS-PDSCH-HS-SCCH-E-AGCH-E-RGCHOrE-HICHTransmissionCellPortionValue ::= SEQUENCE (SIZE (1..64)) OF TransmittedCarrierPowerOfAllCodesNotUsedForHS-PDSCH-HS-SCCH-E-AGCH-E-RGCHOrE-HICHTransmissionCellPortionValue-Item

TransmittedCarrierPowerOfAllCodesNotUsedForHS-PDSCH-HS-SCCH-E-AGCH-E-RGCHOrE-HICHTransmissionCellPortionValue-Item ::= SEQUENCE{
	cellPortionID							CellPortionID,
	transmittedCarrierPowerOfAllCodesNotUsedForHSTransmissionValue	TransmittedCarrierPowerOfAllCodesNotUsedForHSTransmissionValue,
--	iE-Extensions							ProtocolExtensionContainer { { TransmittedCarrierPowerOfAllCodesNotUsedForHS-PDSCH-HS-SCCH-E-AGCH-E-RGCHOrE-HICHTransmissionCellPortionValue-Item-ExtIEs} }		OPTIONAL,
	iE-Extensions							ProtocolExtensionContainer OPTIONAL,
	...
}

--TransmittedCarrierPowerOfAllCodesNotUsedForHS-PDSCH-HS-SCCH-E-AGCH-E-RGCHOrE-HICHTransmissionCellPortionValue-Item-ExtIEs NBAP-PROTOCOL-EXTENSION ::= {
--	...
--}

TransmittedCarrierPowerOfAllCodesNotUsedForHSTransmissionValue ::= INTEGER(0..100)
-- According to mapping in [22] and [23]

--Transmitted-Carrier-Power-For-CellPortion-Value ::= SEQUENCE (SIZE (1..maxNrOfCellPortionsPerCell)) OF Transmitted-Carrier-Power-For-CellPortion-Value-Item
Transmitted-Carrier-Power-For-CellPortion-Value ::= SEQUENCE (SIZE (1..64)) OF Transmitted-Carrier-Power-For-CellPortion-Value-Item

Transmitted-Carrier-Power-For-CellPortion-Value-Item ::= SEQUENCE{
	cellPortionID							CellPortionID, 
	transmitted-Carrier-Power-Value			Transmitted-Carrier-Power-Value,
--	iE-Extensions							ProtocolExtensionContainer { { Transmitted-Carrier-Power-For-CellPortion-Value-Item-ExtIEs} }		OPTIONAL,
	iE-Extensions							ProtocolExtensionContainer OPTIONAL,
	...
}

--Transmitted-Carrier-Power-For-CellPortion-Value-Item-ExtIEs NBAP-PROTOCOL-EXTENSION ::= {
--	...
--}

Transmitted-Carrier-Power-Value ::= INTEGER(0..100)
-- According to mapping in [22]/[23]

Transmitted-Code-Power-Value ::= INTEGER (0..127)
-- According to mapping in [22]/[23]. Values 0 to 9 and 123 to 127 shall not be used.

Transmitted-Code-Power-Value-IncrDecrThres ::= INTEGER (0..112,...)

TransmissionDiversityApplied ::= BOOLEAN
-- true: applied, false: not applied

TransmitDiversityIndicator ::= ENUMERATED {
	active,
	inactive
}

TFCS ::= SEQUENCE {
	tFCSvalues					CHOICE {
		no-Split-in-TFCI			TFCS-TFCSList,
		not-Used-split-in-TFCI		NULL,
		-- This choice shall never be made by the CRNC and the Node B shall consider the procedure as failed if it is received.
		...
	},
--	iE-Extensions		ProtocolExtensionContainer  { { TFCS-ExtIEs} }		OPTIONAL,
	iE-Extensions		ProtocolExtensionContainer  OPTIONAL,
	...
}

--TFCS-ExtIEs NBAP-PROTOCOL-EXTENSION ::= {
--	...
--}

TFCS-TFCSList ::= SEQUENCE (SIZE (1..1024)) OF
	SEQUENCE {
		cTFC				TFCS-CTFC,
		tFC-Beta		TransportFormatCombination-Beta 	OPTIONAL,
		-- The IE shall be present if the TFCS concerns a UL DPCH or PRACH channel [FDD – or PCPCH channel].
--		iE-Extensions		ProtocolExtensionContainer  { { TFCS-TFCSList-ExtIEs} }		OPTIONAL,
		iE-Extensions		ProtocolExtensionContainer  OPTIONAL,
		...
}

--TFCS-TFCSList-ExtIEs NBAP-PROTOCOL-EXTENSION ::= {
--	...
--}

TFCS-CTFC ::= CHOICE {
	ctfc2bit							INTEGER (0..3),
	ctfc4bit							INTEGER (0..15),
	ctfc6bit							INTEGER (0..63),
	ctfc8bit							INTEGER (0..255),
	ctfc12bit							INTEGER (0..4095),
	ctfc16bit							INTEGER (0..65535),
	ctfcmaxbit							INTEGER (0..16777215)
}


TransportBearerRequestIndicator ::= ENUMERATED {
	bearerRequested,
	bearerNotRequested,
	...
}

TransportFormatSet ::= SEQUENCE {
	dynamicParts			TransportFormatSet-DynamicPartList,
	semi-staticPart			TransportFormatSet-Semi-staticPart,
--	iE-Extensions			ProtocolExtensionContainer  { { TransportFormatSet-ExtIEs} }		OPTIONAL,
	iE-Extensions			ProtocolExtensionContainer OPTIONAL,
	...
}

--TransportFormatSet-ExtIEs NBAP-PROTOCOL-EXTENSION ::= {
--	...
--}

--TransportFormatSet-DynamicPartList ::= SEQUENCE (SIZE (1..maxNrOfTFs)) OF
TransportFormatSet-DynamicPartList ::= SEQUENCE (SIZE (1..32)) OF
	SEQUENCE {
		nrOfTransportBlocks			TransportFormatSet-NrOfTransportBlocks,
		transportBlockSize			TransportFormatSet-TransportBlockSize		OPTIONAL,
		-- This IE shall be present if the Number of Transport Blocks IE is set to a value greater than 0
		mode						TransportFormatSet-ModeDP,
--		iE-Extensions				ProtocolExtensionContainer  { { TransportFormatSet-DynamicPartList-ExtIEs} }		OPTIONAL,
		iE-Extensions				ProtocolExtensionContainer OPTIONAL,
		...
	}

--TransportFormatSet-DynamicPartList-ExtIEs NBAP-PROTOCOL-EXTENSION ::= {
--	...
--}

TDD-TransportFormatSet-ModeDP ::= SEQUENCE {
	transmissionTimeIntervalInformation		TransmissionTimeIntervalInformation		OPTIONAL,
	-- This IE shall be present if the Transmission Time Interval IE in the Semi-static Transport Format Information IE is set to “dynamic”
--	iE-Extensions							ProtocolExtensionContainer { {TDD-TransportFormatSet-ModeDP-ExtIEs} } OPTIONAL,
	iE-Extensions							ProtocolExtensionContainer OPTIONAL,
	...
	}

--TDD-TransportFormatSet-ModeDP-ExtIEs NBAP-PROTOCOL-EXTENSION ::= {
--	...
--}

TransmissionTimeIntervalInformation ::= SEQUENCE (SIZE (1..4)) OF
	SEQUENCE {
		transmissionTimeInterval		TransportFormatSet-TransmissionTimeIntervalDynamic,
--	iE-Extensions						ProtocolExtensionContainer { { TransmissionTimeIntervalInformation-ExtIEs} }		OPTIONAL,
	iE-Extensions						ProtocolExtensionContainer OPTIONAL,
	...
}

--TransmissionTimeIntervalInformation-ExtIEs NBAP-PROTOCOL-EXTENSION ::= {
--	...
--}

TransportFormatSet-Semi-staticPart ::= SEQUENCE {
	transmissionTimeInterval	 		TransportFormatSet-TransmissionTimeIntervalSemiStatic,
	channelCoding					TransportFormatSet-ChannelCodingType,
	codingRate						TransportFormatSet-CodingRate				OPTIONAL,
	-- This IE shall be present if the Type of channel coding IE is set to 'convolutional' or 'turbo' 
	rateMatchingAttribute			TransportFormatSet-RateMatchingAttribute,
	cRC-Size						TransportFormatSet-CRC-Size,
	mode							TransportFormatSet-ModeSSP	,
--	iE-Extensions					ProtocolExtensionContainer { { TransportFormatSet-Semi-staticPart-ExtIEs} }		OPTIONAL,
	iE-Extensions					ProtocolExtensionContainer OPTIONAL,
	...
}

--TransportFormatSet-Semi-staticPart-ExtIEs NBAP-PROTOCOL-EXTENSION ::= {
--	...
--}

TransportFormatSet-ChannelCodingType ::= ENUMERATED {
	no-codingTDD,
	convolutional-coding,
	turbo-coding,
	...
}

TransportFormatSet-CodingRate ::= ENUMERATED {
	half,
	third,
	...
}

TransportFormatSet-CRC-Size ::= ENUMERATED {
	v0,
	v8,
	v12,
	v16,
	v24,
	...
}

TransportFormatSet-ModeDP ::= CHOICE {
	tdd 				TDD-TransportFormatSet-ModeDP,
	notApplicable				NULL,
	...
}

TransportFormatSet-ModeSSP ::= CHOICE {
	tdd				TransportFormatSet-SecondInterleavingMode,
	notApplicable				NULL,
	...
}

TransportFormatSet-NrOfTransportBlocks ::= INTEGER (0..512)

--TransportFormatSet-RateMatchingAttribute ::= INTEGER (1..maxRateMatching)
TransportFormatSet-RateMatchingAttribute ::= INTEGER (1..256)

TransportFormatSet-SecondInterleavingMode ::= ENUMERATED {
	frame-related,
	timeSlot-related,
	...
}

TransportFormatSet-TransmissionTimeIntervalDynamic ::= ENUMERATED {
	msec-10,
	msec-20,
	msec-40,
	msec-80,
	...
}

TransportFormatSet-TransmissionTimeIntervalSemiStatic ::= ENUMERATED {
	msec-10,
	msec-20,
	msec-40,
	msec-80,
	dynamic,
	...,
	msec-5
}

TransportFormatSet-TransportBlockSize ::= INTEGER (0..5000)

TransportLayerAddress ::= BIT STRING (SIZE (1..160, ...))

TSTD-Indicator ::= ENUMERATED {
	active,
	inactive
}

TUTRANGPS ::= SEQUENCE {
	ms-part 	INTEGER (0..16383),
	ls-part		INTEGER (0..4294967295)
}

TUTRANGPSChangeLimit ::= INTEGER (1..256)
-- Unit chip, Step 1/16 chip, Range 1/16..16 chip

TUTRANGPSDriftRate ::= INTEGER (-50..50)
-- Unit chip/s, Step 1/256 chip/s, Range -50/256..+50/256 chip/s

TUTRANGPSDriftRateQuality ::= INTEGER (0..50)
-- Unit chip/s, Step 1/256 chip/s, Range 0..50/256 chip/s

TUTRANGPSAccuracyClass ::= ENUMERATED {
	accuracy-class-A,
	accuracy-class-B,
	accuracy-class-C,
	...
}

TUTRANGPSMeasurementThresholdInformation ::= SEQUENCE {
	tUTRANGPSChangeLimit					TUTRANGPSChangeLimit					OPTIONAL,
	predictedTUTRANGPSDeviationLimit		PredictedTUTRANGPSDeviationLimit		OPTIONAL,
--	iE-Extensions					ProtocolExtensionContainer { { TUTRANGPSMeasurementThresholdInformation-ExtIEs} }		OPTIONAL,
	iE-Extensions					ProtocolExtensionContainer OPTIONAL,
	...
}

--TUTRANGPSMeasurementThresholdInformation-ExtIEs NBAP-PROTOCOL-EXTENSION ::= {
--	...
--}

TUTRANGPSMeasurementValueInformation ::= SEQUENCE {
		tUTRANGPS						TUTRANGPS,
		tUTRANGPSQuality				TUTRANGPSQuality				OPTIONAL,
		tUTRANGPSDriftRate				TUTRANGPSDriftRate,
		tUTRANGPSDriftRateQuality		TUTRANGPSDriftRateQuality		OPTIONAL,
--		iE-Extensions					ProtocolExtensionContainer { {TUTRANGPSMeasurementValueInformationItem-ExtIEs} }		OPTIONAL,
		iE-Extensions					ProtocolExtensionContainer OPTIONAL,
		...
}

--TUTRANGPSMeasurementValueInformationItem-ExtIEs NBAP-PROTOCOL-EXTENSION ::= {
--	...
--}

TUTRANGPSQuality ::= INTEGER (0..255)
-- Unit chip, Step 1/16 chip, Range 0.. 255/16 chip

TypeOfError ::= ENUMERATED {
	not-understood,
	missing,
	...
}

-- ==========================================
--	U
-- ==========================================

UARFCN ::= INTEGER (0..16383, ...)
-- corresponds to 0MHz .. 3276.6MHz

UC-Id ::= SEQUENCE {
	rNC-ID				RNC-ID,
	c-ID				C-ID,
--	iE-Extensions			ProtocolExtensionContainer { {UC-Id-ExtIEs} } OPTIONAL,
	iE-Extensions			ProtocolExtensionContainer OPTIONAL,
	...
}
--UC-Id-ExtIEs NBAP-PROTOCOL-EXTENSION ::= {
--	...
--}

UDRE ::= ENUMERATED {
    udre-minusequal-one-m,
    udre-betweenoneandfour-m,
    udre-betweenfourandeight-m,
    udre-greaterequaleight-m
}


UE-Capability-Information ::= SEQUENCE {
	hSDSCH-Physical-Layer-Category		INTEGER (1..64,...),
--	iE-Extensions						ProtocolExtensionContainer { { UE-Capability-Information-ExtIEs } }			OPTIONAL,
	iE-Extensions						ProtocolExtensionContainer OPTIONAL,
	...
}

--UE-Capability-Information-ExtIEs NBAP-PROTOCOL-EXTENSION ::= {
--	...
--}


UL-CapacityCredit ::= INTEGER (0..65535)

UL-DL-mode ::= ENUMERATED {
	ul-only,
	dl-only,
	both-ul-and-dl
}

UL-DPDCH-Indicator-For-E-DCH-Operation ::= ENUMERATED {
	ul-DPDCH-present,
	ul-DPDCH-not-present
}

Uplink-Compressed-Mode-Method 	::= ENUMERATED {
	sFdiv2,
	higher-layer-scheduling,
	...
}

--UL-Timeslot-Information ::= SEQUENCE (SIZE (1..maxNrOfULTSs)) OF UL-Timeslot-InformationItem
UL-Timeslot-Information ::= SEQUENCE (SIZE (1..15)) OF UL-Timeslot-InformationItem

UL-Timeslot-InformationItem ::= SEQUENCE {
	timeSlot								TimeSlot,
	midambleShiftAndBurstType				MidambleShiftAndBurstType,
	tFCI-Presence							TFCI-Presence,
	uL-Code-InformationList					TDD-UL-Code-Information,
--	iE-Extensions							ProtocolExtensionContainer { { UL-Timeslot-InformationItem-ExtIEs} }		OPTIONAL,
	iE-Extensions							ProtocolExtensionContainer OPTIONAL,
	...
}

--UL-Timeslot-InformationItem-ExtIEs NBAP-PROTOCOL-EXTENSION ::= {
--	...
--}

--UL-TimeslotLCR-Information ::= SEQUENCE (SIZE (1..maxNrOfULTSLCRs)) OF UL-TimeslotLCR-InformationItem
UL-TimeslotLCR-Information ::= SEQUENCE (SIZE (1..6)) OF UL-TimeslotLCR-InformationItem

UL-TimeslotLCR-InformationItem ::= SEQUENCE {
	timeSlotLCR								TimeSlotLCR,
	midambleShiftLCR						MidambleShiftLCR,
	tFCI-Presence							TFCI-Presence,
	uL-Code-InformationList					TDD-UL-Code-LCR-Information,
--	iE-Extensions							ProtocolExtensionContainer { { UL-TimeslotLCR-InformationItem-ExtIEs} }		OPTIONAL,
	iE-Extensions							ProtocolExtensionContainer OPTIONAL,
	...
}

--UL-TimeslotLCR-InformationItem-ExtIEs NBAP-PROTOCOL-EXTENSION ::= {
--	...
--}

UL-DPCCH-SlotFormat ::= INTEGER (0..5,...)

UL-SIR ::= INTEGER (-82..173)
-- According to mapping in [16]

UL-FP-Mode ::= ENUMERATED {
	normal,
	silent,
	...
}

UL-PhysCH-SF-Variation ::= ENUMERATED {
	sf-variation-supported,
	sf-variation-not-supported
}

UL-ScramblingCode ::= SEQUENCE {
	uL-ScramblingCodeNumber			UL-ScramblingCodeNumber,
	uL-ScramblingCodeLength			UL-ScramblingCodeLength,
--	iE-Extensions					ProtocolExtensionContainer { { UL-ScramblingCode-ExtIEs } }		OPTIONAL,
	iE-Extensions					ProtocolExtensionContainer OPTIONAL,
	...
}

--UL-ScramblingCode-ExtIEs NBAP-PROTOCOL-EXTENSION ::= {
--	...
--}

UL-ScramblingCodeNumber ::= INTEGER (0..16777215)

UL-ScramblingCodeLength ::= ENUMERATED {
	short,
	long
}

UL-Synchronisation-Parameters-LCR ::= SEQUENCE {
	uL-Synchronisation-StepSize			UL-Synchronisation-StepSize,
	uL-Synchronisation-Frequency		UL-Synchronisation-Frequency,
--	iE-Extensions						ProtocolExtensionContainer { { UL-Synchronisation-Parameters-LCR-ExtIEs } }		OPTIONAL,
	iE-Extensions						ProtocolExtensionContainer OPTIONAL,
	...
}

--UL-Synchronisation-Parameters-LCR-ExtIEs NBAP-PROTOCOL-EXTENSION ::= {
--	...
--}

UL-Synchronisation-StepSize ::= INTEGER (1..8)

UL-Synchronisation-Frequency ::= INTEGER (1..8)

--UL-TimeSlot-ISCP-Info ::= SEQUENCE (SIZE (1..maxNrOfULTSs)) OF	UL-TimeSlot-ISCP-InfoItem
UL-TimeSlot-ISCP-Info ::= SEQUENCE (SIZE (1..15)) OF	UL-TimeSlot-ISCP-InfoItem

UL-TimeSlot-ISCP-InfoItem ::= SEQUENCE {
 	timeSlot						TimeSlot,
	iSCP							UL-TimeslotISCP-Value,
--	iE-Extensions					ProtocolExtensionContainer { { UL-TimeSlot-ISCP-InfoItem-ExtIEs} }		OPTIONAL,
	iE-Extensions					ProtocolExtensionContainer OPTIONAL,
	...
 }

--UL-TimeSlot-ISCP-InfoItem-ExtIEs NBAP-PROTOCOL-EXTENSION ::= {
--	...
--}

--UL-TimeSlot-ISCP-LCR-Info ::= SEQUENCE (SIZE (1..maxNrOfULTSLCRs)) OF	UL-TimeSlot-ISCP-LCR-InfoItem
UL-TimeSlot-ISCP-LCR-Info ::= SEQUENCE (SIZE (1..6)) OF	UL-TimeSlot-ISCP-LCR-InfoItem

UL-TimeSlot-ISCP-LCR-InfoItem ::= SEQUENCE {
 	timeSlotLCR						TimeSlotLCR,
	iSCP							UL-TimeslotISCP-Value,
--	iE-Extensions					ProtocolExtensionContainer { { UL-TimeSlot-ISCP-LCR-InfoItem-ExtIEs} }		OPTIONAL,
	iE-Extensions					ProtocolExtensionContainer OPTIONAL,
	...
 }

--UL-TimeSlot-ISCP-LCR-InfoItem-ExtIEs NBAP-PROTOCOL-EXTENSION ::= {
--	...
--}

UpPTSInterferenceValue ::= INTEGER (0..127,...)

Unidirectional-DCH-Indicator	::= ENUMERATED {
	downlink-DCH-only,
	uplink-DCH-only
}

--USCH-Information ::= SEQUENCE (SIZE (1..maxNrOfUSCHs)) OF USCH-InformationItem
USCH-Information ::= SEQUENCE (SIZE (1..32)) OF USCH-InformationItem

USCH-InformationItem ::= SEQUENCE {
	uSCH-ID									USCH-ID,
	cCTrCH-ID								CCTrCH-ID,			-- UL CCTrCH in which the USCH is mapped
	transportFormatSet						TransportFormatSet,	-- For USCH
	allocationRetentionPriority				AllocationRetentionPriority,
--	iE-Extensions							ProtocolExtensionContainer { { USCH-InformationItem-ExtIEs} }		OPTIONAL,
	iE-Extensions							ProtocolExtensionContainer OPTIONAL,
	...
}

--USCH-InformationItem-ExtIEs NBAP-PROTOCOL-EXTENSION ::= {
--	{ ID id-bindingID						CRITICALITY	ignore		EXTENSION 	BindingID			PRESENCE 	optional	}|
	-- Shall be ignored if bearer establishment with ALCAP.
--	{ ID id-transportlayeraddress			CRITICALITY	ignore		EXTENSION 	TransportLayerAddress	PRESENCE 	optional	}|
	-- Shall be ignored if bearer establishment with ALCAP.
--{ ID id-TnlQos							CRITICALITY ignore		EXTENSION	TnlQos	PRESENCE optional	},
--	...
--}

--USCH-InformationResponse ::= SEQUENCE (SIZE (1..maxNrOfUSCHs)) OF USCH-InformationResponseItem
USCH-InformationResponse ::= SEQUENCE (SIZE (1..32)) OF USCH-InformationResponseItem

USCH-InformationResponseItem ::= SEQUENCE {
	uSCH-ID										USCH-ID,
	bindingID									BindingID				OPTIONAL,
	transportLayerAddress						TransportLayerAddress	OPTIONAL,
--	iE-Extensions								ProtocolExtensionContainer { { USCH-InformationResponseItem-ExtIEs} }		OPTIONAL,
	iE-Extensions								ProtocolExtensionContainer OPTIONAL,
	...
}

--USCH-InformationResponseItem-ExtIEs NBAP-PROTOCOL-EXTENSION ::= {
--	...
--}

UL-TimeslotISCP-Value ::= INTEGER (0..127)
-- According to mapping in [23]

UL-TimeslotISCP-Value-IncrDecrThres ::= INTEGER (0..126)

USCH-ID ::= INTEGER (0..255)

-- ==========================================
--	V
-- ==========================================

-- ==========================================
--	W
-- ==========================================

-- ==========================================
--	X
-- ==========================================

-- ==========================================
--	Y
-- ==========================================

-- ==========================================
--	Z
-- ==========================================

-- END

--9.3.5	Common Definitions
-- **************************************************************
--
-- Common definitions
--
-- **************************************************************

--NBAP-CommonDataTypes {
--itu-t (0) identified-organization (4) etsi (0) mobileDomain (0) 
--umts-Access (20) modules (3) nbap (2) version1 (1) nbap-CommonDataTypes (3)  }

--DEFINITIONS AUTOMATIC TAGS ::= 

--BEGIN

-- **************************************************************
--
-- Extension constants
--
-- **************************************************************

maxPrivateIEs 					INTEGER ::= 65535
maxProtocolExtensions 			INTEGER ::= 65535
maxProtocolIEs					INTEGER ::= 65535

-- **************************************************************
--
-- Common Data Types
--
-- **************************************************************

Criticality		::= ENUMERATED { reject, ignore, notify }

MessageDiscriminator	::= ENUMERATED { common, dedicated }

Presence		::= ENUMERATED { optional, conditional, mandatory }

PrivateIE-ID	::= CHOICE {
	local				INTEGER (0..65535),
	global				OBJECT IDENTIFIER
}

ProcedureCode	::= INTEGER {
	id-audit 												(0),
	id-auditRequired 										(1),
	id-blockResource 										(2),
	id-cellDeletion 										(3),
	id-cellReconfiguration 									(4),
	id-cellSetup 											(5),
	id-cellSynchronisationInitiation						(45),
	id-cellSynchronisationReconfiguration					(46),
	id-cellSynchronisationReporting							(47),
	id-cellSynchronisationTermination						(48),
	id-cellSynchronisationFailure							(49),
	id-commonMeasurementFailure 							(6),
	id-commonMeasurementInitiation 							(7),
	id-commonMeasurementReport 								(8),
	id-commonMeasurementTermination 						(9),
	id-commonTransportChannelDelete 						(10),
	id-commonTransportChannelReconfigure 					(11),
	id-commonTransportChannelSetup 							(12),
	id-compressedModeCommand 								(14),
	id-dedicatedMeasurementFailure 							(16),
	id-dedicatedMeasurementInitiation 						(17),
	id-dedicatedMeasurementReport 							(18),
	id-dedicatedMeasurementTermination 						(19),
	id-downlinkPowerControl 								(20),
	id-downlinkPowerTimeslotControl 						(38),
	id-errorIndicationForCommon								(35),
	id-errorIndicationForDedicated							(21),
	id-informationExchangeFailure							(40),
	id-informationExchangeInitiation						(41),
	id-informationExchangeTermination						(42),
	id-informationReporting									(43),
	id-BearerRearrangement									(50),
	id-mBMSNotificationUpdate								(53),
	id-physicalSharedChannelReconfiguration 				(37),
	id-privateMessageForCommon								(36),
	id-privateMessageForDedicated							(22),
	id-radioLinkAddition 									(23),
	id-radioLinkDeletion 									(24),
	id-radioLinkFailure 									(25),
	id-radioLinkPreemption									(39),
	id-radioLinkRestoration 								(26),
	id-radioLinkSetup 										(27),
	id-reset												(13),
	id-resourceStatusIndication 							(28),
	id-cellSynchronisationAdjustment						(44),
	id-synchronisedRadioLinkReconfigurationCancellation		(29),
	id-synchronisedRadioLinkReconfigurationCommit			(30),
	id-synchronisedRadioLinkReconfigurationPreparation 		(31),
	id-systemInformationUpdate 								(32),
	id-unblockResource 										(33),
	id-unSynchronisedRadioLinkReconfiguration 				(34),
	id-radioLinkActivation									(51),
	id-radioLinkParameterUpdate								(52)
} (0..255)

ProcedureID		::= SEQUENCE {
	procedureCode			ProcedureCode,
	ddMode					ENUMERATED { tdd, fdd, common, ... }
}

ProtocolIE-ID		::= INTEGER {
id-AICH-Information													(0),
id-AICH-InformationItem-ResourceStatusInd							(1),
id-BCH-Information													(7),
id-BCH-InformationItem-ResourceStatusInd							(8),
id-BCCH-ModificationTime											(9),
id-BlockingPriorityIndicator										(10),
id-Cause															(13),
id-CCP-InformationItem-AuditRsp										(14),
id-CCP-InformationList-AuditRsp										(15),
id-CCP-InformationItem-ResourceStatusInd							(16),
id-Cell-InformationItem-AuditRsp									(17),
id-Cell-InformationItem-ResourceStatusInd							(18),
id-Cell-InformationList-AuditRsp									(19),
id-CellParameterID													(23),
id-CFN																(24),
id-C-ID																(25),
id-CommonMeasurementAccuracy										(39),
id-CommonMeasurementObjectType-CM-Rprt								(31),
id-CommonMeasurementObjectType-CM-Rqst								(32),
id-CommonMeasurementObjectType-CM-Rsp								(33),
id-CommonMeasurementType											(34),
id-CommonPhysicalChannelID											(35),
id-CommonPhysicalChannelType-CTCH-SetupRqstFDD						(36),
id-CommonPhysicalChannelType-CTCH-SetupRqstTDD						(37),
id-CommunicationControlPortID										(40),
id-ConfigurationGenerationID										(43),
id-CRNC-CommunicationContextID										(44),
id-CriticalityDiagnostics											(45),
id-DCHs-to-Add-FDD													(48),
id-DCH-AddList-RL-ReconfPrepTDD										(49),
id-DCHs-to-Add-TDD													(50),
id-DCH-DeleteList-RL-ReconfPrepFDD									(52),
id-DCH-DeleteList-RL-ReconfPrepTDD									(53),
id-DCH-DeleteList-RL-ReconfRqstFDD									(54),
id-DCH-DeleteList-RL-ReconfRqstTDD									(55),
id-DCH-FDD-Information												(56),
id-DCH-TDD-Information												(57),
id-DCH-InformationResponse											(59),
id-FDD-DCHs-to-Modify												(62),
id-TDD-DCHs-to-Modify												(63),
id-DCH-ModifyList-RL-ReconfRqstTDD									(65),
id-DCH-RearrangeList-Bearer-RearrangeInd							(135),
id-DedicatedMeasurementObjectType-DM-Rprt							(67),
id-DedicatedMeasurementObjectType-DM-Rqst							(68),
id-DedicatedMeasurementObjectType-DM-Rsp							(69),
id-DedicatedMeasurementType											(70),
id-DL-CCTrCH-InformationItem-RL-SetupRqstTDD						(72),
id-DL-CCTrCH-InformationList-RL-AdditionRqstTDD						(73),
id-DL-CCTrCH-InformationList-RL-SetupRqstTDD						(76),
id-DL-DPCH-InformationItem-RL-AdditionRqstTDD						(77),
id-DL-DPCH-InformationList-RL-SetupRqstTDD							(79),
id-DL-DPCH-Information-RL-ReconfPrepFDD								(81),
id-DL-DPCH-Information-RL-ReconfRqstFDD								(82),
id-DL-DPCH-Information-RL-SetupRqstFDD								(83),
id-DL-DPCH-TimingAdjustment											(21),
id-DL-ReferencePowerInformationItem-DL-PC-Rqst						(84),
id-DLReferencePower													(85),
id-DLReferencePowerList-DL-PC-Rqst									(86),
id-Unused-ProtocolIE-ID-87											(87),
id-Unused-ProtocolIE-ID-89											(89),
id-Unused-ProtocolIE-ID-91											(91),
id-Unused-ProtocolIE-ID-93											(93),
id-DSCHs-to-Add-TDD													(96),
id-DSCH-Information-DeleteList-RL-ReconfPrepTDD						(98),
id-DSCH-Information-ModifyList-RL-ReconfPrepTDD						(100),
id-DSCH-InformationResponse											(105),
id-Unused-ProtocolIE-ID-106											(106),
id-DSCH-TDD-Information												(107),
id-Unused-ProtocolIE-ID-108											(108),
id-Unused-ProtocolIE-ID-112											(112),
id-DSCH-RearrangeList-Bearer-RearrangeInd							(136),
id-End-Of-Audit-Sequence-Indicator 									(113),
id-FACH-Information													(116),
id-FACH-InformationItem-ResourceStatusInd							(117),
id-FACH-ParametersList-CTCH-ReconfRqstTDD							(120),
id-FACH-ParametersListIE-CTCH-SetupRqstFDD							(121),
id-FACH-ParametersListIE-CTCH-SetupRqstTDD							(122),
id-IndicationType-ResourceStatusInd									(123),
id-Local-Cell-ID													(124),
id-Local-Cell-Group-InformationItem-AuditRsp						(2),
id-Local-Cell-Group-InformationItem-ResourceStatusInd				(3),
id-Local-Cell-Group-InformationItem2-ResourceStatusInd				(4),
id-Local-Cell-Group-InformationList-AuditRsp						(5),
id-Local-Cell-InformationItem-AuditRsp								(125),
id-Local-Cell-InformationItem-ResourceStatusInd						(126),
id-Local-Cell-InformationItem2-ResourceStatusInd					(127),
id-Local-Cell-InformationList-AuditRsp								(128),
id-AdjustmentPeriod													(129),
id-MaxAdjustmentStep												(130),
id-MaximumTransmissionPower											(131),
id-MeasurementFilterCoefficient										(132),
id-MeasurementID													(133),
id-MessageStructure													(115),
id-MIB-SB-SIB-InformationList-SystemInfoUpdateRqst					(134),
id-NodeB-CommunicationContextID										(143),
id-NeighbouringCellMeasurementInformation							(455),
id-P-CCPCH-Information												(144),
id-P-CCPCH-InformationItem-ResourceStatusInd						(145),
id-P-CPICH-Information												(146),
id-P-CPICH-InformationItem-ResourceStatusInd						(147),
id-P-SCH-Information												(148),
id-PCCPCH-Information-Cell-ReconfRqstTDD							(150),
id-PCCPCH-Information-Cell-SetupRqstTDD								(151),
id-PCH-Parameters-CTCH-ReconfRqstTDD								(155),
id-PCH-ParametersItem-CTCH-SetupRqstFDD								(156),
id-PCH-ParametersItem-CTCH-SetupRqstTDD								(157),
id-PCH-Information													(158),
id-PDSCH-Information-AddListIE-PSCH-ReconfRqst						(161),
id-PDSCH-Information-ModifyListIE-PSCH-ReconfRqst					(162),
id-PDSCHSets-AddList-PSCH-ReconfRqst								(163),
id-PDSCHSets-DeleteList-PSCH-ReconfRqst								(164),
id-PDSCHSets-ModifyList-PSCH-ReconfRqst								(165),
id-PICH-Information													(166),
id-PICH-Parameters-CTCH-ReconfRqstTDD								(168),
id-PowerAdjustmentType												(169),
id-PRACH-Information												(170),
id-PrimaryCCPCH-Information-Cell-ReconfRqstFDD						(175),
id-PrimaryCCPCH-Information-Cell-SetupRqstFDD						(176),
id-PrimaryCPICH-Information-Cell-ReconfRqstFDD						(177),
id-PrimaryCPICH-Information-Cell-SetupRqstFDD						(178),
id-PrimarySCH-Information-Cell-ReconfRqstFDD						(179),
id-PrimarySCH-Information-Cell-SetupRqstFDD							(180),
id-PrimaryScramblingCode											(181),
id-SCH-Information-Cell-ReconfRqstTDD								(183),
id-SCH-Information-Cell-SetupRqstTDD								(184),
id-PUSCH-Information-AddListIE-PSCH-ReconfRqst						(185),
id-PUSCH-Information-ModifyListIE-PSCH-ReconfRqst					(186),
id-PUSCHSets-AddList-PSCH-ReconfRqst								(187),
id-PUSCHSets-DeleteList-PSCH-ReconfRqst								(188),
id-PUSCHSets-ModifyList-PSCH-ReconfRqst								(189),
id-RACH-Information													(190),
id-RACH-ParametersItem-CTCH-SetupRqstFDD							(196),
id-RACH-ParameterItem-CTCH-SetupRqstTDD								(197),
id-ReportCharacteristics											(198),
id-Reporting-Object-RL-FailureInd									(199),
id-Reporting-Object-RL-RestoreInd									(200),
id-RL-InformationItem-DM-Rprt										(202),
id-RL-InformationItem-DM-Rqst										(203),
id-RL-InformationItem-DM-Rsp										(204),
id-RL-InformationItem-RL-AdditionRqstFDD							(205),
id-RL-informationItem-RL-DeletionRqst								(206),
id-RL-InformationItem-RL-FailureInd									(207),
id-RL-InformationItem-RL-PreemptRequiredInd							(286),
id-RL-InformationItem-RL-ReconfPrepFDD								(208),
id-RL-InformationItem-RL-ReconfRqstFDD								(209),
id-RL-InformationItem-RL-RestoreInd									(210),
id-RL-InformationItem-RL-SetupRqstFDD								(211),
id-RL-InformationList-RL-AdditionRqstFDD							(212),
id-RL-informationList-RL-DeletionRqst								(213),
id-RL-InformationList-RL-PreemptRequiredInd							(237),
id-RL-InformationList-RL-ReconfPrepFDD								(214),
id-RL-InformationList-RL-ReconfRqstFDD								(215),
id-RL-InformationList-RL-SetupRqstFDD								(216),
id-RL-InformationResponseItem-RL-AdditionRspFDD						(217),
id-RL-InformationResponseItem-RL-ReconfReady						(218),
id-RL-InformationResponseItem-RL-ReconfRsp							(219),
id-RL-InformationResponseItem-RL-SetupRspFDD						(220),
id-RL-InformationResponseList-RL-AdditionRspFDD						(221),
id-RL-InformationResponseList-RL-ReconfReady						(222),
id-RL-InformationResponseList-RL-ReconfRsp							(223),
id-RL-InformationResponseList-RL-SetupRspFDD						(224),
id-RL-InformationResponse-RL-AdditionRspTDD							(225),
id-RL-InformationResponse-RL-SetupRspTDD							(226),
id-RL-Information-RL-AdditionRqstTDD								(227),
id-RL-Information-RL-ReconfRqstTDD									(228),
id-RL-Information-RL-ReconfPrepTDD									(229),
id-RL-Information-RL-SetupRqstTDD									(230),
id-RL-ReconfigurationFailureItem-RL-ReconfFailure					(236),
id-RL-Set-InformationItem-DM-Rprt									(238),
id-RL-Set-InformationItem-DM-Rsp									(240),
id-RL-Set-InformationItem-RL-FailureInd								(241),
id-RL-Set-InformationItem-RL-RestoreInd								(242),
id-S-CCPCH-Information												(247),
id-S-CPICH-Information												(249),
id-SCH-Information													(251),
id-S-SCH-Information												(253),
id-Secondary-CCPCHListIE-CTCH-ReconfRqstTDD							(257),
id-Secondary-CCPCH-parameterListIE-CTCH-SetupRqstTDD				(258),
id-Secondary-CCPCH-Parameters-CTCH-ReconfRqstTDD					(259),
id-SecondaryCPICH-InformationItem-Cell-ReconfRqstFDD				(260),
id-SecondaryCPICH-InformationItem-Cell-SetupRqstFDD					(261),
id-SecondaryCPICH-InformationList-Cell-ReconfRqstFDD				(262),
id-SecondaryCPICH-InformationList-Cell-SetupRqstFDD					(263),
id-SecondarySCH-Information-Cell-ReconfRqstFDD						(264),
id-SecondarySCH-Information-Cell-SetupRqstFDD						(265),
id-SegmentInformationListIE-SystemInfoUpdate						(266),
id-SFN																(268),
id-SignallingBearerRequestIndicator									(138),
id-ShutdownTimer													(269),
id-Start-Of-Audit-Sequence-Indicator								(114),
id-Successful-RL-InformationRespItem-RL-AdditionFailureFDD			(270),
id-Successful-RL-InformationRespItem-RL-SetupFailureFDD				(271),
id-SyncCase															(274),
id-SyncCaseIndicatorItem-Cell-SetupRqstTDD-PSCH						(275),
id-T-Cell															(276),
id-TargetCommunicationControlPortID									(139),
id-TimeSlotConfigurationList-Cell-ReconfRqstTDD						(277),
id-TimeSlotConfigurationList-Cell-SetupRqstTDD						(278),
id-TransmissionDiversityApplied										(279),
id-TypeOfError														(508),
id-UARFCNforNt														(280),
id-UARFCNforNd														(281),
id-UARFCNforNu														(282),
id-UL-CCTrCH-InformationItem-RL-SetupRqstTDD						(284),
id-UL-CCTrCH-InformationList-RL-AdditionRqstTDD						(285),
id-UL-CCTrCH-InformationList-RL-SetupRqstTDD						(288),
id-UL-DPCH-InformationItem-RL-AdditionRqstTDD						(289),
id-UL-DPCH-InformationList-RL-SetupRqstTDD							(291),
id-UL-DPCH-Information-RL-ReconfPrepFDD								(293),
id-UL-DPCH-Information-RL-ReconfRqstFDD								(294),
id-UL-DPCH-Information-RL-SetupRqstFDD								(295),
id-Unsuccessful-RL-InformationRespItem-RL-AdditionFailureFDD		(296),
id-Unsuccessful-RL-InformationRespItem-RL-SetupFailureFDD			(297),
id-Unsuccessful-RL-InformationResp-RL-AdditionFailureTDD			(300),
id-Unsuccessful-RL-InformationResp-RL-SetupFailureTDD				(301),
id-USCH-Information-Add												(302),
id-USCH-Information-DeleteList-RL-ReconfPrepTDD						(304),
id-USCH-Information-ModifyList-RL-ReconfPrepTDD						(306),
id-USCH-InformationResponse											(309),
id-USCH-Information													(310),
id-USCH-RearrangeList-Bearer-RearrangeInd							(141),
id-Active-Pattern-Sequence-Information 								(315),
id-AICH-ParametersListIE-CTCH-ReconfRqstFDD							(316),
id-AdjustmentRatio													(317),
id-Not-Used-320														(320),
id-Not-Used-322														(322),
id-FACH-ParametersListIE-CTCH-ReconfRqstFDD							(323),
id-CauseLevel-PSCH-ReconfFailure									(324),
id-CauseLevel-RL-AdditionFailureFDD									(325),
id-CauseLevel-RL-AdditionFailureTDD									(326),
id-CauseLevel-RL-ReconfFailure										(327),
id-CauseLevel-RL-SetupFailureFDD									(328),
id-CauseLevel-RL-SetupFailureTDD									(329),
id-Not-Used-330														(330),
id-Not-Used-332														(332),
id-Closed-Loop-Timing-Adjustment-Mode								(333),
id-CommonPhysicalChannelType-CTCH-ReconfRqstFDD						(334),
id-Compressed-Mode-Deactivation-Flag								(335),
id-Not-Used-336														(336),
id-Not-Used-342														(342),
id-Not-Used-343														(343),
id-DL-CCTrCH-InformationAddList-RL-ReconfPrepTDD					(346),
id-DL-CCTrCH-InformationDeleteItem-RL-ReconfRqstTDD					(347),
id-DL-CCTrCH-InformationDeleteList-RL-ReconfPrepTDD					(348),
id-DL-CCTrCH-InformationDeleteList-RL-ReconfRqstTDD					(349),
id-DL-CCTrCH-InformationModifyItem-RL-ReconfRqstTDD					(350),
id-DL-CCTrCH-InformationModifyList-RL-ReconfPrepTDD					(351),
id-DL-CCTrCH-InformationModifyList-RL-ReconfRqstTDD					(352),
id-DL-DPCH-InformationAddListIE-RL-ReconfPrepTDD					(353),
id-DL-DPCH-InformationModify-AddListIE-RL-ReconfPrepTDD				(355),
id-DL-DPCH-InformationModify-DeleteListIE-RL-ReconfPrepTDD			(356),
id-DL-DPCH-InformationModify-ModifyListIE-RL-ReconfPrepTDD			(357),
id-DL-TPC-Pattern01Count 											(358),
id-DPC-Mode															(450),
id-DPCHConstant														(359),
id-Unused-ProtocolIE-ID-94											(94),
id-Unused-ProtocolIE-ID-110											(110),
id-Unused-ProtocolIE-ID-111											(111),
id-FACH-ParametersList-CTCH-SetupRsp								(362),
id-Limited-power-increase-information-Cell-SetupRqstFDD				(369),
id-PCH-Parameters-CTCH-SetupRsp										(374),
id-PCH-ParametersItem-CTCH-ReconfRqstFDD							(375),
id-Not-Used-376														(376),
id-PICH-ParametersItem-CTCH-ReconfRqstFDD							(380),
id-PRACHConstant													(381),
id-PRACH-ParametersListIE-CTCH-ReconfRqstFDD						(383),
id-PUSCHConstant													(384),
id-RACH-Parameters-CTCH-SetupRsp									(385),
id-Unused-ProtocolIE-ID-443											(443),
id-Synchronisation-Configuration-Cell-ReconfRqst					(393),
id-Synchronisation-Configuration-Cell-SetupRqst						(394),
id-Transmission-Gap-Pattern-Sequence-Information					(395),
id-UL-CCTrCH-InformationAddList-RL-ReconfPrepTDD					(396),
id-UL-CCTrCH-InformationDeleteItem-RL-ReconfRqstTDD					(397),
id-UL-CCTrCH-InformationDeleteList-RL-ReconfPrepTDD					(398),
id-UL-CCTrCH-InformationDeleteList-RL-ReconfRqstTDD					(399),
id-UL-CCTrCH-InformationModifyItem-RL-ReconfRqstTDD					(400),
id-UL-CCTrCH-InformationModifyList-RL-ReconfPrepTDD					(401),
id-UL-CCTrCH-InformationModifyList-RL-ReconfRqstTDD					(402),
id-UL-DPCH-InformationAddListIE-RL-ReconfPrepTDD					(403),
id-UL-DPCH-InformationModify-AddListIE-RL-ReconfPrepTDD				(405),
id-UL-DPCH-InformationModify-DeleteListIE-RL-ReconfPrepTDD			(406),
id-UL-DPCH-InformationModify-ModifyListIE-RL-ReconfPrepTDD			(407),
id-Unsuccessful-PDSCHSetItem-PSCH-ReconfFailureTDD					(408),
id-Unsuccessful-PUSCHSetItem-PSCH-ReconfFailureTDD					(409),
id-CommunicationContextInfoItem-Reset								(412),
id-CommunicationControlPortInfoItem-Reset							(414),
id-ResetIndicator													(416),
id-Unused-ProtocolIE-ID-417											(417),
id-Unused-ProtocolIE-ID-418											(418),
id-Unused-ProtocolIE-ID-419											(419),
id-Unused-ProtocolIE-ID-142											(142),
id-TimingAdvanceApplied												(287),
id-CFNReportingIndicator											(6),
id-SFNReportingIndicator											(11),
id-InnerLoopDLPCStatus												(12),
id-TimeslotISCPInfo													(283),
id-PICH-ParametersItem-CTCH-SetupRqstTDD							(167),
id-PRACH-ParametersItem-CTCH-SetupRqstTDD							(20),
id-CCTrCH-InformationItem-RL-FailureInd								(46),
id-CCTrCH-InformationItem-RL-RestoreInd								(47),
id-CauseLevel-SyncAdjustmntFailureTDD								(420),
id-CellAdjustmentInfo-SyncAdjustmntRqstTDD							(421),
id-CellAdjustmentInfoItem-SyncAdjustmentRqstTDD						(494),
id-CellSyncBurstInfoList-CellSyncReconfRqstTDD						(482),
id-CellSyncBurstTransInit-CellSyncInitiationRqstTDD					(422),
id-CellSyncBurstMeasureInit-CellSyncInitiationRqstTDD				(423),
id-CellSyncBurstTransReconfiguration-CellSyncReconfRqstTDD			(424),
id-CellSyncBurstMeasReconfiguration-CellSyncReconfRqstTDD			(425),
id-CellSyncBurstTransInfoList-CellSyncReconfRqstTDD					(426),
id-CellSyncBurstMeasInfoList-CellSyncReconfRqstTDD					(427),
id-CellSyncBurstTransReconfInfo-CellSyncReconfRqstTDD				(428),
id-CellSyncInfo-CellSyncReprtTDD									(429),
id-CSBTransmissionID												(430),
id-CSBMeasurementID													(431),
id-IntStdPhCellSyncInfoItem-CellSyncReprtTDD						(432),
id-NCyclesPerSFNperiod 												(433),
id-NRepetitionsPerCyclePeriod										(434),
id-SyncFrameNumber													(437),
id-SynchronisationReportType										(438),
id-SynchronisationReportCharacteristics								(439),
id-Unsuccessful-cell-InformationRespItem-SyncAdjustmntFailureTDD	(440),
id-LateEntranceCellSyncInfoItem-CellSyncReprtTDD					(119),
id-ReferenceClockAvailability										(435),
id-ReferenceSFNoffset												(436),
id-InformationExchangeID											(444),
id-InformationExchangeObjectType-InfEx-Rqst							(445),
id-InformationType													(446),
id-InformationReportCharacteristics									(447),
id-InformationExchangeObjectType-InfEx-Rsp							(448),
id-InformationExchangeObjectType-InfEx-Rprt							(449),
id-IPDLParameter-Information-Cell-ReconfRqstFDD						(451),
id-IPDLParameter-Information-Cell-SetupRqstFDD						(452),
id-IPDLParameter-Information-Cell-ReconfRqstTDD						(453),
id-IPDLParameter-Information-Cell-SetupRqstTDD						(454),
id-DL-DPCH-LCR-Information-RL-SetupRqstTDD							(74),
id-DwPCH-LCR-Information											(78),
id-DwPCH-LCR-InformationList-AuditRsp                   			(90),
id-DwPCH-LCR-Information-Cell-SetupRqstTDD                   		(97),
id-DwPCH-LCR-Information-Cell-ReconfRqstTDD							(99),
id-DwPCH-LCR-Information-ResourceStatusInd							(101),
id-maxFACH-Power-LCR-CTCH-SetupRqstTDD                   			(154),
id-maxFACH-Power-LCR-CTCH-ReconfRqstTDD                   			(174),
id-FPACH-LCR-Information											(290),
id-FPACH-LCR-Information-AuditRsp                   				(292),
id-FPACH-LCR-InformationList-AuditRsp                   			(22),
id-FPACH-LCR-InformationList-ResourceStatusInd                   	(311),
id-FPACH-LCR-Parameters-CTCH-SetupRqstTDD                   		(312),
id-FPACH-LCR-Parameters-CTCH-ReconfRqstTDD                   		(314),
id-PCCPCH-LCR-Information-Cell-SetupRqstTDD                   		(456),
id-PCH-Power-LCR-CTCH-SetupRqstTDD									(457),
id-PCH-Power-LCR-CTCH-ReconfRqstTDD									(458),
id-PICH-LCR-Parameters-CTCH-SetupRqstTDD                   			(459),
id-PRACH-LCR-ParametersList-CTCH-SetupRqstTDD                  		(461),
id-RL-InformationResponse-LCR-RL-SetupRspTDD	                   	(463),
id-Secondary-CCPCH-LCR-parameterList-CTCH-SetupRqstTDD              (465),
id-TimeSlot															(495),
id-TimeSlotConfigurationList-LCR-Cell-ReconfRqstTDD                 (466),
id-TimeSlotConfigurationList-LCR-Cell-SetupRqstTDD                  (467),
id-TimeslotISCP-LCR-InfoList-RL-SetupRqstTDD                   		(468),
id-TimeSlotLCR-CM-Rqst                   							(469),
id-UL-DPCH-LCR-Information-RL-SetupRqstTDD                   		(470),
id-DL-DPCH-InformationItem-LCR-RL-AdditionRqstTDD					(472),
id-UL-DPCH-InformationItem-LCR-RL-AdditionRqstTDD					(473),
id-TimeslotISCP-InformationList-LCR-RL-AdditionRqstTDD				(474),
id-DL-DPCH-LCR-InformationAddList-RL-ReconfPrepTDD					(475),
id-DL-DPCH-LCR-InformationModify-AddList-RL-ReconfPrepTDD			(477),
id-DL-Timeslot-LCR-InformationModify-ModifyList-RL-ReconfPrepTDD	(479),
id-TimeslotISCPInfoList-LCR-DL-PC-RqstTDD							(480),
id-UL-DPCH-LCR-InformationAddListIE-RL-ReconfPrepTDD				(481),
id-UL-DPCH-LCR-InformationModify-AddList							(483),
id-UL-TimeslotLCR-Information-RL-ReconfPrepTDD						(485),
id-UL-SIRTarget														(510),
id-PDSCH-AddInformation-LCR-PSCH-ReconfRqst							(486),
id-PDSCH-AddInformation-LCR-AddListIE-PSCH-ReconfRqst				(487),
id-Unused-ProtocolIE-ID-26											( 26),
id-Unused-ProtocolIE-ID-27											( 27),
id-PDSCH-ModifyInformation-LCR-PSCH-ReconfRqst						(488),
id-PDSCH-ModifyInformation-LCR-ModifyListIE-PSCH-ReconfRqst			(489),
id-PUSCH-AddInformation-LCR-PSCH-ReconfRqst							(490),
id-PUSCH-AddInformation-LCR-AddListIE-PSCH-ReconfRqst				(491),
id-PUSCH-ModifyInformation-LCR-PSCH-ReconfRqst						(492),
id-PUSCH-ModifyInformation-LCR-ModifyListIE-PSCH-ReconfRqst			(493),
id-timeslotInfo-CellSyncInitiationRqstTDD							(496),
id-SyncReportType-CellSyncReprtTDD									(497),
id-Power-Local-Cell-Group-InformationItem-AuditRsp					(498),
id-Power-Local-Cell-Group-InformationItem-ResourceStatusInd			(499),
id-Power-Local-Cell-Group-InformationItem2-ResourceStatusInd		(500),
id-Power-Local-Cell-Group-InformationList-AuditRsp					(501),
id-Power-Local-Cell-Group-InformationList-ResourceStatusInd			(502),
id-Power-Local-Cell-Group-InformationList2-ResourceStatusInd		(503),
id-Power-Local-Cell-Group-ID										(504),
id-PUSCH-Info-DM-Rqst												(505),
id-PUSCH-Info-DM-Rsp												(506),
id-PUSCH-Info-DM-Rprt												(507),
id-InitDL-Power														(509),
id-cellSyncBurstRepetitionPeriod									(511),
id-ReportCharacteristicsType-OnModification							(512),
id-SFNSFNMeasurementValueInformation								(513),
id-SFNSFNMeasurementThresholdInformation							(514),
id-TUTRANGPSMeasurementValueInformation								(515),
id-TUTRANGPSMeasurementThresholdInformation							(516),
id-Rx-Timing-Deviation-Value-LCR									(520),
id-RL-InformationResponse-LCR-RL-AdditionRspTDD						(51),
id-DL-PowerBalancing-Information									(28),
id-DL-PowerBalancing-ActivationIndicator							(29),
id-DL-PowerBalancing-UpdatedIndicator								(30),
id-CCTrCH-Initial-DL-Power-RL-SetupRqstTDD							(517),
id-CCTrCH-Initial-DL-Power-RL-AdditionRqstTDD						(518),
id-CCTrCH-Initial-DL-Power-RL-ReconfPrepTDD							(519),
id-IPDLParameter-Information-LCR-Cell-SetupRqstTDD					(41),
id-IPDLParameter-Information-LCR-Cell-ReconfRqstTDD 				(42),
id-HS-PDSCH-HS-SCCH-E-AGCH-E-RGCH-E-HICH-MaxPower-PSCH-ReconfRqst	(522),
id-HS-PDSCH-HS-SCCH-ScramblingCode-PSCH-ReconfRqst					(523),
id-HS-PDSCH-FDD-Code-Information-PSCH-ReconfRqst					(524),
id-HS-SCCH-FDD-Code-Information-PSCH-ReconfRqst						(525),
id-HS-PDSCH-TDD-Information-PSCH-ReconfRqst							(526),
id-Add-To-HS-SCCH-Resource-Pool-PSCH-ReconfRqst						(527),
id-Modify-HS-SCCH-Resource-Pool-PSCH-ReconfRqst						(528),
id-Delete-From-HS-SCCH-Resource-Pool-PSCH-ReconfRqst				(529),
id-bindingID														(102),
id-RL-Specific-DCH-Info												(103),
id-transportlayeraddress 											(104),
id-DelayedActivation 												(231),
id-DelayedActivationList-RL-ActivationCmdFDD						(232),
id-DelayedActivationInformation-RL-ActivationCmdFDD					(233),
id-DelayedActivationList-RL-ActivationCmdTDD						(234),
id-DelayedActivationInformation-RL-ActivationCmdTDD					(235),
id-neighbouringTDDCellMeasurementInformationLCR						(58),
id-SYNCDlCodeId-TransInitLCR-CellSyncInitiationRqstTDD				(543),
id-SYNCDlCodeId-MeasureInitLCR-CellSyncInitiationRqstTDD			(544),
id-SYNCDlCodeIdTransReconfInfoLCR-CellSyncReconfRqstTDD				(545),
id-SYNCDlCodeIdMeasReconfigurationLCR-CellSyncReconfRqstTDD			(546),
id-SYNCDlCodeIdMeasInfoList-CellSyncReconfRqstTDD					(547),
id-SyncDLCodeIdsMeasInfoList-CellSyncReprtTDD						(548),
id-SyncDLCodeIdThreInfoLCR											(549),
id-NSubCyclesPerCyclePeriod-CellSyncReconfRqstTDD					(550),
id-DwPCH-Power														(551),
id-AccumulatedClockupdate-CellSyncReprtTDD							(552),
id-Angle-Of-Arrival-Value-LCR										(521),
id-HSDSCH-FDD-Information											(530),
id-HSDSCH-FDD-Information-Response									(531),
id-HSDSCH-Information-to-Modify										(534),
id-HSDSCH-RNTI														(535),
id-HSDSCH-TDD-Information											(536),
id-HSDSCH-TDD-Information-Response									(537),
id-HSPDSCH-RL-ID													(541),
id-PrimCCPCH-RSCP-DL-PC-RqstTDD										(542),
id-Unused-ProtocolIE-ID-64											(64),
id-PDSCH-RL-ID														(66),
id-HSDSCH-RearrangeList-Bearer-RearrangeInd							(553),
id-UL-Synchronisation-Parameters-LCR								(554),
id-HSDSCH-FDD-Update-Information									(555),
id-HSDSCH-TDD-Update-Information									(556),
id-DL-DPCH-TimeSlotFormat-LCR-ModifyItem-RL-ReconfPrepTDD			(558),
id-UL-DPCH-TimeSlotFormat-LCR-ModifyItem-RL-ReconfPrepTDD			(559),
id-TDD-TPC-UplinkStepSize-LCR-RL-SetupRqstTDD						(560),
id-TDD-TPC-UplinkStepSize-LCR-RL-AdditionRqstTDD					(561),
id-TDD-TPC-DownlinkStepSize-RL-AdditionRqstTDD						(562),
id-TDD-TPC-UplinkStepSize-InformationAdd-LCR-RL-ReconfPrepTDD		(563),
id-TDD-TPC-UplinkStepSize-InformationModify-LCR-RL-ReconfPrepTDD	(564),
id-TDD-TPC-DownlinkStepSize-InformationModify-RL-ReconfPrepTDD		(565),
id-TDD-TPC-DownlinkStepSize-InformationAdd-RL-ReconfPrepTDD		(566),
id-CCTrCH-Maximum-DL-Power-RL-SetupRqstTDD							(567),
id-CCTrCH-Minimum-DL-Power-RL-SetupRqstTDD							(568),
id-CCTrCH-Maximum-DL-Power-RL-AdditionRqstTDD						(569),
id-CCTrCH-Minimum-DL-Power-RL-AdditionRqstTDD						(570),
id-CCTrCH-Maximum-DL-Power-InformationAdd-RL-ReconfPrepTDD			(571),
id-CCTrCH-Minimum-DL-Power-InformationAdd-RL-ReconfPrepTDD			(572),
id-CCTrCH-Maximum-DL-Power-InformationModify-RL-ReconfPrepTDD		(573),
id-CCTrCH-Minimum-DL-Power-InformationModify-RL-ReconfPrepTDD		(574),
id-Maximum-DL-Power-Modify-LCR-InformationModify-RL-ReconfPrepTDD	(575),
id-Minimum-DL-Power-Modify-LCR-InformationModify-RL-ReconfPrepTDD	(576),
id-DL-DPCH-LCR-InformationModify-ModifyList-RL-ReconfRqstTDD		(577),
id-CCTrCH-Maximum-DL-Power-InformationModify-RL-ReconfRqstTDD		(578),
id-CCTrCH-Minimum-DL-Power-InformationModify-RL-ReconfRqstTDD		(579),
id-Initial-DL-Power-TimeslotLCR-InformationItem						(580),
id-Maximum-DL-Power-TimeslotLCR-InformationItem						(581),
id-Minimum-DL-Power-TimeslotLCR-InformationItem						(582),
id-HS-DSCHProvidedBitRateValueInformation							(583),
id-HS-DSCHRequiredPowerValueInformation								(585),
id-HS-DSCHRequiredPowerValue										(586),
id-TransmittedCarrierPowerOfAllCodesNotUsedForHSTransmission			(587),
id-HS-SICH-Reception-Quality 										(588),
id-HS-SICH-Reception-Quality-Measurement-Value 						(589),
id-HSSICH-Info-DM-Rprt 												(590),
id-HSSICH-Info-DM-Rqst												(591),
id-HSSICH-Info-DM-Rsp												(592),
id-Best-Cell-Portions-Value											(593),
id-Primary-CPICH-Usage-for-Channel-Estimation						(594),
id-Secondary-CPICH-Information-Change								(595),
id-NumberOfReportedCellPortions										(596),
id-CellPortion-InformationItem-Cell-SetupRqstFDD					(597),
id-CellPortion-InformationList-Cell-SetupRqstFDD					(598),
id-TimeslotISCP-LCR-InfoList-RL-ReconfPrepTDD						(599),
id-Secondary-CPICH-Information										(600),
id-Received-total-wide-band-power-For-CellPortion					(601),
id-Unidirectional-DCH-Indicator										(602),
id-TimingAdjustmentValueLCR											(603),
id-multipleRL-dl-DPCH-InformationList								(604),
id-multipleRL-dl-DPCH-InformationModifyList							(605),
id-multipleRL-ul-DPCH-InformationList								(606),
id-multipleRL-ul-DPCH-InformationModifyList							(607),
id-RL-ID															(608),
id-SAT-Info-Almanac-ExtItem											(609),
id-HSDPA-Capability													(610),
id-HSDSCH-Resources-Information-AuditRsp							(611),
id-HSDSCH-Resources-Information-ResourceStatusInd					(612),
id-HSDSCH-MACdFlows-to-Add											(613),
id-HSDSCH-MACdFlows-to-Delete										(614),
id-HSDSCH-Information-to-Modify-Unsynchronised						(615),
id-TnlQos															(616),
id-Received-total-wide-band-power-For-CellPortion-Value				(617),
id-Transmitted-Carrier-Power-For-CellPortion						(618),
id-Transmitted-Carrier-Power-For-CellPortion-Value 					(619),
id-TransmittedCarrierPowerOfAllCodesNotUsedForHS-PDSCH-HS-SCCH-E-AGCH-E-RGCHOrE-HICHTransmissionCellPortion		(620),
id-TransmittedCarrierPowerOfAllCodesNotUsedForHS-PDSCH-HS-SCCH-E-AGCH-E-RGCHOrE-HICHTransmissionCellPortionValue	(621),
id-UpPTSInterferenceValue											(622),
id-PrimaryCCPCH-RSCP-Delta											(623),
id-MeasurementRecoveryBehavior										(624),
id-MeasurementRecoveryReportingIndicator							(625),
id-MeasurementRecoverySupportIndicator								(626),
id-Tstd-indicator													(627),
id-multiple-RL-Information-RL-ReconfPrepTDD							(628),
id-multiple-RL-Information-RL-ReconfRqstTDD							(629),
id-DL-DPCH-Power-Information-RL-ReconfPrepFDD						(630),
id-F-DPCH-Information-RL-ReconfPrepFDD								(631),
id-F-DPCH-Information-RL-SetupRqstFDD								(632),
id-Additional-S-CCPCH-Parameters-CTCH-ReconfRqstTDD					(633),
id-Additional-S-CCPCH-Parameters-CTCH-SetupRqstTDD					(634),
id-Additional-S-CCPCH-LCR-Parameters-CTCH-ReconfRqstTDD				(635),
id-Additional-S-CCPCH-LCR-Parameters-CTCH-SetupRqstTDD				(636),
id-MICH-CFN															(637),
id-MICH-Information-AuditRsp										(638),
id-MICH-Information-ResourceStatusInd								(639),
id-MICH-Parameters-CTCH-ReconfRqstFDD								(640),
id-MICH-Parameters-CTCH-ReconfRqstTDD								(641),
id-MICH-Parameters-CTCH-SetupRqstFDD								(642),
id-MICH-Parameters-CTCH-SetupRqstTDD								(643),
id-Modification-Period												(644),
id-NI-Information-NotifUpdateCmd									(645),
id-S-CCPCH-InformationListExt-AuditRsp								(646),
id-S-CCPCH-InformationListExt-ResourceStatusInd						(647),
id-S-CCPCH-LCR-InformationListExt-AuditRsp							(648),
id-S-CCPCH-LCR-InformationListExt-ResourceStatusInd					(649),
id-HARQ-Preamble-Mode												(650),
id-Initial-DL-DPCH-TimingAdjustment									(651),
id-Initial-DL-DPCH-TimingAdjustment-Allowed							(652),
id-DLTransmissionBranchLoadValue									(653),
id-Power-Local-Cell-Group-choice-CM-Rqst							(654),
id-Power-Local-Cell-Group-choice-CM-Rsp								(655),
id-Power-Local-Cell-Group-choice-CM-Rprt							(656),
id-SynchronisationIndicator											(657),
id-HSDPA-And-EDCH-CellPortion-Information-PSCH-ReconfRqst			(658),
id-HSDPA-And-EDCH-CellPortion-InformationList-PSCH-ReconfRqst		(659),
id-HS-DSCHRequiredPowerValue-For-Cell-Portion						(660),
id-HS-DSCHRequiredPowerValueInformation-For-CellPortion				(661),
id-HS-DSCHProvidedBitRateValueInformation-For-CellPortion			(662),
id-E-AGCH-And-E-RGCH-E-HICH-FDD-Scrambling-Code						(663),
id-E-AGCH-FDD-Code-Information										(664),
id-E-DCH-Capability													(665),
id-E-DCH-FDD-DL-Control-Channel-Information							(666),
id-E-DCH-FDD-Information											(667),
id-E-DCH-FDD-Information-Response									(668),
id-E-DCH-FDD-Information-to-Modify									(669),
id-E-DCH-MACdFlows-to-Add											(670),
id-E-DCH-MACdFlows-to-Delete										(671),
id-E-DCH-Resources-Information-AuditRsp								(672),
id-E-DCH-Resources-Information-ResourceStatusInd					(673),
id-E-DCH-RL-Indication												(674),
id-E-DCH-RL-Set-ID													(675),
id-E-DPCH-Information-RL-ReconfPrepFDD								(676),
id-E-DPCH-Information-RL-SetupRqstFDD								(677),
id-E-RGCH-E-HICH-FDD-Code-Information								(678),
id-Serving-E-DCH-RL-ID												(679),
id-UL-DPDCH-Indicator-For-E-DCH-Operation							(680),
id-FDD-S-CCPCH-FrameOffset-CTCH-SetupRqstFDD						(681),
id-E-DPCH-Information-RL-ReconfRqstFDD								(682),
id-Maximum-Target-ReceivedTotalWideBandPower						(683),
id-E-DCHProvidedBitRateValueInformation								(684),
id-HARQ-Preamble-Mode-Activation-Indicator							(685),
id-RL-Specific-E-DCH-Info											(686),
id-E-DCH-CapacityConsumptionLaw										(687),
id-multiple-DedicatedMeasurementValueList-TDD-DM-Rsp				(688),
id-multiple-DedicatedMeasurementValueList-LCR-TDD-DM-Rsp			(689),
id-E-DCH-RearrangeList-Bearer-RearrangeInd							(690),
id-HSDPA-And-EDCH-CellPortion-InformationListIE-PSCH-ReconfRqst		(691),
id-multipleRL-dl-CCTrCH-InformationModifyList-RL-ReconfRqstTDD		(692),
id-Target-NonServing-EDCH-To-Total-EDCH-Power-Ratio					(693),
id-CellPortion-InformationItem-Cell-ReconfRqstFDD					(694),
id-CellPortion-InformationList-Cell-ReconfRqstFDD					(695),
id-multiple-PUSCH-InfoList-DM-Rsp									(696),
id-multiple-PUSCH-InfoList-DM-Rprt									(697),
id-Reference-ReceivedTotalWideBandPower								(698)
} (0..65535)

TransactionID 		::= CHOICE {
	shortTransActionId		INTEGER (0..127),
	longTransActionId		INTEGER (0..32767)
}

TriggeringMessage	::= ENUMERATED { initiating-message, successful-outcome, unsuccessfull-outcome, outcome }

--END

--9.3.7	Container Definitions
-- **************************************************************
--
-- Container definitions
--
-- **************************************************************

--NBAP-Containers {
--itu-t (0) identified-organization (4) etsi (0) mobileDomain (0) 
--umts-Access (20) modules (3) nbap (2) version1 (1) nbap-Containers (5) }

--DEFINITIONS AUTOMATIC TAGS ::= 

--BEGIN

-- **************************************************************
--
-- IE parameter types from other modules.
--
-- **************************************************************

--IMPORTS
--	maxProtocolExtensions,
--	maxPrivateIEs,
--	maxProtocolIEs,
--	Criticality,
--	Presence,
--	PrivateIE-ID,
--	ProtocolIE-ID
--FROM NBAP-CommonDataTypes;

-- **************************************************************
--
-- Class Definition for Protocol IEs
--
-- **************************************************************

--NBAP-PROTOCOL-IES ::= CLASS {
--	&id		ProtocolIE-ID 			UNIQUE,
--	&criticality	Criticality,
--	&Value,
--	&presence	Presence
--}

--WITH SYNTAX {
--	ID		&id
--	CRITICALITY	&criticality
--	TYPE		&Value
--	PRESENCE	&presence
--}

-- **************************************************************
--
-- Class Definition for Protocol IEs
--
-- **************************************************************

--NBAP-PROTOCOL-IES-PAIR ::= CLASS {
--	&id			ProtocolIE-ID 			UNIQUE,
--	&firstCriticality	Criticality,
--	&FirstValue,
--	&secondCriticality	Criticality,
--	&SecondValue,
--	&presence		Presence
--}

--WITH SYNTAX {
--	ID			&id
--	FIRST CRITICALITY	&firstCriticality
--	FIRST TYPE		&FirstValue
--	SECOND CRITICALITY 	&secondCriticality
--	SECOND TYPE		&SecondValue
--	PRESENCE		&presence
--}

-- **************************************************************
--
-- Class Definition for Protocol Extensions
--
-- **************************************************************

--NBAP-PROTOCOL-EXTENSION ::= CLASS {
--	&id		ProtocolIE-ID 		UNIQUE,
--	&criticality	Criticality,
--	&Extension,
--	&presence		Presence
--}

--WITH SYNTAX {
--	ID		&id
--	CRITICALITY	&criticality
--	EXTENSION	&Extension
--	PRESENCE	&presence
--}

-- **************************************************************
--
-- Class Definition for Private IEs
--
-- **************************************************************

--NBAP-PRIVATE-IES ::= CLASS {
--	&id		PrivateIE-ID,
--	&criticality	Criticality,
--	&Value,
--	&presence		Presence
--}


--WITH SYNTAX {
--	ID		&id
--	CRITICALITY	&criticality
--	TYPE	&Value
--	PRESENCE	&presence
--}

-- **************************************************************
--
-- Container for Protocol IEs
--
-- **************************************************************

--ProtocolIE-Container {NBAP-PROTOCOL-IES : IEsSetParam} ::= 
--	SEQUENCE (SIZE (0..maxProtocolIEs)) OF
--	ProtocolIE-Field {{IEsSetParam}}

ProtocolIE-Container ::= 
	SEQUENCE (SIZE (0..65535)) OF
	ProtocolIE-Field

--ProtocolIE-Single-Container {NBAP-PROTOCOL-IES : IEsSetParam} ::=
--	ProtocolIE-Field {{IEsSetParam}}

ProtocolIE-Single-Container ::=
	ProtocolIE-Field 

--ProtocolIE-Field {NBAP-PROTOCOL-IES : IEsSetParam} ::= SEQUENCE {
--	id		NBAP-PROTOCOL-IES.&id		({IEsSetParam}),
--	criticality		NBAP-PROTOCOL-IES.&criticality	({IEsSetParam}{@id}),
--	value		NBAP-PROTOCOL-IES.&Value	 ({IEsSetParam}{@id})
--}
ProtocolIE-Field ::= SEQUENCE {
	id				ProtocolIE-ID,
	criticality		Criticality,
	value			ProtocolIEValue
}

ProtocolIEValue ::= ANY

-- **************************************************************
--
-- Container for Protocol IE Pairs
--
-- **************************************************************

--ProtocolIE-ContainerPair {NBAP-PROTOCOL-IES-PAIR : IEsSetParam} ::= 
--	SEQUENCE (SIZE (0..maxProtocolIEs)) OF
--	ProtocolIE-FieldPair {{IEsSetParam}}

ProtocolIE-ContainerPair ::= 
	SEQUENCE (SIZE (0..65535)) OF
	ProtocolIE-FieldPair

--ProtocolIE-FieldPair {NBAP-PROTOCOL-IES-PAIR : IEsSetParam} ::= SEQUENCE {
--	id				NBAP-PROTOCOL-IES-PAIR.&id			({IEsSetParam}),
--	firstCriticality		NBAP-PROTOCOL-IES-PAIR.&firstCriticality	({IEsSetParam}{@id}),
--	firstValue			NBAP-PROTOCOL-IES-PAIR.&FirstValue	({IEsSetParam}{@id}),
--	secondCriticality		NBAP-PROTOCOL-IES-PAIR.&secondCriticality	({IEsSetParam}{@id}),
--	secondValue			NBAP-PROTOCOL-IES-PAIR.&SecondValue	({IEsSetParam}{@id})
--}

ProtocolIE-FieldPair ::= SEQUENCE {
	id					ProtocolIE-ID,
	firstCriticality	Criticality,
	firstValue			FirstValue,
	secondCriticality	Criticality,
	secondValue			SecondValue
}

FirstValue ::= ANY
SecondValue ::= ANY
-- **************************************************************
--
-- Container Lists for Protocol IE Containers
--
-- **************************************************************

--ProtocolIE-ContainerList {INTEGER : lowerBound, INTEGER : upperBound, NBAP-PROTOCOL-IES : IEsSetParam} ::=
--	SEQUENCE (SIZE (lowerBound..upperBound)) OF
--	ProtocolIE-Container {{IEsSetParam}}

ProtocolIE-ContainerList ::=
	SEQUENCE (SIZE (0..65535)) OF
	ProtocolIE-Container

--ProtocolIE-ContainerPairList {INTEGER : lowerBound, INTEGER : upperBound, NBAP-PROTOCOL-IES-PAIR : IEsSetParam} ::=
--	SEQUENCE (SIZE (lowerBound..upperBound)) OF
--	ProtocolIE-ContainerPair {{IEsSetParam}}

ProtocolIE-ContainerPairList ::=
	SEQUENCE (SIZE (0..65535)) OF
	ProtocolIE-ContainerPair

-- **************************************************************
--
-- Container for Protocol Extensions
--
-- **************************************************************

--ProtocolExtensionContainer {NBAP-PROTOCOL-EXTENSION : ExtensionSetParam} ::= 
--	SEQUENCE (SIZE (1..maxProtocolExtensions)) OF
--	ProtocolExtensionField {{ExtensionSetParam}}

ProtocolExtensionContainer ::= 
	SEQUENCE (SIZE (1..65535)) OF
	ProtocolExtensionField

--ProtocolExtensionField {NBAP-PROTOCOL-EXTENSION : ExtensionSetParam} ::= SEQUENCE {
--	id		NBAP-PROTOCOL-EXTENSION.&id	({ExtensionSetParam}),
--	criticality	NBAP-PROTOCOL-EXTENSION.&criticality	({ExtensionSetParam}{@id}),
--	extensionValue	NBAP-PROTOCOL-EXTENSION.&Extension	({ExtensionSetParam}{@id})
--}
ProtocolExtensionField ::= SEQUENCE {
	id				ProtocolIE-ID,
	criticality		Criticality,
	extensionValue	Extension
}

Extension ::= ANY
-- **************************************************************
--
-- Container for Private IEs
--
-- **************************************************************

--PrivateIE-Container {NBAP-PRIVATE-IES : IEsSetParam} ::= 
--	SEQUENCE (SIZE (1..maxPrivateIEs)) OF
--	PrivateIE-Field {{IEsSetParam}}

PrivateIE-Container ::= 
	SEQUENCE (SIZE (1..65535)) OF
	PrivateIE-Field

--PrivateIE-Field {NBAP-PRIVATE-IES : IEsSetParam} ::= SEQUENCE {
--	id			NBAP-PRIVATE-IES.&id	
--	({IEsSetParam}),
--	criticality			NBAP-PRIVATE-IES.&criticality
--	({IEsSetParam}{@id}),
--	value		NBAP-PRIVATE-IES.&Value
--	({IEsSetParam}{@id})
--}

PrivateIE-Field ::= SEQUENCE {
	privateIEid			PrivateIE-ID,
	criticality			Criticality,
	privateIEvalue		PrivateIEvalue
}

PrivateIEvalue ::= ANY
-- END
END

-- SIGNALLING-CHANNEL-SUSPEND-REDIRECT.asn
--
-- Taken from ITU ASN.1 database
-- http://www.itu.int/ITU-T/asn1/database/itu-t/h/h460.15/2004/SIGNALLING-CHANNEL-SUSPEND-REDIRECT.asn
--

-- Module SIGNALLING-CHANNEL-SUSPEND-REDIRECT (H.460.15:03/2004)
SIGNALLING-CHANNEL-SUSPEND-REDIRECT DEFINITIONS AUTOMATIC TAGS ::=
BEGIN

IMPORTS TransportAddress
          FROM H323-MESSAGES;

SignallingChannelData ::= SEQUENCE {
  signallingChannelData
    CHOICE {channelSuspendRequest   ChannelSuspendRequest,
            channelSuspendResponse  ChannelSuspendResponse,
            channelSuspendConfirm   ChannelSuspendConfirm,
            channelSuspendCancel    ChannelSuspendCancel,
            channelResumeRequest    ChannelResumeRequest,
            channelResumeResponse   ChannelResumeResponse,
            ...},
  ...
}

ChannelSuspendRequest ::= SEQUENCE {
  channelResumeAddress  SEQUENCE OF TransportAddress,
  immediateResume       BOOLEAN,
  resetH245             NULL OPTIONAL,
  ...
}

ChannelSuspendResponse ::= SEQUENCE {
  okToSuspend           BOOLEAN,
  channelResumeAddress  SEQUENCE OF TransportAddress,
  ...
}

ChannelSuspendConfirm ::= SEQUENCE {...
}

ChannelSuspendCancel ::= SEQUENCE {...
}

ChannelResumeRequest ::= SEQUENCE {
  randomNumber  INTEGER(0..4294967295),
  resetH245     NULL OPTIONAL,
  ...
}

ChannelResumeResponse ::= SEQUENCE {...
}

END -- of ASN.1

-- Generated by Asnp, the ASN.1 pretty-printer of France Telecom R&D

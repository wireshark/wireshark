-- CALL-PARTY-CATEGORY.asn
--
-- Taken from ITU ASN.1 database
-- http://www.itu.int/ITU-T/asn1/database/itu-t/h/h460.15/2004/SIGNALLING-CHANNEL-SUSPEND-REDIRECT.asn
--
-- http://www.itu.int/ITU-T/asn1/database/itu-t/h/h460.10/2004/CALL-PARTY-CATEGORY.asn
--

-- Module CALL-PARTY-CATEGORY (H.460.10:03/2004)
CALL-PARTY-CATEGORY DEFINITIONS AUTOMATIC TAGS ::=
BEGIN

CallPartyCategoryInfo ::= SEQUENCE {
  callPartyCategory    CallPartyCategory OPTIONAL,
  originatingLineInfo  OriginatingLineInfo OPTIONAL,
  ...
}

CallPartyCategory ::= INTEGER(0..255)

OriginatingLineInfo ::= INTEGER(0..255)

END

-- Generated by Asnp, the ASN.1 pretty-printer of France Telecom R&D

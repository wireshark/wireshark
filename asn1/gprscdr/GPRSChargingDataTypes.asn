-- $Id$
-- 3GPP TS 32.298 V6.1.0 (2005-09)
--GPRSChargingDataTypes {itu-t identified-organization (4) etsi (0) mobileDomain (0) gsmUmtsNetwork (x) charging (5) asn1Module (z) gprsChargingDataTypes (2) version1 (1)}
GPRSChargingDataTypes {itu-t (0) identified-organization (4) etsi (0) mobileDomain (0) charging (5) gprsChargingDataTypes (2) asn1Module (0) version1 (0)}

DEFINITIONS IMPLICIT TAGS	::=

BEGIN

-- EXPORTS everything

IMPORTS

--CallDuration, CalledNumber, CallEventRecordType, CallingNumber, CallReferenceNumber, CellId, DefaultSMS-Handling, Diagnostics, Ext-GeographicalInformation, IMSI, IMEI, IPAddress, ISDN-AddressString, LCSCause, LCSClientExternalID, LCSClientIdentity, LCSClientInternalID, LCSClientType, LCS-Priority, LCSQoSInfo, LevelOfCAMELService, LocalSequenceNumber, LocationAreaAndCell, LocationAreaCode, LocationType, ManagementExtensions, MessageReference, MSISDN, NotificationToMSUser, PositioningData, RecordingEntity, ServiceKey, SMSResult, SmsTpDestinationNumber, TimeStamp
--
--FROM 3GPPGenericChargingDataTypes {itu-t identified-organization (4) etsi(0) mobileDomain (0) gsmUmtsNetwork (x) charging (y) asn1Module (z) genericChargingDataTypes (0) version1 (1)}


DefaultGPRS-Handling
FROM MAP-MS-DataTypes    { itu-t identified-organization (4) etsi (0) mobileDomain (0)
gsm-Network (1) modules (3) map-MS-DataTypes (11) version6 (6)  }
-- from TS 29.002 [60]


LocationMethod
FROM SS-DataTypes { itu-t identified-organization (4) etsi (0) mobileDomain (0) gsm-Access (2) modules (3) ss-DataTypes (2) version7 (7)}

-- from TS 24.080 [61] (editor's note: correct reference?)

--MBMS2G3GIndicator, FileRepairSupported, MBMSServiceType, MBMSUserServiceType, RequiredMBMSBearerCapabilities, MBMSSessionIdentity, TMGI, MBMSInformation


--FROM MBMSChargingDataTypes {itu-t identified-organization (4) etsi(0) mobileDomain (0) gsm-Network (1) charging (y)  asn1Module (z) mbmsChargingDataTypes (6) version1 (1)}
--FROM MBMSChargingDataTypes {itu-t (0) identified-organization (4) etsi(0) mobileDomain (0) charging (5) mbmsChargingDataTypes (8) asn1Module (0) version1 (0)}

-- Editor's note:  consider moving the above 2 items also into the generic module in order to avoid again copying from external sources.
;

------------------------------------------------------------------------------
--
--  GPRS CALL AND EVENT RECORDS
--
------------------------------------------------------------------------------

GPRSCallEventRecord	::= CHOICE
--
-- Record values 20..27 are GPRS specific
-- Record values 29..30 are GPRS and MBMS specific
{
	sgsnPDPRecord			[20] SGSNPDPRecord,
	ggsnPDPRecord			[21] GGSNPDPRecord,
	sgsnMMRecord			[22] SGSNMMRecord,
	sgsnSMORecord			[23] SGSNSMORecord,
	sgsnSMTRecord			[24] SGSNSMTRecord,
--	sgsnLCTRecord			[25] SGSNLCTRecord,
--	sgsnLCORecord			[26] SGSNLCORecord,
--	sgsnLCNRecord			[27] SGSNLCNRecord,
	egsnPDPRecord			[28] EGSNPDPRecord,
	sgsnMBMSRecord			[29] SGSNMBMSRecord,
	ggsnMBMSRecord			[30] GGSNMBMSRecord
}
-- Editor's note:  the acronyms for the LCS record types are not consistent with CS and the "call event record type" notation.  They also contradict to the record type definitons below, so alignment is needed.

GGSNPDPRecord 	::= SET
{
	recordType					 [0] CallEventRecordType,
	networkInitiation			 [1] NetworkInitiatedPDPContext OPTIONAL,
	servedIMSI					 [3] IMSI,
	ggsnAddress					 [4] GSNAddress,
	chargingID					 [5] ChargingID,
	sgsnAddress					 [6] SEQUENCE OF GSNAddress,
	accessPointNameNI			 [7] AccessPointNameNI OPTIONAL,
	pdpType						 [8] PDPType OPTIONAL,
	servedPDPAddress			 [9] PDPAddress OPTIONAL,
	dynamicAddressFlag			 [11] DynamicAddressFlag OPTIONAL,
	listOfTrafficVolumes		 [12] SEQUENCE OF ChangeOfCharCondition OPTIONAL,
	recordOpeningTime			 [13] TimeStamp,
	duration					 [14] CallDuration,
	causeForRecClosing			 [15] CauseForRecClosing,
	diagnostics					 [16] Diagnostics OPTIONAL,
	recordSequenceNumber		 [17] INTEGER OPTIONAL,
	nodeID						 [18] NodeID OPTIONAL,
	recordExtensions			 [19] ManagementExtensions OPTIONAL,
	localSequenceNumber			 [20] LocalSequenceNumber OPTIONAL,
	apnSelectionMode			 [21] APNSelectionMode OPTIONAL,
	servedMSISDN				 [22] MSISDN OPTIONAL,
	chargingCharacteristics		 [23] ChargingCharacteristics,
	chChSelectionMode			 [24] ChChSelectionMode OPTIONAL,
	iMSsignalingContext			 [25] NULL OPTIONAL,
	externalChargingID			 [26] OCTET STRING OPTIONAL,
	sgsnPLMNIdentifier			 [27] PLMN-Id OPTIONAL,
	pSFurnishChargingInformation [28] PSFurnishChargingInformation OPTIONAL,
	servedIMEISV				 [29] IMEI OPTIONAL,
	rATType						 [30] RATType OPTIONAL,
	mSTimeZone 					 [31] MSTimeZone OPTIONAL,
	userLocationInformation		 [32] OCTET STRING OPTIONAL,
	cAMELChargingInformation	 [33] OCTET STRING OPTIONAL

}

EGSNPDPRecord 	::= SET
{
	recordType					 [0] CallEventRecordType,
	networkInitiation			 [1] NetworkInitiatedPDPContext OPTIONAL,
	servedIMSI					 [3] IMSI,
	ggsnAddress					 [4] GSNAddress,
	chargingID					 [5] ChargingID,
	sgsnAddress					 [6] SEQUENCE OF GSNAddress,
	accessPointNameNI			 [7] AccessPointNameNI OPTIONAL,
	pdpType						 [8] PDPType OPTIONAL,
	servedPDPAddress			 [9] PDPAddress OPTIONAL,
	dynamicAddressFlag			 [11] DynamicAddressFlag OPTIONAL,
	listOfTrafficVolumes		 [12] SEQUENCE OF ChangeOfCharCondition OPTIONAL,
	recordOpeningTime			 [13] TimeStamp,
	duration					 [14] CallDuration,
	causeForRecClosing			 [15] CauseForRecClosing,
	diagnostics					 [16] Diagnostics OPTIONAL,
	recordSequenceNumber		 [17] INTEGER OPTIONAL,
	nodeID						 [18] NodeID OPTIONAL,
	recordExtensions			 [19] ManagementExtensions OPTIONAL,
	localSequenceNumber			 [20] LocalSequenceNumber OPTIONAL,
	apnSelectionMode			 [21] APNSelectionMode OPTIONAL,
	servedMSISDN				 [22] MSISDN OPTIONAL,
	chargingCharacteristics		 [23] ChargingCharacteristics,
	chChSelectionMode			 [24] ChChSelectionMode OPTIONAL,
	iMSsignalingContext			 [25] NULL OPTIONAL,
	externalChargingID			 [26] OCTET STRING OPTIONAL,
	sgsnPLMNIdentifier			 [27] PLMN-Id OPTIONAL,
	pSFurnishChargingInformation [28] PSFurnishChargingInformation OPTIONAL,
	servedIMEISV				 [29] IMEI OPTIONAL,
	rATType						 [30] RATType OPTIONAL,
	mSTimeZone 					 [31] MSTimeZone OPTIONAL,
	userLocationInformation		 [32] OCTET STRING OPTIONAL,
	cAMELChargingInformation	 [33] OCTET STRING OPTIONAL,
	listOfServiceData			 [34] SEQUENCE OF ChangeOfServiceCondition OPTIONAL
}


SGSNMMRecord	::= SET
{
	recordType					[0] CallEventRecordType,
	servedIMSI					[1] IMSI,
	servedIMEI					[2] IMEI OPTIONAL,
	sgsnAddress				    [3] GSNAddress OPTIONAL,
	msNetworkCapability		    [4] MSNetworkCapability OPTIONAL,
	routingArea				    [5] RoutingAreaCode OPTIONAL,
	locationAreaCode			[6] LocationAreaCode OPTIONAL,
	cellIdentifier				[7] CellId OPTIONAL,
	changeLocation				[8] SEQUENCE OF ChangeLocation OPTIONAL,
	recordOpeningTime			[9] TimeStamp,
	duration					[10] CallDuration OPTIONAL,
	sgsnChange					[11] SGSNChange OPTIONAL,
	causeForRecClosing			[12] CauseForRecClosing,
	diagnostics				    [13] Diagnostics OPTIONAL,
	recordSequenceNumber		[14] INTEGER OPTIONAL,
	nodeID						[15] NodeID OPTIONAL,
	recordExtensions			[16] ManagementExtensions OPTIONAL,
	localSequenceNumber		    [17] LocalSequenceNumber OPTIONAL,
	servedMSISDN				[18] MSISDN OPTIONAL,
	chargingCharacteristics	    [19] ChargingCharacteristics,
	cAMELInformationMM 		    [20] CAMELInformationMM OPTIONAL,
	rATType						[21] RATType OPTIONAL,
	chChSelectionMode			[22] ChChSelectionMode OPTIONAL
}

SGSNPDPRecord 	::= SET
{
	recordType					[0] CallEventRecordType,
	networkInitiation			[1] NetworkInitiatedPDPContext OPTIONAL,
	servedIMSI					[3] IMSI,
	servedIMEI					[4] IMEI OPTIONAL,
	sgsnAddress				    [5] GSNAddress OPTIONAL,
	msNetworkCapability		    [6] MSNetworkCapability OPTIONAL,
	routingArea				    [7] RoutingAreaCode OPTIONAL,
	locationAreaCode			[8] LocationAreaCode OPTIONAL,
	cellIdentifier				[9] CellId OPTIONAL,
	chargingID					[10] ChargingID,
	ggsnAddressUsed			    [11] GSNAddress,
	accessPointNameNI			[12] AccessPointNameNI OPTIONAL,
	pdpType						[13] PDPType OPTIONAL,
	servedPDPAddress			[14] PDPAddress OPTIONAL,
	listOfTrafficVolumes		[15] SEQUENCE OF ChangeOfCharCondition OPTIONAL,
	recordOpeningTime			[16] TimeStamp,
	duration					[17] CallDuration,
	sgsnChange					[18] SGSNChange OPTIONAL,
	causeForRecClosing			[19] CauseForRecClosing,
	diagnostics				    [20] Diagnostics OPTIONAL,
	recordSequenceNumber		[21] INTEGER OPTIONAL,
	nodeID						[22] NodeID OPTIONAL,
	recordExtensions			[23] ManagementExtensions OPTIONAL,
	localSequenceNumber		    [24] LocalSequenceNumber OPTIONAL,
	apnSelectionMode			[25] APNSelectionMode OPTIONAL,
	accessPointNameOI			[26] AccessPointNameOI OPTIONAL,
	servedMSISDN				[27] MSISDN OPTIONAL,
	chargingCharacteristics	    [28] ChargingCharacteristics,
	rATType						[29] RATType OPTIONAL,
	cAMELInformationPDP  		[30] CAMELInformationPDP OPTIONAL,
	rNCUnsentDownlinkVolume	    [31] DataVolumeGPRS OPTIONAL,
	chChSelectionMode			[32] ChChSelectionMode OPTIONAL,
	dynamicAddressFlag			[33] DynamicAddressFlag OPTIONAL
}

SGSNSMORecord	::= SET
{
	recordType					[0] CallEventRecordType,
	servedIMSI					[1] IMSI,
	servedIMEI					[2] IMEI OPTIONAL,
	servedMSISDN				[3] MSISDN OPTIONAL,
	msNetworkCapability		    [4] MSNetworkCapability OPTIONAL,
	serviceCentre				[5] AddressString OPTIONAL,
	recordingEntity			    [6] RecordingEntity OPTIONAL,
	locationArea				[7] LocationAreaCode OPTIONAL,
	routingArea				    [8] RoutingAreaCode OPTIONAL,
	cellIdentifier				[9] CellId OPTIONAL,
	messageReference			[10] MessageReference,
	eventTimeStamp		    	[11] TimeStamp,
	smsResult					[12] SMSResult OPTIONAL,
	recordExtensions			[13] ManagementExtensions OPTIONAL,
	nodeID						[14] NodeID OPTIONAL,
	localSequenceNumber		    [15] LocalSequenceNumber OPTIONAL,
	chargingCharacteristics	    [16] ChargingCharacteristics,
	rATType						[17] RATType OPTIONAL,
	destinationNumber			[18] SmsTpDestinationNumber OPTIONAL,
	cAMELInformationSMS		    [19] CAMELInformationSMS OPTIONAL,
	chChSelectionMode			[20] ChChSelectionMode OPTIONAL
}

SGSNSMTRecord	::= SET
{
	recordType				[0] CallEventRecordType,
	servedIMSI				[1] IMSI,
	servedIMEI				[2] IMEI OPTIONAL,
	servedMSISDN			[3] MSISDN OPTIONAL,
	msNetworkCapability	    [4] MSNetworkCapability OPTIONAL,
	serviceCentre			[5] AddressString OPTIONAL,
	recordingEntity		    [6] RecordingEntity OPTIONAL,
	locationArea			[7] LocationAreaCode OPTIONAL,
	routingArea			    [8] RoutingAreaCode OPTIONAL,
	cellIdentifier			[9] CellId OPTIONAL,
	eventTimeStamp		    [10] TimeStamp,
	smsResult				[11] SMSResult OPTIONAL,
	recordExtensions		[12] ManagementExtensions OPTIONAL,
	nodeID					[13] NodeID OPTIONAL,
	localSequenceNumber	    [14] LocalSequenceNumber OPTIONAL,
	chargingCharacteristics	[15] ChargingCharacteristics,
	rATType					[16] RATType OPTIONAL,
	chChSelectionMode		[17] ChChSelectionMode OPTIONAL,
	cAMELInformationSMS		[18] CAMELInformationSMS OPTIONAL
}

SGSNMTLCSRecord			::= SET
{
	recordType				[0] CallEventRecordType,
	recordingEntity			[1] RecordingEntity,
	lcsClientType			[2] LCSClientType,
	lcsClientIdentity		[3] LCSClientIdentity,
	servedIMSI				[4] IMSI,
	servedMSISDN			[5] MSISDN OPTIONAL,
	sgsnAddress				[6] GSNAddress OPTIONAL,
	locationType			[7] LocationType,
	lcsQos					[8] LCSQoSInfo OPTIONAL,
	lcsPriority				[9] LCS-Priority OPTIONAL,
	mlcNumber				[10] ISDN-AddressString,
	eventTimeStamp			[11] TimeStamp,
	measurementDuration		[12] CallDuration OPTIONAL,
	notificationToMSUser	[13] NotificationToMSUser OPTIONAL,
	privacyOverride			[14] NULL OPTIONAL,
	location				[15] LocationAreaAndCell OPTIONAL,
	routingArea			    [16] RoutingAreaCode OPTIONAL,
	locationEstimate		[17] Ext-GeographicalInformation OPTIONAL,
	positioningData			[18] PositioningData OPTIONAL,
	lcsCause				[19] LCSCause OPTIONAL,
	diagnostics				[20] Diagnostics OPTIONAL,
	nodeID					[21] NodeID OPTIONAL,
	localSequenceNumber	    [22] LocalSequenceNumber OPTIONAL,
	chargingCharacteristics	[23] ChargingCharacteristics,
	chChSelectionMode		[24] ChChSelectionMode OPTIONAL,
	rATType					[25] RATType OPTIONAL,
	recordExtensions		[26] ManagementExtensions OPTIONAL,
	causeForRecClosing		[27] CauseForRecClosing
}

SGSNMOLCSRecord			::= SET
{
	recordType				[0] CallEventRecordType,
	recordingEntity			[1] RecordingEntity,
	lcsClientType			[2] LCSClientType OPTIONAL,
	lcsClientIdentity		[3] LCSClientIdentity OPTIONAL,
	servedIMSI				[4] IMSI,
	servedMSISDN			[5] MSISDN OPTIONAL,
	sgsnAddress				[6] GSNAddress OPTIONAL,
	locationMethod			[7] LocationMethod,
	lcsQos					[8] LCSQoSInfo OPTIONAL,
	lcsPriority				[9] LCS-Priority OPTIONAL,
	mlcNumber				[10] ISDN-AddressString OPTIONAL,
	eventTimeStamp			[11] TimeStamp,
	measurementDuration		[12] CallDuration OPTIONAL,
	location				[13] LocationAreaAndCell OPTIONAL,
	routingArea			    [14] RoutingAreaCode OPTIONAL,
	locationEstimate		[15] Ext-GeographicalInformation OPTIONAL,
	positioningData			[16] PositioningData OPTIONAL,
	lcsCause				[17] LCSCause OPTIONAL,
	diagnostics				[18] Diagnostics OPTIONAL,
	nodeID					[19] NodeID OPTIONAL,
	localSequenceNumber	    [20] LocalSequenceNumber OPTIONAL,
	chargingCharacteristics	[21] ChargingCharacteristics,
	chChSelectionMode		[22] ChChSelectionMode OPTIONAL,
	rATType					[23] RATType OPTIONAL,
	recordExtensions		[24] ManagementExtensions OPTIONAL,
	causeForRecClosing		[25] CauseForRecClosing
}

SGSNNILCSRecord			::= SET
{
	recordType				[0] CallEventRecordType,
	recordingEntity			[1] RecordingEntity,
	lcsClientType			[2] LCSClientType OPTIONAL,
	lcsClientIdentity		[3] LCSClientIdentity OPTIONAL,
	servedIMSI				[4] IMSI OPTIONAL,
	servedMSISDN			[5] MSISDN OPTIONAL,
	sgsnAddress				[6] GSNAddress OPTIONAL,
	servedIMEI				[7] IMEI OPTIONAL,
	lcsQos					[8] LCSQoSInfo OPTIONAL,
	lcsPriority				[9] LCS-Priority OPTIONAL,
	mlcNumber				[10] ISDN-AddressString OPTIONAL,
	eventTimeStamp			[11] TimeStamp,
	measurementDuration		[12] CallDuration OPTIONAL,
	location				[13] LocationAreaAndCell OPTIONAL,
	routingArea			    [14] RoutingAreaCode OPTIONAL,
	locationEstimate		[15] Ext-GeographicalInformation OPTIONAL,
	positioningData			[16] PositioningData OPTIONAL,
	lcsCause				[17] LCSCause OPTIONAL,
	diagnostics				[18] Diagnostics OPTIONAL,
	nodeID					[19] NodeID OPTIONAL,
	localSequenceNumber	    [20] LocalSequenceNumber OPTIONAL,
	chargingCharacteristics	[21] ChargingCharacteristics,
	chChSelectionMode		[22] ChChSelectionMode OPTIONAL,
	rATType					[23] RATType OPTIONAL,
	recordExtensions		[24] ManagementExtensions OPTIONAL,
	causeForRecClosing		[25] CauseForRecClosing
}

SGSNMBMSRecord 	::= SET
{
	recordType					 [0] CallEventRecordType,
	ggsnAddress					 [1] GSNAddress,
	chargingID					 [2] ChargingID,
	listofDownstreamNodes		 [3] SEQUENCE OF RouteingAreaCode,
	accessPointNameNI			 [4] AccessPointNameNI OPTIONAL,
	servedPDPAddress			 [5] PDPAddress OPTIONAL,
	listOfTrafficVolumes		 [6] SEQUENCE OF ChangeOfCharCondition OPTIONAL,
	recordOpeningTime			 [7] TimeStamp,
	duration					 [8] CallDuration,
	causeForRecClosing			 [9] CauseForRecClosing,
	diagnostics					 [10] Diagnostics OPTIONAL,
	recordSequenceNumber		 [11] INTEGER OPTIONAL,
	nodeID						 [12] NodeID OPTIONAL,
	recordExtensions			 [13] ManagementExtensions OPTIONAL,
	localSequenceNumber			 [14] LocalSequenceNumber OPTIONAL,
	sgsnPLMNIdentifier			 [15] PLMN-Id OPTIONAL,
	numberofReceivingUE			 [16] INTEGER OPTIONAL,
	mbmsInformation				 [17] MBMSInformation OPTIONAL

}
-- WS no def found
RouteingAreaCode ::= OCTET STRING

GGSNMBMSRecord 	::= SET
{
	recordType					 [0] CallEventRecordType,
	ggsnAddress					 [1] GSNAddress,
	chargingID					 [2] ChargingID,
	listofDownstreamNodes		 [3] SEQUENCE OF GSNAddress,
	accessPointNameNI			 [4] AccessPointNameNI OPTIONAL,
	servedPDPAddress			 [5] PDPAddress OPTIONAL,
	listOfTrafficVolumes		 [6] SEQUENCE OF ChangeOfCharCondition OPTIONAL,
	recordOpeningTime			 [7] TimeStamp,
	duration					 [8] CallDuration,
	causeForRecClosing			 [9] CauseForRecClosing,
	diagnostics					 [10] Diagnostics OPTIONAL,
	recordSequenceNumber		 [11] INTEGER OPTIONAL,
	nodeID						 [12] NodeID OPTIONAL,
	recordExtensions			 [13] ManagementExtensions OPTIONAL,
	localSequenceNumber			 [14] LocalSequenceNumber OPTIONAL,
	mbmsInformation				 [15] MBMSInformation OPTIONAL
}

------------------------------------------------------------------------------
--
--  COMMON DATA TYPES
--
------------------------------------------------------------------------------

AccessPointNameNI	::= IA5String (SIZE(1..63))
	--
	-- Network Identifier part of APN in  dot representation.
	-- For example, if the complete APN is 'apn1a.apn1b.apn1c.mnc022.mcc111.gprs'
	-- NI is 'apn1a.apn1b.apn1c' and is presented in this form in the CDR..
	--

AccessPointNameOI	::= IA5String (SIZE(1..37))
	--
	-- Operator Identifier part of APN in dot representation.
	-- In the 'apn1a.apn1b.apn1c.mnc022.mcc111.gprs' example, the OI portion is 'mnc022.mcc111.gprs'
	-- and is presented in this form in the CDR.
	--

APNSelectionMode::= ENUMERATED
{
	--
	-- See Information Elements TS 29.060 [75]
	--
	mSorNetworkProvidedSubscriptionVerified				(0),
	mSProvidedSubscriptionNotVerified					(1),
	networkProvidedSubscriptionNotVerified				(2)
}

CAMELAccessPointNameNI	::= AccessPointNameNI

CAMELAccessPointNameOI	::= AccessPointNameOI

CAMELInformationMM		::= SET
{
	sCFAddress						[1] SCFAddress OPTIONAL,
	serviceKey						[2]	ServiceKey OPTIONAL,
	defaultTransactionHandling	    [3]	DefaultGPRS-Handling OPTIONAL,
	numberOfDPEncountered  		    [4] NumberOfDPEncountered OPTIONAL,
	levelOfCAMELService			    [5] LevelOfCAMELService OPTIONAL,
	freeFormatData					[6] FreeFormatData OPTIONAL,
	fFDAppendIndicator	     		[7]	FFDAppendIndicator OPTIONAL
}

CAMELInformationPDP	::= SET
{
	sCFAddress						[1] SCFAddress OPTIONAL,
	serviceKey						[2]	ServiceKey OPTIONAL,
	defaultTransactionHandling	    [3]	DefaultGPRS-Handling OPTIONAL,
	cAMELAccessPointNameNI		    [4] CAMELAccessPointNameNI OPTIONAL,
	cAMELAccessPointNameOI		    [5] CAMELAccessPointNameOI OPTIONAL,
	numberOfDPEncountered  		    [6] NumberOfDPEncountered OPTIONAL,
	levelOfCAMELService			    [7] LevelOfCAMELService OPTIONAL,
	freeFormatData					[8]	FreeFormatData OPTIONAL,
	fFDAppendIndicator	     		[9]	FFDAppendIndicator OPTIONAL
}

CAMELInformationSMS		::= SET
{
	sCFAddress								[1] SCFAddress OPTIONAL,
	serviceKey								[2]	ServiceKey OPTIONAL,
	defaultSMSHandling						[3]	DefaultSMS-Handling OPTIONAL,
	cAMELCallingPartyNumber				    [4] CallingNumber OPTIONAL,
	cAMELDestinationSubscriberNumber		[5] SmsTpDestinationNumber OPTIONAL,
	cAMELSMSCAddress						[6] AddressString OPTIONAL,
	freeFormatData							[7]	FreeFormatData OPTIONAL,
	smsReferenceNumber						[8] CallReferenceNumber	OPTIONAL
}

CategoryId ::= INTEGER
-- IP service flow identity (DCCA)
-- range of 4 byte (0..4294967259)

CauseForRecClosing	::= INTEGER
{
	--
	-- In GGSN the value sGSNChange should be used for partial record
	-- generation due to SGSN Address List Overflow
	--
	-- LCS related causes belong to the MAP error causes acc. TS 29.002
	--
	-- cause codes 0 to 15 are defined in TS 32.205 as 'CauseForTerm' (cause for termination)
	--
	normalRelease					(0),
	abnormalRelease			    	(4),
	cAMELInitCallRelease			(5),
	volumeLimit				    	(16),
	timeLimit						(17),
	sGSNChange						(18),
	maxChangeCond					(19),
	managementIntervention	    	(20),
    intraSGSNIntersystemChange		(21),
	rATChange						(22),
	unauthorizedRequestingNetwork	(52),
	unauthorizedLCSClient			(53),
	positionMethodFailure			(54),
	unknownOrUnreachableLCSClient	(58),
	listofDownstreamNodeChange		(59)
}

ChangeCondition	::= ENUMERATED
{
	qoSChange				(0),
	tariffTime				(1),
	recordClosure			(2)
}

ChangeOfCharCondition	::= SEQUENCE
{
	--
	-- Used in PDP context record only
	--
	qosRequested				[1] QoSInformation OPTIONAL,
	qosNegotiated				[2] QoSInformation OPTIONAL,
	dataVolumeGPRSUplink		[3] DataVolumeGPRS,
	dataVolumeGPRSDownlink	    [4] DataVolumeGPRS,
	changeCondition			    [5] ChangeCondition,
	changeTime					[6] TimeStamp
}

ChangeOfServiceCondition	::= SEQUENCE
{
	--
	-- Used for Flow based Charging service data container
	--
	categoryId                  [1] CategoryId,
	ratingGroupId               [2] RatingGroupId,
	localSequenceNumber			[3] LocalSequenceNumber OPTIONAL,
	timeOfFirstUsage            [4] TimeStamp,
	timeOfLastUsage             [5] TimeStamp,
	timeUsage                   [6] CallDuration,
	serviceChangeCause      	[7] ServiceChangeCause,
	qoSInformationNeg           [8] QoSInformation OPTIONAL,
	sgsn-Address                [9] GSNAddress OPTIONAL,
	sGSNPLMNIdentifier          [10] SGSNPLMNIdentifier OPTIONAL,
	datavolumeFBCUplink         [11] DataVolumeGPRS,
	datavolumeFBCDownlink       [12] DataVolumeGPRS,
	timeOfReport				[13] TimeStamp,
	rATType						[14] RATType OPTIONAL
}

-- WS No def. found
SGSNPLMNIdentifier ::= OCTET STRING
ChangeLocation	::= SEQUENCE
{
	--
	-- used in SGSNMMRecord only
	--
	locationAreaCode		[0] LocationAreaCode,
	routingAreaCode		    [1] RoutingAreaCode,
	cellId					[2] CellId OPTIONAL,
	changeTime				[3] TimeStamp
}

ChargingCharacteristics	::= OCTET STRING (SIZE(2))
    --
	--	Bit 0-3: Profile Index
	--	Bit 4-15: For Behavior
	--

ChargingID	::= INTEGER (0..4294967295)
	--
	-- Generated in GGSN, part of PDP context, see TS 23.060
	-- 0..4294967295 is equivalent to 0..2**32-1
	--

ChChSelectionMode		::= ENUMERATED
{
	sGSNSupplied				(0),	-- For GGSN only
	subscriptionSpecific		(1),	-- For SGSN only
	aPNSpecific					(2),	-- For SGSN only
	homeDefault					(3),	-- For SGSN and GGSN
	roamingDefault				(4),	-- For SGSN and GGSN
	visitingDefault				(5)		-- For SGSN and GGSN
}


DataVolumeGPRS	::= INTEGER
	--
	-- The volume of data transferred in octets.
	--

DynamicAddressFlag	::= BOOLEAN

ETSIAddress	::= AddressString
	--
	-- First octet for nature of address, and numbering plan indicator (3 for X.121)
	-- Other octets TBCD
	-- See TS 29.002
	--

FFDAppendIndicator	::= BOOLEAN

FreeFormatData	::=	OCTET STRING (SIZE(1..160))
	--
	-- Free formated data as sent in the FurnishChargingInformationGPRS
	-- see TS 29.078
	--

GSNAddress	::= IPAddress

MSNetworkCapability	::= OCTET STRING (SIZE(1..8))
	-- see 3G TS 24.008

NetworkInitiatedPDPContext	::= BOOLEAN
	--
	-- Set to true if PDP context was initiated from network side
	--

NodeID	::= IA5String (SIZE(1..20))

NumberOfDPEncountered  ::= INTEGER

PDPAddress	::= CHOICE
{
	iPAddress				[0] IPAddress,
	eTSIAddress			    [1] ETSIAddress
}

PDPType		::= OCTET STRING (SIZE(2))
	--
	-- OCTET 1: PDP Type Organization
	-- OCTET 2: PDP Type Number
	-- See TS 29.060 [75]
	--

PLMN-Id		::= OCTET STRING (SIZE (3))
	--	This is a 1:1 copy from the Routing Area Identity (RAI) IE specified in TS 29.060 [75]
	--  as follows:
	--	OCTET 1 of PLMN-Id = OCTET 2 of RAI
	--	OCTET 2 of PLMN-Id = OCTET 3 of RAI
	--	OCTET 3 of PLMN-Id = OCTET 4 of RAI




PSFurnishChargingInformation  ::= SEQUENCE

{
	pSFreeFormatData			[1] FreeFormatData,
	pSFFDAppendIndicator  	    [2] FFDAppendIndicator OPTIONAL
}


QoSInformation	::= OCTET STRING (SIZE (4..12))

	--
	-- This  octet string
	-- is a 1:1 copy of the contents (i.e. starting with octet 4) of the "Quality of
	-- service Profile" information element specified in 3GPP TS 29.060 [75].

--RATType	::= INTEGER (0..255)
RATType	::= INTEGER
	--
	-- Ihis integer is 1:1 copy of the RAT type value as defined in 3GPP TS 29.060 [75].
	--
-- WS Extension
{
	reserved			(0),
	utran				(1),
	geran				(2),
	wlan				(3),
	gan					(4),
	hspa-evolution		(5)
}(0..255)

RoutingAreaCode	::= OCTET STRING (SIZE(1))
	--
	-- See TS 24.008	--
	--

RatingGroupId ::= IA5String (SIZE(1..16))
-- DCC rule base identifier

ServiceChangeCause	::= OCTET STRING (SIZE(4))
	--
-- service container closure reason
-- (some of the values are non-exclusive)
--
-- cause values for Gn update/release and TTS
--  H'00000001 (Bit  1): QoS change
--  H'00000002 (Bit  2): SGSN change
--  H'00000004 (Bit  3): SGSN PLMN ID change
--  H'00000008 (Bit  4): tariff time switch
--  H'00000010 (Bit  5): PDP context release
--  H'00000020 (Bit  6): RAT change
--
-- cause values for service stop:
--  H'00000040 (Bit  7): service idled out (= service release by QHT)
--  H'00000080 (Bit  8): not used
--  H'00000100 (Bit  9): configuration change
--  H'00000200 (Bit 10): service stop
--
-- cause values for service reauthorization request:
--  H'00000400 (Bit 11): time threshold reached
--  H'00000800 (Bit 12): volume threshold reached
--  H'00001000 (Bit 13): time exhausted
--  H'00002000 (Bit 14): volume exhausted
--
-- cause values for quota return:
--  H'00004000 (Bit 15): timeout
--  H'00008000 (Bit 16): return requested
--  H'00010000 (Bit 17): reauthorisation request
--  			Bit 18-32: are unused and will always be zero

SCFAddress	::= AddressString
	--
	-- See TS 29.002	--
	--

SGSNChange	::= BOOLEAN
	--
	-- present if first record after inter SGSN routing area update
	-- in new SGSN
	--

-- WS Loacly imported MBMS structs

MBMSInformation			::= SET
{
	tMGI						[1] TMGI OPTIONAL,
	mBMSSessionIdentity			[2] MBMSSessionIdentity OPTIONAL,
	mBMSServiceType				[3] MBMSServiceType OPTIONAL,
	mBMSUserServiceType			[4] MBMSUserServiceType OPTIONAL, -- only supported in the BM-SC
	mBMS2G3GIndicator			[5] MBMS2G3GIndicator OPTIONAL,
	fileRepairSupported			[6] BOOLEAN OPTIONAL,			  -- only supported in the BM-SC
	rAI							[7] RoutingAreaCode OPTIONAL,	  -- only supported in the BM-SC
	mBMSServiceArea				[8] MBMSServiceArea OPTIONAL,
	requiredMBMSBearerCaps		[9] RequiredMBMSBearerCapabilities OPTIONAL,
	mBMSGWAddress				[10] GSNAddress OPTIONAL,
	cNIPMulticastDistribution	[11] CNIPMulticastDistribution OPTIONAL
}

MBMS2G3GIndicator		::= ENUMERATED
{
	t2G				(0),	-- For GERAN access only
	t3G				(1),	-- For UTRAN access only
	t2G-AND-3G		(2) 	-- For both UTRAN and GERAN access
}


MBMSServiceType		::= ENUMERATED
{
	mULTICAST		(0),
	bROADCAST		(1)
}

MBMSUserServiceType		::= ENUMERATED
{
	dOWNLOAD		(0),
	sTREAMING		(1)
}

RequiredMBMSBearerCapabilities		::= OCTET STRING (SIZE (3..14))

--
-- This  octet string
-- is a 1:1 copy of the contents (i.e. starting with octet 5) of the "Quality of
-- service Profile" information element specified in 3GPP TS 29.060 [75].
--


MBMSSessionIdentity		::= OCTET STRING (SIZE (1))

--
-- This octet string is a 1:1 copy of the contents of the MBMS-Session-Identity
-- AVP specified in 3GPP TS 29.061 [82]
--

TMGI		::= OCTET STRING
--
-- This  octet string
-- is a 1:1 copy of the contents (i.e. starting with octet 4) of the "TMGI"
-- information element specified in 3GPP TS 29.060 [75].
--

MBMSServiceArea		::= OCTET STRING

CNIPMulticastDistribution		::= ENUMERATED
{
	nO-IP-MULTICAST				(0),
	iP-MULTICAST				(1)
}

END

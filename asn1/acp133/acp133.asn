ACP133CommonContent { joint-iso-ccitt(2) country(16) us(840) organization(1) gov(101) dod(2) ds(2) module(0) commonContent(2) editionB (3) }
DEFINITIONS ::=
BEGIN
IMPORTS
  GeneralNames, CertificateAssertion
    FROM CertificateExtensions {joint-iso-ccitt ds(5)
               module(1) certificateExtensions(26) 0}
  AlgorithmIdentifier
    --==
    FROM AuthenticationFramework {joint-iso-itu-t ds(5) module(1)
      authenticationFramework(7) 3}
  ContentLength, EncodedInformationTypesConstraints, ExtendedContentType,
    ORAddress, ORName, RequestedDeliveryMethod, SecurityContext
    --==
    FROM MTSAbstractService {joint-iso-itu-t mhs(6) mts(3) modules(0)
      mts-abstract-service(1) version-1999(1)}
    DirectoryString
    --==
    FROM SelectedAttributeTypes {joint-iso-itu-t ds(5) module(1)
      selectedAttributeTypes(5) 4}
    Name
    --==
    FROM InformationFramework {joint-iso-itu-t ds(5) module(1)
      informationFramework(1) 3};



ACPPreferredDelivery ::= ENUMERATED { smtp(0), acp127(1), mhs(2) }

ALType ::= INTEGER { aig(0), type(1), cad(2), taskforce(3), dag(4) }

Community ::= ENUMERATED { genser(0), si(1), both(2) }

OnSupported ::= BIT STRING { acp127-nn(0), acp127-pn(1), acp127-tn(2) }

ACPLegacyFormat ::= INTEGER {
	janap128(0),
	acp127(1), -- changed from acp126 for consistency purposes
	doi103(2),
	doi103-special(3),
	acp127(4),
	acp127-converted(5),
	reserved-1(6), -- hold for ACP127Standard if needed
	acp127-state(7),
	acp127-modified(8),
	socomm-special(9),
	socomm-narrative(10),
	reserved-2(11), -- hold for SOCOMMNarrativeTTY if needed
	socomm-narrative-special(12),
	socomm-data(13),
	socomm-internal(14),
	socomm-external(15),
	mfi-default(16),
	acp-legacy-format-smtp(17),
	p22(18),
	-- 19 - 31 for national or bilateral use
	acp145-united-states(32),
	acp145-australia(33),
	acp145-canada(34),
	acp145-united-kingdom(35),
	acp145-new-zealand(36) }

ACPNoAttachments ::= BOOLEAN

Active ::= BOOLEAN

Addressees ::= SEQUENCE OF PrintableString (SIZE (1..55))

Classification ::= ENUMERATED { unmarked(0), unclassified(1), restricted(2),
confidential(3), secret(4), top-secret(5) }

DistributionCode ::= PrintableString

EmConCapability ::= BOOLEAN

EmConState ::= ENUMERATED { enabled(0), receive-only(1), electronic-silence(2), disabled(3) }

JPEG ::= OCTET STRING -- a JPEG image

MaxMessageSize ::= INTEGER

MonthlyUKMs ::= --SIGNED { SEQUENCE OF UKMEntry }-- SEQUENCE {
  ukm-entries			SEQUENCE OF UKMEntry,
  algorithm-identifier		AlgorithmIdentifier,
  encrypted			BIT STRING
}

MsgProtocolInfoCapability ::= ENUMERATED { acp-127(0), acp-123(1) }

Remarks ::= SEQUENCE OF PrintableString

-- RIParameters used to be defined as a ASN.1 SET specification, but
-- this has been deprecated in edition D in favour of a DirectoryString
-- containing a sequence of dollar separated PrintableStrings.
--
-- Implemented in Wireshark as a CHOICE to be able to decode both without
-- using a preference.
RIParameters ::= CHOICE {
	ri-parameters             DirectoryString,
	ri-parameters-deprecated  RIParametersDeprecated
}

RIParametersDeprecated ::= SET {
	rI 		[0] PrintableString,
	rIType 		[1] ENUMERATED 
	{ normal(0), off-line(1), partTimeTerminal(2) },
	minimize 	[2] BOOLEAN, -- not used any more --
	sHD 		[3] PrintableString,
	classification 	[4] Classification
}

UKMEntry ::= SEQUENCE {
	tag PairwiseTag,
	ukm OCTET STRING
}

WebAccessCapability ::= BOOLEAN

-- these are imported directly from SDN.701

PairwiseTag  			::= SEQUENCE  {
	kmid		Kmid,
	edition		INTEGER --(1..ub-edition-size)--,
	date		UTCTime OPTIONAL }

Kmid 			::=  OCTET STRING

MLReceiptPolicy		::=  CHOICE  {
     none		[0] NULL,
     insteadOf		[1] SEQUENCE -- (SIZE (1..ub-insteadOf))
						OF GeneralNames,
     inAdditionTo	[2] SEQUENCE --(SIZE (1..ub-inAdditionTo))
						OF GeneralNames }

END

-- Required for support for h248v1
--
-- $Id$
-- 
-- This file represents the differences between h248v1 and the h248v3, the current version
-- This file is included in the Makefile generate_dissectors and related tasks necessary
-- to generate epan/dissectors/packet-h248.[ch]

H238V1-SUPPORT DEFINITIONS IMPLICIT TAGS ::=
BEGIN
	
	--	V1 version of AuditReply
	AuditReplyV1 ::= SEQUENCE
	{
		terminationID		[0] TerminationID,
		auditResult			[1] AuditResultV1
	}
	
	--	V1 Version of AuditResult
	AuditResultV1 ::= CHOICE
	{
		contectAuditResult		[0] TerminationID,
		terminationAuditResult	[1] TerminationAudit
	}
		
	-- V1
	EventParameterV1 ::= SEQUENCE
	{
		eventParamterName		[0] EventParameterName,
		value					[1] EventParamValueV1
	}
		
	-- V1

	SigParameterV1 ::= SEQUENCE
	{
		sigParameterName	[0] SigParameterName,
		value				[1] SigParamValueV1
--		value				[1] ValueV1
		
	}
	
--	ValueV1 ::= OCTET STRING
	EventParamValueV1 ::= OCTET STRING
	SigParamValueV1 ::= OCTET STRING

END
